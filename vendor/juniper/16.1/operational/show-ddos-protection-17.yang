/*
 * Copyright (c) 2017 Juniper Networks, Inc.
 * All rights reserved.
 */

 module show-ddos-protection-17 {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-ddos-syslog-aggregate-flows {
     description "Show aggregate culprit flows";
     input {
       leaf fpc-slot {
         description "FPC slot number";
         type uint32 {
           range "0 .. 63";
         }
       }
       leaf level {
         type enumeration {
           enum "brief" {
             description "Show brief output";
           }
           enum "detail" {
             description "Show detailed output";
           }
           enum "summary" {
             description "Show flow information summary";
           }
         }
       }
     }
     output {
       container ddos-protocols-information {
         container detail {
           leaf total-packet-types {
             type int32;
             description "Total number of packet types";
           }
           leaf mod-packet-types {
             type int32;
             description "Number of packet types modified through user configuration";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container parameters {
           leaf total-packet-types {
             type int32;
             description "Total number of packet types";
           }
           leaf mod-packet-types {
             type int32;
             description "Number of packet types modified through user configuration";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container statistics {
           leaf total-packet-types {
             type int32;
             description "Total number of packet types";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container culprit-flows {
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container violations {
           leaf total-packet-types {
             type int32;
             description "Total number of packet types";
           }
           leaf packet-types-in-violation {
             type int32;
             description "Number of packet types receiving excess traffic";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
       }
     }
   }
   rpc get-ddos-ptpv6-information {
     description "Show PTPv6 traffic information";
     output {
       container ddos-protocols-information {
         container detail {
           leaf total-packet-types {
             type int32;
             description "Total number of packet types";
           }
           leaf mod-packet-types {
             type int32;
             description "Number of packet types modified through user configuration";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container parameters {
           leaf total-packet-types {
             type int32;
             description "Total number of packet types";
           }
           leaf mod-packet-types {
             type int32;
             description "Number of packet types modified through user configuration";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container statistics {
           leaf total-packet-types {
             type int32;
             description "Total number of packet types";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container culprit-flows {
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container violations {
           leaf total-packet-types {
             type int32;
             description "Total number of packet types";
           }
           leaf packet-types-in-violation {
             type int32;
             description "Number of packet types receiving excess traffic";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
       }
     }
   }
   rpc get-ddos-ptpv6-parameters {
     description "Show PTPV6 protocol parameters";
     input {
       leaf level {
         type enumeration {
           enum "brief" {
             description "Show brief output";
           }
           enum "detail" {
             description "Show detailed output";
           }
           enum "terse" {
             description "Show terse output";
           }
         }
       }
     }
     output {
       container ddos-protocols-information {
         container detail {
           leaf total-packet-types {
             type int32;
             description "Total number of packet types";
           }
           leaf mod-packet-types {
             type int32;
             description "Number of packet types modified through user configuration";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container parameters {
           leaf total-packet-types {
             type int32;
             description "Total number of packet types";
           }
           leaf mod-packet-types {
             type int32;
             description "Number of packet types modified through user configuration";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container statistics {
           leaf total-packet-types {
             type int32;
             description "Total number of packet types";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container culprit-flows {
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container violations {
           leaf total-packet-types {
             type int32;
             description "Total number of packet types";
           }
           leaf packet-types-in-violation {
             type int32;
             description "Number of packet types receiving excess traffic";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
       }
     }
   }
   rpc get-ddos-ptpv6-statistics {
     description "Show PTPV6 statistics and states";
     input {
       leaf level {
         type enumeration {
           enum "brief" {
             description "Show brief output";
           }
           enum "detail" {
             description "Show detailed output";
           }
           enum "terse" {
             description "Show terse output";
           }
         }
       }
     }
     output {
       container ddos-protocols-information {
         container detail {
           leaf total-packet-types {
             type int32;
             description "Total number of packet types";
           }
           leaf mod-packet-types {
             type int32;
             description "Number of packet types modified through user configuration";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container parameters {
           leaf total-packet-types {
             type int32;
             description "Total number of packet types";
           }
           leaf mod-packet-types {
             type int32;
             description "Number of packet types modified through user configuration";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container statistics {
           leaf total-packet-types {
             type int32;
             description "Total number of packet types";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container culprit-flows {
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container violations {
           leaf total-packet-types {
             type int32;
             description "Total number of packet types";
           }
           leaf packet-types-in-violation {
             type int32;
             description "Number of packet types receiving excess traffic";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
       }
     }
   }
   rpc get-ddos-ptpv6-violations {
     description "Show PTPV6 traffic violations";
     output {
       container ddos-protocols-information {
         container detail {
           leaf total-packet-types {
             type int32;
             description "Total number of packet types";
           }
           leaf mod-packet-types {
             type int32;
             description "Number of packet types modified through user configuration";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container parameters {
           leaf total-packet-types {
             type int32;
             description "Total number of packet types";
           }
           leaf mod-packet-types {
             type int32;
             description "Number of packet types modified through user configuration";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container statistics {
           leaf total-packet-types {
             type int32;
             description "Total number of packet types";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container culprit-flows {
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container violations {
           leaf total-packet-types {
             type int32;
             description "Total number of packet types";
           }
           leaf packet-types-in-violation {
             type int32;
             description "Number of packet types receiving excess traffic";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
       }
     }
   }
   rpc get-ddos-ptpv6-flow-parameters {
     description "Show PTPV6 flow detection parameters";
     input {
       leaf level {
         type enumeration {
           enum "brief" {
             description "Show brief output";
           }
           enum "detail" {
             description "Show detailed output";
           }
           enum "terse" {
             description "Show terse output";
           }
         }
       }
     }
     output {
       container ddos-protocols-information {
         container detail {
           leaf total-packet-types {
             type int32;
             description "Total number of packet types";
           }
           leaf mod-packet-types {
             type int32;
             description "Number of packet types modified through user configuration";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container parameters {
           leaf total-packet-types {
             type int32;
             description "Total number of packet types";
           }
           leaf mod-packet-types {
             type int32;
             description "Number of packet types modified through user configuration";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container statistics {
           leaf total-packet-types {
             type int32;
             description "Total number of packet types";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container culprit-flows {
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container violations {
           leaf total-packet-types {
             type int32;
             description "Total number of packet types";
           }
           leaf packet-types-in-violation {
             type int32;
             description "Number of packet types receiving excess traffic";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
       }
     }
   }
   rpc get-ddos-ptpv6-flows {
     description "Show PTPV6 culprit flows";
     input {
       leaf fpc-slot {
         description "FPC slot number";
         type uint32 {
           range "0 .. 63";
         }
       }
       leaf level {
         type enumeration {
           enum "brief" {
             description "Show brief output";
           }
           enum "detail" {
             description "Show detailed output";
           }
           enum "summary" {
             description "Show flow information summary";
           }
         }
       }
     }
     output {
       container ddos-protocols-information {
         container detail {
           leaf total-packet-types {
             type int32;
             description "Total number of packet types";
           }
           leaf mod-packet-types {
             type int32;
             description "Number of packet types modified through user configuration";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container parameters {
           leaf total-packet-types {
             type int32;
             description "Total number of packet types";
           }
           leaf mod-packet-types {
             type int32;
             description "Number of packet types modified through user configuration";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container statistics {
           leaf total-packet-types {
             type int32;
             description "Total number of packet types";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container culprit-flows {
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container violations {
           leaf total-packet-types {
             type int32;
             description "Total number of packet types";
           }
           leaf packet-types-in-violation {
             type int32;
             description "Number of packet types receiving excess traffic";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
       }
     }
   }
   rpc get-ddos-ptpv6-aggregate {
     description "Show aggregate for all PTPv6 traffic information";
     output {
       container ddos-protocols-information {
         container detail {
           leaf total-packet-types {
             type int32;
             description "Total number of packet types";
           }
           leaf mod-packet-types {
             type int32;
             description "Number of packet types modified through user configuration";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container parameters {
           leaf total-packet-types {
             type int32;
             description "Total number of packet types";
           }
           leaf mod-packet-types {
             type int32;
             description "Number of packet types modified through user configuration";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container statistics {
           leaf total-packet-types {
             type int32;
             description "Total number of packet types";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container culprit-flows {
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container violations {
           leaf total-packet-types {
             type int32;
             description "Total number of packet types";
           }
           leaf packet-types-in-violation {
             type int32;
             description "Number of packet types receiving excess traffic";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
       }
     }
   }
   rpc get-ddos-ptpv6-aggregate-flows {
     description "Show aggregate culprit flows";
     input {
       leaf fpc-slot {
         description "FPC slot number";
         type uint32 {
           range "0 .. 63";
         }
       }
       leaf level {
         type enumeration {
           enum "brief" {
             description "Show brief output";
           }
           enum "detail" {
             description "Show detailed output";
           }
           enum "summary" {
             description "Show flow information summary";
           }
         }
       }
     }
     output {
       container ddos-protocols-information {
         container detail {
           leaf total-packet-types {
             type int32;
             description "Total number of packet types";
           }
           leaf mod-packet-types {
             type int32;
             description "Number of packet types modified through user configuration";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container parameters {
           leaf total-packet-types {
             type int32;
             description "Total number of packet types";
           }
           leaf mod-packet-types {
             type int32;
             description "Number of packet types modified through user configuration";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container statistics {
           leaf total-packet-types {
             type int32;
             description "Total number of packet types";
           }
           leaf packet-types-rcvd-packets {
             type int32;
             description "Number of packet types that have received packets";
           }
           leaf packet-types-in-violation {
             type int32;
             description "Number of packet types receiving excess traffic";
           }
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container culprit-flows {
           leaf flows-current {
             type int32;
             description "Number of flows that are currently being tracked";
           }
           leaf flows-cumulative {
             type int32;
             description "Number of flows that the system has seen";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
         container violations {
           leaf total-packet-types {
             type int32;
             description "Total number of packet types";
           }
           leaf packet-types-in-violation {
             type int32;
             description "Number of packet types receiving excess traffic";
           }
           container ddos-protocol-group {
             leaf group-name {
               type string;
               description "Protocol group name";
             }
             container ddos-protocol {
               leaf packet-type {
                 type string;
                 description "Protocol packet type name";
               }
               leaf packet-type-description {
                 type string;
                 description "Protocol packet type description";
               }
               container ddos-basic-parameters {
                 container aggr {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                 }
                 container proto {
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                 }
                 container brief {
                   leaf group-name {
                     type string;
                     description "Protocol group name";
                   }
                   leaf packet-type {
                     type string;
                     description "Protocol packet type name";
                   }
                   leaf policer-bandwidth {
                     type int32;
                     description "Policer bandwidth";
                   }
                   leaf policer-bandwidth-user {
                     type string;
                     description "User has configured the policer bandwidth";
                   }
                   leaf policer-burst {
                     type int32;
                     description "Policer burst";
                   }
                   leaf policer-burst-user {
                     type int32;
                     description "User has configured the policer burst";
                   }
                   leaf policer-priority {
                     type int32;
                     description "Policer priority";
                   }
                   leaf policer-priority-user {
                     type int32;
                     description "User has configured the policer priority";
                   }
                   leaf policer-time-recover {
                     type int32;
                     description "Time to return to normal state";
                   }
                   leaf policer-time-recover-user {
                     type int32;
                     description "User has configured the time to return to normal state";
                   }
                   leaf policer-enable {
                     type string;
                     description "Policer enable";
                   }
                   leaf policer-enable-user {
                     type string;
                     description "User has configured the policer enable option";
                   }
                   leaf policer-bypass-aggregate {
                     type string;
                     description "Bypass aggregate policer";
                   }
                   leaf policer-bypass-aggregate-user {
                     type string;
                     description "User has configured the bypass aggregate policer option";
                   }
                   leaf policer-fpc-scaled {
                     type string;
                     description "Parameter scaling is configured for this FPC slot";
                   }
                 }
               }
               container ddos-flow-detection {
                 container detail {
                   leaf detection-mode {
                     type string;
                     description "Flow detection mode";
                   }
                   leaf detection-mode-user {
                     type string;
                     description "User has configured the flow detection mode";
                   }
                   leaf detect-time {
                     type int32;
                     description "The time to determine a flow is culprit";
                   }
                   leaf detect-time-user {
                     type int32;
                     description "User has configured the time to determine a flow is culprit";
                   }
                   leaf log-flows {
                     type string;
                     description "Log flow and other messages";
                   }
                   leaf log-flows-user {
                     type string;
                     description "User has configured the log flow and other messages option";
                   }
                   leaf recover-time {
                     type int32;
                     description "The time to remove a flow after its traffic is below max rate";
                   }
                   leaf recover-time-user {
                     type int32;
                     description "User has configured the time to remove a flow after its traffic is below max rate";
                   }
                   leaf timeout-active-flows {
                     type string;
                     description "Time out active flows";
                   }
                   leaf timeout-active-flows-user {
                     type string;
                     description "User has configured the time out active flows option";
                   }
                   leaf timeout-time {
                     type int32;
                     description "The time to remove a flow after it is discovered";
                   }
                   leaf timeout-time-user {
                     type int32;
                     description "User has configured the time to remove a flow after it is discovered";
                   }
                   container flow-aggregation-level-states {
                     leaf sub-detection-mode {
                       type string;
                       description "Detection mode at subscriber level";
                     }
                     leaf sub-detection-mode-user {
                       type string;
                       description "User has configured the detection mode at subscriber level";
                     }
                     leaf sub-control-mode {
                       type string;
                       description "Flow control mode at subscriber level";
                     }
                     leaf sub-control-mode-user {
                       type string;
                       description "User has configured the flow control mode at subscriber level";
                     }
                     leaf sub-bandwidth {
                       type int32;
                       description "The maximum flow rate at subscriber level";
                     }
                     leaf sub-bandwidth-user {
                       type int32;
                       description "User has configured the maximum flow rate at subscriber level";
                     }
                     leaf ifl-detection-mode {
                       type string;
                       description "Detection mode at logical interface level";
                     }
                     leaf ifl-detection-mode-user {
                       type string;
                       description "User has configured the detection mode at logical interface level";
                     }
                     leaf ifl-control-mode {
                       type string;
                       description "Flow control mode at logical interface level";
                     }
                     leaf ifl-control-mode-user {
                       type string;
                       description "User has configured the flow control mode at logical interface level";
                     }
                     leaf ifl-bandwidth {
                       type int32;
                       description "The maximum flow rate at logical interface level";
                     }
                     leaf ifl-bandwidth-user {
                       type int32;
                       description "User has configured the maximum flow rate at logical interface level";
                     }
                     leaf ifd-detection-mode {
                       type string;
                       description "Detection mode at physical interface level";
                     }
                     leaf ifd-detection-mode-user {
                       type string;
                       description "User has configured the detection mode at physical interface level";
                     }
                     leaf ifd-control-mode {
                       type string;
                       description "Flow control mode at physical interface level";
                     }
                     leaf ifd-control-mode-user {
                       type string;
                       description "User has configured the flow control mode at physical interface level";
                     }
                     leaf ifd-bandwidth {
                       type int32;
                       description "The maximum flow rate at physical interface level";
                     }
                     leaf ifd-bandwidth-user {
                       type int32;
                       description "User has configured the maximum flow rate at physical interface level";
                     }
                   }
                 }
                 container brief {
                   leaf group-name {
                     type string;
                     description "Protocol group name";
                   }
                   leaf packet-type {
                     type string;
                     description "Protocol packet type name";
                   }
                   leaf detection-mode {
                     type string;
                     description "Flow detection mode";
                   }
                   leaf detection-mode-user {
                     type string;
                     description "User has configured the flow detection mode";
                   }
                   leaf policer-bandwidth {
                     type int32;
                     description "Policer bandwidth";
                   }
                   leaf policer-bandwidth-user {
                     type string;
                     description "User has configured the policer bandwidth";
                   }
                   leaf sub-detection-mode {
                     type string;
                     description "Detection mode at subscriber level";
                   }
                   leaf sub-control-mode {
                     type string;
                     description "Flow control mode at subscriber level";
                   }
                   leaf sub-bandwidth {
                     type int32;
                     description "The maximum flow rate at subscriber level";
                   }
                   leaf sub-level-user {
                     type string;
                     description "User has configured subscriber level parameters";
                   }
                   leaf ifl-detection-mode {
                     type string;
                     description "Detection mode at logical interface level";
                   }
                   leaf ifl-control-mode {
                     type string;
                     description "Flow control mode at logical interface level";
                   }
                   leaf ifl-bandwidth {
                     type int32;
                     description "The maximum flow rate at logical interface level";
                   }
                   leaf ifl-level-user {
                     type string;
                     description "User has configured logical interface level parameters";
                   }
                   leaf ifd-detection-mode {
                     type string;
                     description "Detection mode at physical interface level";
                   }
                   leaf ifd-control-mode {
                     type string;
                     description "Flow control mode at physical interface level";
                   }
                   leaf ifd-bandwidth {
                     type int32;
                     description "The maximum flow rate at physical interface level";
                   }
                   leaf ifd-level-user {
                     type string;
                     description "User has configured physical interface level parameters";
                   }
                   leaf log-flows {
                     type string;
                     description "Log flow and other messages";
                   }
                   leaf log-flows-user {
                     type string;
                     description "User has configured the log flow and other messages option";
                   }
                   leaf timeout-active-flows {
                     type string;
                     description "Time out active flows";
                   }
                   leaf timeout-active-flows-user {
                     type string;
                     description "User has configured the time out active flows option";
                   }
                   container flow-aggregation-level-states {
                     leaf sub-detection-mode-user {
                       type string;
                       description "User has configured the detection mode at subscriber level";
                     }
                     leaf sub-control-mode-user {
                       type string;
                       description "User has configured the flow control mode at subscriber level";
                     }
                     leaf sub-bandwidth-user {
                       type int32;
                       description "User has configured the maximum flow rate at subscriber level";
                     }
                     leaf ifl-detection-mode-user {
                       type string;
                       description "User has configured the detection mode at logical interface level";
                     }
                     leaf ifl-control-mode-user {
                       type string;
                       description "User has configured the flow control mode at logical interface level";
                     }
                     leaf ifl-bandwidth-user {
                       type int32;
                       description "User has configured the maximum flow rate at logical interface level";
                     }
                     leaf ifd-detection-mode-user {
                       type string;
                       description "User has configured the detection mode at physical interface level";
                     }
                     leaf ifd-control-mode-user {
                       type string;
                       description "User has configured the flow control mode at physical interface level";
                     }
                     leaf ifd-bandwidth-user {
                       type int32;
                       description "User has configured the maximum flow rate at physical interface level";
                     }
                   }
                 }
               }
               container ddos-system-statistics {
                 container violated-aggr {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-aggr {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-aggr {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container violated-proto {
                   leaf fpc-violation-count-current {
                     type int32;
                     description "Number of FPCs receiving excess traffic";
                   }
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container normal-proto {
                   leaf fpc-violation-count {
                     type int32;
                     description "Number of FPCs received excess traffic";
                   }
                   leaf policer-violation-start-time {
                     type string;
                     description "Time the policer violation was first observed";
                   }
                   leaf policer-violation-last-time {
                     type string;
                     description "Time the policer violation was last observed";
                   }
                   leaf policer-violation-duration {
                     type string;
                     description "Duration of the policer violation";
                   }
                   leaf policer-violation-count {
                     type int32;
                     description "Number of times the policer has been violated";
                   }
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container clean-proto {
                   leaf packet-received {
                     type int32;
                     description "Number of packets received";
                   }
                   leaf packet-arrival-rate {
                     type int32;
                     description "Current packet arrival rate";
                   }
                   leaf packet-dropped {
                     type int32;
                     description "Number of packets dropped";
                   }
                   leaf packet-arrival-rate-max {
                     type int32;
                     description "Maximum packet arrival rate";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
                 container brief {
                   leaf group-name {
                     type string;
                     description "Protocol group name";
                   }
                   leaf packet-type {
                     type string;
                     description "Protocol packet type name";
                   }
                   leaf packet-received {
                     type int32;
                     description "Number of packets received";
                   }
                   leaf packet-dropped {
                     type int32;
                     description "Number of packets dropped";
                   }
                   leaf packet-arrival-rate {
                     type int32;
                     description "Current packet arrival rate";
                   }
                   leaf policer-violation-count {
                     type int32;
                     description "Number of times the policer has been violated";
                   }
                   leaf protocol-states {
                     type string;
                     description "Current protocol states";
                   }
                   container ddos-flow-level-statistics {
                     container system {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                     }
                     container fpc {
                       leaf flow-aggregation-level {
                         type string;
                         description "Aggregation level of the flow";
                       }
                       leaf flows-current {
                         type int32;
                         description "Number of flows that are currently being tracked";
                       }
                       leaf flows-cumulative {
                         type int32;
                         description "Number of flows that the system has seen";
                       }
                       leaf aggr-level-state {
                         type string;
                         description "The detection state of the aggregation level";
                       }
                     }
                   }
                 }
               }
               container ddos-instance {
                 container detail {
                   leaf protocol-states-locale {
                     type string;
                     description "Location of the reported protocol states";
                   }
                   container ddos-instance-parameters {
                     container re {
                       leaf policer-bandwidth {
                         type int32;
                         description "Policer bandwidth";
                       }
                       leaf policer-burst {
                         type int32;
                         description "Policer burst";
                       }
                       leaf policer-enable {
                         type string;
                         description "Policer enable";
                       }
                       leaf policer-enable-user {
                         type string;
                         description "User has configured the policer enable option";
                       }
                       leaf policer-bypass-aggregate {
                         type string;
                         description "Bypass aggregate policer";
                       }
                     }
                     container fpc {
                       leaf policer-bandwidth-scale {
                         type int32;
                         description "Policer bandwidth scale in percent";
                       }
                       leaf policer-bandwidth-scale-user {
                         type string;
                         description "User has configured the policer bandwidth scale";
                       }
                       leaf policer-bandwidth {
                         type int32;
                         description "Policer bandwidth";
                       }
                       leaf policer-burst-scale {
                         type int32;
                         description "Policer burst scale in percent";
                       }
                       leaf policer-burst-scale-user {
                         type string;
                         description "User has configured the policer burst scale";
                       }
                       leaf policer-burst {
                         type int32;
                         description "Policer burst";
                       }
                       leaf policer-enable {
                         type string;
                         description "Policer enable";
                       }
                       leaf policer-enable-user {
                         type string;
                         description "User has configured the policer enable option";
                       }
                       leaf hostbound-queue {
                         type int32;
                         description "Hostbound queue for exception packets";
                       }
                       leaf hostbound-queue-user {
                         type string;
                         description "User has configured the hostbound queue";
                       }
                       leaf policer-bypass-aggregate {
                         type string;
                         description "Bypass aggregate policer";
                       }
                     }
                   }
                   container ddos-instance-statistics {
                     container violated-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-aggr {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-aggr {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container violated-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container normal-proto {
                       leaf policer-violation-start-time {
                         type string;
                         description "Time the policer violation was first observed";
                       }
                       leaf policer-violation-last-time {
                         type string;
                         description "Time the policer violation was last observed";
                       }
                       leaf policer-violation-duration {
                         type string;
                         description "Duration of the policer violation";
                       }
                       leaf policer-violation-count {
                         type int32;
                         description "Number of times the policer has been violated";
                       }
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-protocol {
                         type int32;
                         description "Number of packets dropped by individual policer(s)";
                       }
                       leaf packet-dropped-aggr {
                         type int32;
                         description "Number of packets dropped by aggregate policer";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                     container clean-proto {
                       leaf packet-received {
                         type int32;
                         description "Number of packets received";
                       }
                       leaf packet-arrival-rate {
                         type int32;
                         description "Current packet arrival rate";
                       }
                       leaf packet-dropped {
                         type int32;
                         description "Number of packets dropped";
                       }
                       leaf packet-arrival-rate-max {
                         type int32;
                         description "Maximum packet arrival rate";
                       }
                       leaf packet-dropped-others {
                         type int32;
                         description "Number of packets dropped by other policer(s)";
                       }
                       leaf packet-dropped-flows {
                         type int32;
                         description "Number of packets dropped by flow suppression";
                       }
                       container ddos-flow-level-statistics {
                         container system {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                         }
                         container fpc {
                           leaf flow-aggregation-level {
                             type string;
                             description "Aggregation level of the flow";
                           }
                           leaf flows-current {
                             type int32;
                             description "Number of flows that are currently being tracked";
                           }
                           leaf flows-cumulative {
                             type int32;
                             description "Number of flows that the system has seen";
                           }
                           leaf aggr-level-state {
                             type string;
                             description "The detection state of the aggregation level";
                           }
                         }
                       }
                     }
                   }
                 }
               }
               container ddos-culprit-flow {
                 container brief {
                   leaf group-name {
                     type string;
                     description "Protocol group name";
                   }
                   leaf packet-type {
                     type string;
                     description "Protocol packet type name";
                   }
                   leaf flow-interface {
                     type string;
                     description "Arriving interface of the flow";
                   }
                   leaf flow-source-addr {
                     type string;
                     description "Source address of flow";
                   }
                   leaf flow-aggregation-level {
                     type string;
                     description "Aggregation level of the flow";
                   }
                   leaf flow-id {
                     type int32;
                     description "Flow ID";
                   }
                   leaf flow-found-time {
                     type string;
                     description "The time the flow detect is detected";
                   }
                   leaf packet-arrival-rate {
                     type int32;
                     description "Current packet arrival rate";
                   }
                   leaf packet-received {
                     type int32;
                     description "Number of packets received";
                   }
                 }
                 container detail {
                   leaf group-name {
                     type string;
                     description "Protocol group name";
                   }
                   leaf packet-type {
                     type string;
                     description "Protocol packet type name";
                   }
                   leaf flow-interface {
                     type string;
                     description "Arriving interface of the flow";
                   }
                   leaf flow-aggregation-level {
                     type string;
                     description "Aggregation level of the flow";
                   }
                   leaf flow-id {
                     type int32;
                     description "Flow ID";
                   }
                   leaf flow-ethertype {
                     type string;
                     description "Ethertype of the flow";
                   }
                   leaf flow-outer-vlan {
                     type string;
                     description "Outer vlan-id of the flow";
                   }
                   leaf flow-inner-vlan {
                     type string;
                     description "Inner vlan-id of the flow";
                   }
                   leaf flow-source-addr {
                     type string;
                     description "Source address of flow";
                   }
                   leaf flow-destination-addr {
                     type string;
                     description "Destination address of flow";
                   }
                   leaf flow-source-port {
                     type string;
                     description "Source port of flow";
                   }
                   leaf flow-destination-port {
                     type string;
                     description "Destination port of flow";
                   }
                   leaf flow-icmp-type {
                     type string;
                     description "Icmp or Igmp type of flow";
                   }
                   leaf flow-icmp-code {
                     type string;
                     description "Icmp or Igmp code of flow";
                   }
                   leaf flow-found-time {
                     type string;
                     description "The time the flow detect is detected";
                   }
                   leaf flow-last-violation {
                     type string;
                     description "The time the flow last violated its bandwidth";
                   }
                   leaf packet-arrival-rate {
                     type int32;
                     description "Current packet arrival rate";
                   }
                   leaf packet-received {
                     type int32;
                     description "Number of packets received";
                   }
                 }
               }
               container ddos-violation-statistics {
                 container brief {
                   leaf group-name {
                     type string;
                     description "Protocol group name";
                   }
                   leaf packet-type {
                     type string;
                     description "Protocol packet type name";
                   }
                   leaf policer-bandwidth {
                     type int32;
                     description "Policer bandwidth";
                   }
                   leaf packet-arrival-rate {
                     type int32;
                     description "Current packet arrival rate";
                   }
                   leaf packet-arrival-rate-max {
                     type int32;
                     description "Maximum packet arrival rate";
                   }
                   leaf policer-violation-start-time {
                     type string;
                     description "Time the policer violation was first observed";
                   }
                   leaf protocol-states-locale {
                     type string;
                     description "Location of the reported protocol states";
                   }
                 }
               }
             }
           }
         }
       }
     }
   }
   rpc get-ddos-statistics-information {
     description "Show overall statistics";
     output {
       container ddos-statistics-information {
         leaf ddos-policing-re-enabled {
           type string;
           description "Routing engine policing enable";
         }
         leaf ddos-policing-fpc-enabled {
           type string;
           description "FPC policing enable";
         }
         leaf ddos-flow-detection-enabled {
           type string;
           description "Flow detection enable";
         }
         leaf ddos-logging-enabled {
           type string;
           description "Logging enable";
         }
         leaf violation-report-rate {
           type int32;
           description "Policer violation status change report rate";
         }
         leaf flow-report-rate {
           type int32;
           description "Flow status change report rate";
         }
         leaf detection-mode {
           type string;
           description "Flow detection mode";
         }
         leaf aggr-level-detection-mode {
           type string;
           description "Aggregate level flow detection mode";
         }
         leaf aggr-level-control-mode {
           type string;
           description "Aggregate level flow control mode";
         }
         leaf packet-types-in-violation {
           type int32;
           description "Number of packet types receiving excess traffic";
         }
         leaf packet-types-seen-violation {
           type int32;
           description "Number of packet types received excess traffic";
         }
         leaf total-violations {
           type int32;
           description "Total number of policer violations";
         }
         leaf flows-current {
           type int32;
           description "Number of flows that are currently being tracked";
         }
         leaf flows-cumulative {
           type int32;
           description "Number of flows that the system has seen";
         }
       }
     }
   }
   rpc get-ddos-version {
     description "Show version";
     output {
       container ddos-version {
         leaf total-groups {
           type string;
           description "Total number of protocol groups";
         }
         leaf total-packet-types {
           type int32;
           description "Total number of packet types";
         }
       }
     }
   }
 }
