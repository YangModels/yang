/*
 * Copyright (c) 2017 Juniper Networks, Inc.
 * All rights reserved.
 */

 module show-esis {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-esis-adjacency-information {
     description "Show ES-IS adjacency database";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of ES-IS instance";
         type string;
       }
       leaf esis-neighbor-id {
         description "NSAP/NET of end system";
         type string;
       }
     }
     output {
       container esis-adjacency-information {
         container brief {
           container esis-adjacency {
             leaf esis-neighbor-type {
               type string;
             }
             leaf esis-neighbor-id {
               type string;
             }
             leaf holdtime {
               type int32;
               description "Delay before timing out the adjacency (default is 180 seconds)";
             }
             leaf interface-name {
               type string;
               description "Name of interface";
             }
             container snpa {
               container pfe-port-snpa {
                 description "PFE Port SNPA";
                 leaf pfe-id {
                   type int32;
                 }
                 leaf port-id {
                   type int32;
                 }
               }
               container network-element-port-snpa {
                 description "Network Element Port SNPA";
                 leaf port-id {
                   type int32;
                 }
               }
               container mstp-root-snpa {
                 description "Multiple Spanning Tree Protocol Root SNPA";
                 leaf mstp-root-id {
                   type int32;
                 }
               }
               container gateway-snpa {
                 description "Gateway SNPA";
                 leaf gateway-addr {
                   type ipaddr;
                 }
               }
               container layer2-domain-port-snpa {
                 description "Layer-2 Domain Port SNPA";
                 leaf port-id {
                   type int32;
                 }
               }
               container replication-block-snpa {
                 description "Replication Block SNPA";
                 leaf replication-block-id {
                   type int32;
                 }
               }
               container replication-route-snpa {
                 description "Replication Route SNPA";
                 leaf network-element-id {
                   type ipaddr;
                 }
               }
               container layer2-multicast-port-snpa {
                 description "Layer-2 Multicast Port SNPA";
                 leaf layer2-multicast-port-id {
                   type int32;
                 }
               }
               container inh-snpa {
                 description "Indirection SNPA";
                 leaf inh-id {
                   type int32;
                 }
               }
             }
           }
         }
         container detail {
           container esis-adjacency {
             leaf esis-neighbor-id {
               type string;
             }
             leaf esis-neighbor-type {
               type string;
             }
             leaf interface-name {
               type string;
               description "Name of interface";
             }
             leaf esis-adjacency-advertised-holdtime {
               type string;
               description "Hold time advertised by the adjacency";
             }
             leaf holdtime {
               type int32;
               description "Delay before timing out the adjacency (default is 180 seconds)";
             }
             leaf snpa {
               type string;
             }
           }
         }
         container extensive {
           container esis-adjacency {
             leaf esis-neighbor-id {
               type string;
             }
             leaf esis-neighbor-type {
               type string;
             }
             leaf interface-name {
               type string;
               description "Name of interface";
             }
             leaf esis-adjacency-advertised-holdtime {
               type string;
               description "Hold time advertised by the adjacency";
             }
             leaf holdtime {
               type int32;
               description "Delay before timing out the adjacency (default is 180 seconds)";
             }
             leaf snpa {
               type string;
             }
             container esis-adjacency-log {
               description "Entry describing ES-IS adjacency transition";
               leaf esis-adjacency-when {
                 type string;
                 description "Time at which the transition occurred";
               }
               leaf esis-adjacency-state {
                 type string;
                 description "State of the adjacency";
               }
               leaf esis-adjacency-event {
                 type string;
                 description "Event that triggered the transition";
               }
               leaf esis-adjacency-down-reason {
                 type string;
                 description "Reason for the down transition event";
               }
             }
           }
         }
       }
     }
   }
   rpc get-esis-interface-information {
     description "Show ES-IS interface information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of ES-IS instance";
         type string;
       }
       leaf interface-name {
         description "Name of interface";
         type string;
       }
     }
     output {
       container esis-interface-information {
         container brief {
           container esis-interface {
             leaf interface-name {
               type string;
               description "Name of interface";
             }
             leaf esis-interface-receives {
               type string;
               description "Types of hellos received on this interface - ESH and/or ISH";
             }
             leaf esis-interface-sends {
               type string;
               description "Type of hello message sent out on this interface - ESH or ISH";
             }
             leaf esis-hello-interval {
               type string;
               description "Interval between subsequent hellos (one-third of the hold time)";
             }
             leaf esis-adjacency-count {
               type int32;
               description "Number of adjacencies";
             }
           }
         }
         container detail {
           container esis-interface {
             leaf interface-name {
               type string;
               description "Name of interface";
             }
             leaf esis-interface-receives {
               type string;
               description "Types of hellos received on this interface - ESH and/or ISH";
             }
             leaf esis-interface-sends {
               type string;
               description "Type of hello message sent out on this interface - ESH or ISH";
             }
             leaf esis-hello-interval {
               type string;
               description "Interval between subsequent hellos (one-third of the hold time)";
             }
             leaf esis-adjacency-count {
               type int32;
               description "Number of adjacencies";
             }
             leaf holdtime {
               type int32;
               description "Delay before timing out the adjacency (default is 180 seconds)";
             }
             leaf esis-esct {
               type string;
               description "Suggested hold time for end systems (default is 180 seconds)";
             }
             leaf interface-index {
               type int32;
             }
             leaf esis-interface-state-value {
               type int32;
               description "State of ES-IS interface";
             }
             leaf esis-interface-net {
               type string;
             }
           }
         }
       }
     }
   }
   rpc get-esis-statistics-information {
     description "Show ES-IS performance statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of ES-IS instance";
         type string;
       }
     }
     output {
       container esis-statistics-information {
         container esis-pdu-statistics {
           leaf esis-pdu-type {
             type string;
             description "Type of ES-IS Protocol Data Unit";
           }
           leaf packets-received {
             type uint64;
           }
           leaf packets-processed {
             type uint64;
           }
           leaf packets-dropped {
             type uint64;
           }
           leaf packets-sent {
             type uint64;
           }
           leaf packets-retransmitted {
             type uint64;
           }
         }
         container esis-totals-information {
           leaf packets-received {
             type uint64;
           }
           leaf packets-sent {
             type uint64;
           }
         }
       }
     }
   }
 }
