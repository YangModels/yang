/*
 * Copyright (c) 2017 Juniper Networks, Inc.
 * All rights reserved.
 */

 module show-link-management {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-lm-information {
     description "Show link management information";
     output {
       container lm-information {
         container lm-peer-root-information {
           container lm-peer-information {
             leaf lm-peer-name {
               type string;
               description "Name of object";
             }
             leaf lm-sys-id {
               type int32;
               description "System identifier of object";
             }
             leaf lm-state {
               type string;
               description "State of object";
             }
             leaf lm-peer-control-address {
               type ipaddr;
               description "Peer control address";
             }
             leaf lm-peer-hello-interval {
               type int32;
               description "LMP hello interval";
             }
             leaf lm-peer-hello-dead-interval {
               type int32;
               description "LMP hello dead-interval";
             }
             leaf lm-source {
               type string;
               description "Source of information";
             }
             leaf lm-peer-received-message-id {
               type int32;
               description "LMP last per-peer received message ID";
             }
             leaf lm-peer-sent-message-id {
               type int32;
               description "LMP last per-peer sent message ID";
             }
             container lm-peer-control-channels {
               description "Link management control channels";
               container lm-control-channel-info {
                 description "Link management control channel information";
                 leaf lm-control-channel {
                   type string;
                   description "Peer control channel name";
                 }
                 leaf lm-control-channel-state {
                   type string;
                   description "Peer control channel state";
                 }
               }
             }
             container lm-peer-lmp-control-channels {
               description "Link management control channels";
               container lm-peer-lmp-control-channel-information {
                 description "Link management control channel information";
                 leaf lm-lmp-control-channel-local-id {
                   type int32;
                   description "Peer control channel local ID";
                 }
                 leaf lm-lmp-control-channel-remote-id {
                   type int32;
                   description "Peer control channel remote ID";
                 }
                 leaf lm-lmp-control-channel-state {
                   type string;
                   description "Peer control channel state";
                 }
                 leaf lm-lmp-control-channel-tx-seq-num {
                   type int32;
                   description "LMP transmit sequence number";
                 }
                 leaf lm-lmp-control-channel-rcv-seq-num {
                   type int32;
                   description "LMP receive sequence number";
                 }
                 leaf lm-lmp-control-channel-received-message-id {
                   type int32;
                   description "LMP last per-control-channel received message ID";
                 }
                 leaf lm-lmp-control-channel-sent-message-id {
                   type int32;
                   description "LMP last per-control-channel sent message ID";
                 }
                 container lm-lmp-control-channel-flags {
                   description "Peer control channel flags";
                   leaf cc-restarting {
                     type empty;
                   }
                 }
               }
             }
             container lm-peer-te-links {
               description "Link management peer TE links";
               container lm-peer-te-link-information {
                 description "Link management peer TE link information";
                 leaf lm-peer-te-link {
                   type string;
                   description "TE link name contained in peer";
                 }
               }
             }
           }
         }
         container lm-te-link-root-information {
           container lm-te-link-information {
             leaf lm-te-link-name {
               type string;
               description "Name of object";
             }
             leaf lm-state {
               type string;
               description "State of object";
             }
             leaf lm-te-link-flags {
               type string;
               description "Flags for object";
             }
             leaf lm-local-id {
               type int32;
               description "Local identifier of object";
             }
             leaf lm-remote-id {
               type int32;
               description "Remote identifier of object";
             }
             leaf lm-local-address {
               type string;
               description "Local address of object";
             }
             leaf lm-remote-address {
               type string;
               description "Remote address of object";
             }
             leaf lm-encoding {
               type string;
               description "TE-Link encoding type";
             }
             leaf lm-switching {
               type string;
               description "TE-Link switching capability";
             }
             leaf lm-min-bandwidth {
               type string;
               description "Minimum reservable bandwidth per allocation";
             }
             leaf lm-max-bandwidth {
               type string;
               description "Maximum reservable bandwidth per allocation";
             }
             leaf lm-total-bandwidth {
               type string;
               description "Total bandwidth available on this TE link";
             }
             leaf lm-avail-bandwidth {
               type string;
               description "Unallocated bandwidth on this TE link";
             }
             container lm-te-link-local-flags {
               leaf lm-te-link-nack-sent-flag {
                 type empty;
               }
             }
             container lm-te-link-resources {
               container lm-te-link-resource {
                 container brief {
                   leaf lm-resource-name {
                     type string;
                     description "Resource name";
                   }
                   leaf lm-resource-state {
                     type string;
                   }
                   leaf lm-resource-local-id {
                     type int32;
                     description "Resource local identifier";
                   }
                   leaf lm-resource-remote-id {
                     type int32;
                     description "Resource remote identifier";
                   }
                   leaf lm-resource-bandwidth {
                     type string;
                     description "Total bandwidth of resource";
                   }
                   leaf lm-resource-in-use {
                     type string;
                     description "Resource allocation status";
                   }
                   leaf lm-resource-lsp-name {
                     type string;
                     description "Name of LSP using resource";
                   }
                   leaf lm-resource-local-addr {
                     type ipaddr;
                     description "Resource local address";
                   }
                   leaf lm-resource-remote-addr {
                     type ipaddr;
                     description "Resource remote address";
                   }
                 }
                 container detail {
                   leaf lm-resource-name {
                     type string;
                     description "Resource name";
                   }
                   leaf lm-resource-type {
                     type string;
                     description "Resource type";
                   }
                   leaf lm-sys-id {
                     type int32;
                     description "System identifier of object";
                   }
                   leaf lm-resource-state {
                     type string;
                   }
                   leaf lm-resource-flags {
                     type string;
                     description "Resource flags";
                   }
                   leaf lm-resource-local-id {
                     type int32;
                     description "Resource local identifier";
                   }
                   leaf lm-resource-remote-id {
                     type int32;
                     description "Resource remote identifier";
                   }
                   leaf lm-resource-bandwidth {
                     type string;
                     description "Total bandwidth of resource";
                   }
                   leaf lm-resource-avail-bandwidth {
                     type string;
                     description "Unallocated bandwidth on resource";
                   }
                   leaf lm-resource-traffic-params {
                     type string;
                     description "Traffic parameters of resource";
                   }
                   leaf lm-resource-max-allocations {
                     type int32;
                     description "Maximum number of allocations";
                   }
                   leaf lm-resource-num-allocations {
                     type int32;
                     description "Current number of allocations";
                   }
                   leaf lm-resource-unique-allocations {
                     type int32;
                     description "Current number of unique allocations";
                   }
                   leaf lm-resource-in-use {
                     type string;
                     description "Resource allocation status";
                   }
                   leaf lm-resource-local-addr {
                     type ipaddr;
                     description "Resource local address";
                   }
                   leaf lm-resource-remote-addr {
                     type ipaddr;
                     description "Resource remote address";
                   }
                   container lm-resource-allocation-context {
                     leaf lm-allocated-lsp-name {
                       type string;
                     }
                     leaf lm-local-label {
                       type int32;
                     }
                     leaf lm-remote-label {
                       type int32;
                     }
                     leaf lm-allocated-bandwidth {
                       type string;
                     }
                     leaf lm-bandwidth-shared {
                       type int32;
                     }
                     leaf lm-label-shared {
                       type empty;
                     }
                   }
                 }
               }
             }
           }
         }
         container lm-resource-root-information {
           leaf lm-source {
             type string;
             description "Source of information";
           }
           container lm-resource {
             leaf lm-resource-name {
               type string;
               description "Resource name";
             }
             leaf lm-resource-type {
               type string;
               description "Resource type";
             }
             leaf lm-resource-state {
               type string;
             }
             leaf lm-sys-id {
               type int32;
               description "System identifier of object";
             }
             leaf lm-resource-max-allocations {
               type int32;
               description "Maximum number of allocations";
             }
             leaf lm-resource-bandwidth {
               type string;
               description "Total bandwidth of resource";
             }
             leaf lm-resource-traffic-params {
               type string;
               description "Traffic parameters of resource";
             }
           }
         }
       }
     }
   }
   rpc get-lm-peer-information {
     description "Show peer information";
     input {
       leaf peer-name {
         description "Name of peer";
         type string;
       }
     }
   }
   rpc get-lm-te-link-information {
     description "Show traffic engineering links information";
     input {
       leaf verbosity_level {
         default "brief";
         type enumeration {
           enum "brief" {
             description "Display brief output (default)";
           }
           enum "detail" {
             description "Display detailed output";
           }
         }
       }
       leaf link-name {
         description "Name of traffic engineering link";
         type string;
       }
     }
   }
   rpc get-lm-statistics-information {
     description "Show link management statistics";
     output {
       container lm-statistics-information {
         container lm-peer-statistics {
           leaf lm-peer-name {
             type string;
             description "Name of object";
           }
           container lm-input-statistics {
             description "Input statistics";
             leaf lm-small-packets {
               type int32;
               description "Number of packets too small to process";
             }
             leaf lm-bad-version {
               type int32;
               description "Number of packets with unsupported protocol version";
             }
             leaf lm-no-peer {
               type int32;
               description "Number of messages received for unknown peer";
             }
             leaf lm-wrong-state {
               type int32;
               description "Number of messages received for control channel in wrong state";
             }
             leaf lm-stale-ack {
               type int32;
               description "Number of acknowledgments received for unknown messages";
             }
             leaf lm-stale-nack {
               type int32;
               description "Number of negative acknowledgments received for unknown messages";
             }
             leaf lm-no-cc {
               type int32;
               description "Number of messages received for unknown control channel";
             }
             container lm-received-packets {
               description "Number of packets received";
               leaf lm-packet-type {
                 type string;
                 description "Type of packet";
               }
               leaf lm-packet-count {
                 type int32;
                 description "Number of packets";
               }
             }
             container lm-received-bad-packets {
               description "Number of bad packets received";
               leaf lm-packet-type {
                 type string;
                 description "Type of packet";
               }
               leaf lm-packet-count {
                 type int32;
                 description "Number of packets";
               }
             }
             container lm-received-misordered-packets {
               description "Number of out-of-order packets received";
               leaf lm-packet-type {
                 type string;
                 description "Type of packet";
               }
               leaf lm-packet-count {
                 type int32;
                 description "Number of packets";
               }
             }
           }
           container lm-output-statistics {
             description "Output statistics";
             container lm-sent-packets {
               description "Number of packets sent";
               leaf lm-packet-type {
                 type string;
                 description "Type of packet";
               }
               leaf lm-packet-count {
                 type int32;
                 description "Number of packets";
               }
             }
             container lm-retransmit-packets {
               description "Number of packets retransmitted";
               leaf lm-packet-type {
                 type string;
                 description "Type of packet";
               }
               leaf lm-packet-count {
                 type int32;
                 description "Number of packets";
               }
             }
             container lm-tossed-packets {
               description "Number of messages which failed retransmission";
               leaf lm-packet-type {
                 type string;
                 description "Type of packet";
               }
               leaf lm-packet-count {
                 type int32;
                 description "Number of packets";
               }
             }
           }
         }
       }
     }
   }
   rpc get-lm-peer-statistics {
     description "Show link management statistics for a peer";
     input {
       leaf peer-name {
         description "Name of peer";
         type string;
       }
     }
   }
   rpc get-lm-routing-information {
     description "Show link management information for routing";
     output {
       container lm-information {
         container lm-peer-root-information {
           container lm-peer-information {
             leaf lm-peer-name {
               type string;
               description "Name of object";
             }
             leaf lm-sys-id {
               type int32;
               description "System identifier of object";
             }
             leaf lm-state {
               type string;
               description "State of object";
             }
             leaf lm-peer-control-address {
               type ipaddr;
               description "Peer control address";
             }
             leaf lm-peer-hello-interval {
               type int32;
               description "LMP hello interval";
             }
             leaf lm-peer-hello-dead-interval {
               type int32;
               description "LMP hello dead-interval";
             }
             leaf lm-source {
               type string;
               description "Source of information";
             }
             leaf lm-peer-received-message-id {
               type int32;
               description "LMP last per-peer received message ID";
             }
             leaf lm-peer-sent-message-id {
               type int32;
               description "LMP last per-peer sent message ID";
             }
             container lm-peer-control-channels {
               description "Link management control channels";
               container lm-control-channel-info {
                 description "Link management control channel information";
                 leaf lm-control-channel {
                   type string;
                   description "Peer control channel name";
                 }
                 leaf lm-control-channel-state {
                   type string;
                   description "Peer control channel state";
                 }
               }
             }
             container lm-peer-lmp-control-channels {
               description "Link management control channels";
               container lm-peer-lmp-control-channel-information {
                 description "Link management control channel information";
                 leaf lm-lmp-control-channel-local-id {
                   type int32;
                   description "Peer control channel local ID";
                 }
                 leaf lm-lmp-control-channel-remote-id {
                   type int32;
                   description "Peer control channel remote ID";
                 }
                 leaf lm-lmp-control-channel-state {
                   type string;
                   description "Peer control channel state";
                 }
                 leaf lm-lmp-control-channel-tx-seq-num {
                   type int32;
                   description "LMP transmit sequence number";
                 }
                 leaf lm-lmp-control-channel-rcv-seq-num {
                   type int32;
                   description "LMP receive sequence number";
                 }
                 leaf lm-lmp-control-channel-received-message-id {
                   type int32;
                   description "LMP last per-control-channel received message ID";
                 }
                 leaf lm-lmp-control-channel-sent-message-id {
                   type int32;
                   description "LMP last per-control-channel sent message ID";
                 }
                 container lm-lmp-control-channel-flags {
                   description "Peer control channel flags";
                   leaf cc-restarting {
                     type empty;
                   }
                 }
               }
             }
             container lm-peer-te-links {
               description "Link management peer TE links";
               container lm-peer-te-link-information {
                 description "Link management peer TE link information";
                 leaf lm-peer-te-link {
                   type string;
                   description "TE link name contained in peer";
                 }
               }
             }
           }
         }
         container lm-te-link-root-information {
           container lm-te-link-information {
             leaf lm-te-link-name {
               type string;
               description "Name of object";
             }
             leaf lm-state {
               type string;
               description "State of object";
             }
             leaf lm-te-link-flags {
               type string;
               description "Flags for object";
             }
             leaf lm-local-id {
               type int32;
               description "Local identifier of object";
             }
             leaf lm-remote-id {
               type int32;
               description "Remote identifier of object";
             }
             leaf lm-local-address {
               type string;
               description "Local address of object";
             }
             leaf lm-remote-address {
               type string;
               description "Remote address of object";
             }
             leaf lm-encoding {
               type string;
               description "TE-Link encoding type";
             }
             leaf lm-switching {
               type string;
               description "TE-Link switching capability";
             }
             leaf lm-min-bandwidth {
               type string;
               description "Minimum reservable bandwidth per allocation";
             }
             leaf lm-max-bandwidth {
               type string;
               description "Maximum reservable bandwidth per allocation";
             }
             leaf lm-total-bandwidth {
               type string;
               description "Total bandwidth available on this TE link";
             }
             leaf lm-avail-bandwidth {
               type string;
               description "Unallocated bandwidth on this TE link";
             }
             container lm-te-link-local-flags {
               leaf lm-te-link-nack-sent-flag {
                 type empty;
               }
             }
             container lm-te-link-resources {
               container lm-te-link-resource {
                 container brief {
                   leaf lm-resource-name {
                     type string;
                     description "Resource name";
                   }
                   leaf lm-resource-state {
                     type string;
                   }
                   leaf lm-resource-local-id {
                     type int32;
                     description "Resource local identifier";
                   }
                   leaf lm-resource-remote-id {
                     type int32;
                     description "Resource remote identifier";
                   }
                   leaf lm-resource-bandwidth {
                     type string;
                     description "Total bandwidth of resource";
                   }
                   leaf lm-resource-in-use {
                     type string;
                     description "Resource allocation status";
                   }
                   leaf lm-resource-lsp-name {
                     type string;
                     description "Name of LSP using resource";
                   }
                   leaf lm-resource-local-addr {
                     type ipaddr;
                     description "Resource local address";
                   }
                   leaf lm-resource-remote-addr {
                     type ipaddr;
                     description "Resource remote address";
                   }
                 }
                 container detail {
                   leaf lm-resource-name {
                     type string;
                     description "Resource name";
                   }
                   leaf lm-resource-type {
                     type string;
                     description "Resource type";
                   }
                   leaf lm-sys-id {
                     type int32;
                     description "System identifier of object";
                   }
                   leaf lm-resource-state {
                     type string;
                   }
                   leaf lm-resource-flags {
                     type string;
                     description "Resource flags";
                   }
                   leaf lm-resource-local-id {
                     type int32;
                     description "Resource local identifier";
                   }
                   leaf lm-resource-remote-id {
                     type int32;
                     description "Resource remote identifier";
                   }
                   leaf lm-resource-bandwidth {
                     type string;
                     description "Total bandwidth of resource";
                   }
                   leaf lm-resource-avail-bandwidth {
                     type string;
                     description "Unallocated bandwidth on resource";
                   }
                   leaf lm-resource-traffic-params {
                     type string;
                     description "Traffic parameters of resource";
                   }
                   leaf lm-resource-max-allocations {
                     type int32;
                     description "Maximum number of allocations";
                   }
                   leaf lm-resource-num-allocations {
                     type int32;
                     description "Current number of allocations";
                   }
                   leaf lm-resource-unique-allocations {
                     type int32;
                     description "Current number of unique allocations";
                   }
                   leaf lm-resource-in-use {
                     type string;
                     description "Resource allocation status";
                   }
                   leaf lm-resource-local-addr {
                     type ipaddr;
                     description "Resource local address";
                   }
                   leaf lm-resource-remote-addr {
                     type ipaddr;
                     description "Resource remote address";
                   }
                   container lm-resource-allocation-context {
                     leaf lm-allocated-lsp-name {
                       type string;
                     }
                     leaf lm-local-label {
                       type int32;
                     }
                     leaf lm-remote-label {
                       type int32;
                     }
                     leaf lm-allocated-bandwidth {
                       type string;
                     }
                     leaf lm-bandwidth-shared {
                       type int32;
                     }
                     leaf lm-label-shared {
                       type empty;
                     }
                   }
                 }
               }
             }
           }
         }
         container lm-resource-root-information {
           leaf lm-source {
             type string;
             description "Source of information";
           }
           container lm-resource {
             leaf lm-resource-name {
               type string;
               description "Resource name";
             }
             leaf lm-resource-type {
               type string;
               description "Resource type";
             }
             leaf lm-resource-state {
               type string;
             }
             leaf lm-sys-id {
               type int32;
               description "System identifier of object";
             }
             leaf lm-resource-max-allocations {
               type int32;
               description "Maximum number of allocations";
             }
             leaf lm-resource-bandwidth {
               type string;
               description "Total bandwidth of resource";
             }
             leaf lm-resource-traffic-params {
               type string;
               description "Traffic parameters of resource";
             }
           }
         }
       }
     }
   }
   rpc get-lm-routing-peer-information {
     description "Show peer information";
     input {
       leaf peer-name {
         description "Name of peer";
         type string;
       }
     }
   }
   rpc get-lm-routing-te-link-information {
     description "Show traffic engineering links information";
     input {
       leaf verbosity_level {
         default "brief";
         type enumeration {
           enum "brief" {
             description "Display brief output (default)";
           }
           enum "detail" {
             description "Display detailed output";
           }
         }
       }
       leaf link-name {
         description "Name of traffic engineering link";
         type string;
       }
     }
   }
   rpc get-lm-routing-resource-information {
     description "Show resource information";
     input {
       leaf resource-name {
         description "Name of resource";
         type string;
       }
     }
   }
 }
