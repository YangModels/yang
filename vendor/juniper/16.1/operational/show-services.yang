/*
 * Copyright (c) 2017 Juniper Networks, Inc.
 * All rights reserved.
 */

 module show-services {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-services-security-associations-information {
     description "Show IPSec security association information";
     input {
       leaf level {
         default "brief";
         type enumeration {
           enum "brief" {
             description "Display brief output (default)";
           }
           enum "detail" {
             description "Display detailed output";
           }
           enum "extensive" {
             description "Display extensive output";
           }
         }
       }
       leaf service-set {
         description "Restrict output to one service set";
         type string {
           junos:posix-pattern "^[A-Za-z0-9][_0-9A-Za-z-]{0,62}$";
           junos:pattern-message "Must be a string beginning with a number or letter and consisting of no more than 63 total letters, numbers, dashes and underscores.";
         }
       }
       leaf hex {
         description "Display SPI in hexadecimal format";
         type empty;
       }
     }
     output {
       container services-security-associations-information {
         container brief {
           container services-security-associations-block {
             description "Information about a single services security associations block";
             leaf svc-set-name {
               type string;
               description "Name of the service set";
             }
             leaf outside-service-interface-routing-instance {
               type string;
               description "Name of routing instance that hosts outside service interface";
             }
             container sa-tunnel-information {
               leaf sa-rule-name {
                 type string;
                 description "Name of the rule";
               }
               leaf sa-term-name {
                 type string;
                 description "Name of the term";
               }
               leaf sa-tunnel-index {
                 type int32;
                 description "Tunnel index";
               }
               leaf sa-anchored-pic {
                 type string;
                 description "Anchored pic";
               }
               leaf sa-local-gateway-interface {
                 type string;
                 description "Local gateway  interface";
               }
               leaf sa-local-gateway {
                 type ipaddr;
                 description "Local gateway address";
               }
               leaf sa-remote-gateway {
                 type ipaddr;
                 description "Remote gateway address";
               }
               leaf sa-local-identity {
                 type string;
                 description "Local identity information";
               }
               leaf sa-remote-identity {
                 type string;
                 description "Remote identity information";
               }
               leaf sa-inside-interface {
                 type string;
                 description "Name of IPSec interface to internal network";
               }
               leaf sa-tunnel-mtu {
                 type int32;
                 description "MTU of the IPSec Tunnel";
               }
               leaf sa-udp-encapsulate {
                 type string;
                 description "UDP encapsulation related information";
               }
               leaf sa-udp-dst-port {
                 type string;
                 description "UDP encapsulation port related information";
               }
               leaf sa-no-information {
                 type empty;
                 description "Output string when there are no security associations present";
               }
             }
             container security-associations {
               description "Information about a single security association";
               leaf sa-direction {
                 type string;
                 description "Direction of the security association";
               }
               leaf sa-spi {
                 type string;
                 description "Security Parameter Index";
               }
               leaf sa-aux-spi {
                 type string;
                 description "Auxiliary Security Parameter Index";
               }
               leaf sa-mode {
                 type string;
                 description "Mode of the security association";
               }
               leaf sa-type {
                 type string;
               }
               leaf sa-protocol {
                 type string;
                 description "IPSec security protocol";
               }
             }
           }
         }
         container detail {
           container services-security-associations-block {
             description "Information about a single services security associations block";
             leaf svc-set-name {
               type string;
               description "Name of the service set";
             }
             leaf outside-service-interface-routing-instance {
               type string;
               description "Name of routing instance that hosts outside service interface";
             }
             container sa-tunnel-information {
               leaf sa-rule-name {
                 type string;
                 description "Name of the rule";
               }
               leaf sa-term-name {
                 type string;
                 description "Name of the term";
               }
               leaf sa-tunnel-index {
                 type int32;
                 description "Tunnel index";
               }
               leaf sa-anchored-pic {
                 type string;
                 description "Anchored pic";
               }
               leaf sa-local-gateway-interface {
                 type string;
                 description "Local gateway  interface";
               }
               leaf sa-local-gateway {
                 type ipaddr;
                 description "Local gateway address";
               }
               leaf sa-remote-gateway {
                 type ipaddr;
                 description "Remote gateway address";
               }
               leaf sa-local-identity {
                 type string;
                 description "Local identity information";
               }
               leaf sa-remote-identity {
                 type string;
                 description "Remote identity information";
               }
               leaf sa-inside-interface {
                 type string;
                 description "Name of IPSec interface to internal network";
               }
               leaf sa-tunnel-mtu {
                 type int32;
                 description "MTU of the IPSec Tunnel";
               }
               leaf sa-udp-encapsulate {
                 type string;
                 description "UDP encapsulation related information";
               }
               leaf sa-udp-dst-port {
                 type string;
                 description "UDP encapsulation port related information";
               }
               leaf sa-no-information {
                 type empty;
                 description "Output string when there are no security associations present";
               }
             }
             container security-associations {
               description "Information about a single security association";
               leaf sa-direction {
                 type string;
                 description "Direction of the security association";
               }
               leaf sa-spi {
                 type string;
                 description "Security Parameter Index";
               }
               leaf sa-aux-spi {
                 type string;
                 description "Auxiliary Security Parameter Index";
               }
               leaf sa-mode {
                 type string;
                 description "Mode of the security association";
               }
               leaf sa-type {
                 type string;
               }
               leaf sa-state {
                 type string;
                 description "Status of the SA";
               }
               leaf sa-protocol {
                 type string;
                 description "IPSec security protocol";
               }
               leaf sa-authentication-algorithm {
                 type string;
                 description "Authentication algorithm";
               }
               leaf sa-encryption-algorithm {
                 type string;
                 description "Encryption algorithm";
               }
               leaf sa-soft-lifetime {
                 type string;
                 description "Remaining lifetime, in seconds or kilobytes, before soft lifetime expires";
               }
               leaf sa-hard-lifetime {
                 type string;
                 description "Remaining lifetime, in seconds or kilobytes, before hard lifetime expires";
               }
               leaf sa-anti-replay-service {
                 type string;
                 description "Anti-replay service";
               }
               leaf sa-replay-window-size {
                 type int32;
                 description "Replay window size";
               }
               leaf sa-copy-tos-from-inner-ip-header {
                 type string;
                 description "Copy ToS from inner ip header";
               }
               leaf sa-tos-value {
                 type int32;
                 description "ToS value";
               }
               leaf sa-copy-ttl-from-inner-ip-header {
                 type string;
                 description "Copy TTL from inner ip header";
               }
               leaf sa-ttl-value {
                 type int32;
                 description "TTL value";
               }
             }
           }
         }
         container extensive {
           container services-security-associations-block {
             description "Information about a single services security associations block";
             leaf svc-set-name {
               type string;
               description "Name of the service set";
             }
             leaf outside-service-interface-routing-instance {
               type string;
               description "Name of routing instance that hosts outside service interface";
             }
             container sa-tunnel-information {
               leaf sa-rule-name {
                 type string;
                 description "Name of the rule";
               }
               leaf sa-term-name {
                 type string;
                 description "Name of the term";
               }
               leaf sa-tunnel-index {
                 type int32;
                 description "Tunnel index";
               }
               leaf sa-anchored-pic {
                 type string;
                 description "Anchored pic";
               }
               leaf sa-local-gateway-interface {
                 type string;
                 description "Local gateway  interface";
               }
               leaf sa-local-gateway {
                 type ipaddr;
                 description "Local gateway address";
               }
               leaf sa-remote-gateway {
                 type ipaddr;
                 description "Remote gateway address";
               }
               leaf sa-local-identity {
                 type string;
                 description "Local identity information";
               }
               leaf sa-remote-identity {
                 type string;
                 description "Remote identity information";
               }
               leaf sa-inside-interface {
                 type string;
                 description "Name of IPSec interface to internal network";
               }
               leaf sa-tunnel-mtu {
                 type int32;
                 description "MTU of the IPSec Tunnel";
               }
               leaf sa-udp-encapsulate {
                 type string;
                 description "UDP encapsulation related information";
               }
               leaf sa-udp-dst-port {
                 type string;
                 description "UDP encapsulation port related information";
               }
               leaf sa-no-information {
                 type empty;
                 description "Output string when there are no security associations present";
               }
             }
             container security-associations {
               description "Information about a single security association";
               leaf sa-direction {
                 type string;
                 description "Direction of the security association";
               }
               leaf sa-spi {
                 type string;
                 description "Security Parameter Index";
               }
               leaf sa-aux-spi {
                 type string;
                 description "Auxiliary Security Parameter Index";
               }
               leaf sa-mode {
                 type string;
                 description "Mode of the security association";
               }
               leaf sa-type {
                 type string;
               }
               leaf sa-state {
                 type string;
                 description "Status of the SA";
               }
               leaf sa-protocol {
                 type string;
                 description "IPSec security protocol";
               }
               leaf sa-authentication-algorithm {
                 type string;
                 description "Authentication algorithm";
               }
               leaf sa-encryption-algorithm {
                 type string;
                 description "Encryption algorithm";
               }
               leaf sa-soft-lifetime {
                 type string;
                 description "Remaining lifetime, in seconds or kilobytes, before soft lifetime expires";
               }
               leaf sa-hard-lifetime {
                 type string;
                 description "Remaining lifetime, in seconds or kilobytes, before hard lifetime expires";
               }
               leaf sa-anti-replay-service {
                 type string;
                 description "Anti-replay service";
               }
               leaf sa-replay-window-size {
                 type int32;
                 description "Replay window size";
               }
               leaf sa-copy-tos-from-inner-ip-header {
                 type string;
                 description "Copy ToS from inner ip header";
               }
               leaf sa-tos-value {
                 type int32;
                 description "ToS value";
               }
               leaf sa-copy-ttl-from-inner-ip-header {
                 type string;
                 description "Copy TTL from inner ip header";
               }
               leaf sa-ttl-value {
                 type int32;
                 description "TTL value";
               }
             }
             container tunnel-redundancy-extensive {
               description "Information about IPSec tunnel redundancy";
               leaf ipsec-tunnel-redundancy-primary-remote-address {
                 type ipaddr;
                 description "Address of primary remote gateway";
               }
               leaf ipsec-redundancy-primary-state {
                 type string;
                 description "State of primary remote gateway";
               }
               leaf ipsec-redundancy-counter {
                 type int32;
                 description "Failover counter";
               }
               leaf ipsec-tunnel-redundancy-backup-remote-address {
                 type ipaddr;
                 description "Address of backup remote gateway";
               }
               leaf ipsec-redundancy-backup-state {
                 type string;
                 description "State of backup remote gateway";
               }
               leaf ipsec-redundancy-tunnel-no-information {
                 type empty;
                 description "Output string when tunnel redundancy is not configured";
               }
             }
           }
         }
       }
     }
   }
   rpc get-services-ipsec-statistics-information {
     description "Show IPSec statistics";
     input {
       leaf remote-gw {
         description "Peer address to use as filter";
         type string;
       }
       leaf display {
         default "brief";
         type enumeration {
           enum "detail" {
             description "Display all tunnels";
           }
           enum "brief" {
             description "Display accumulated statistics (default)";
           }
         }
       }
       leaf service-set {
         description "Name of service set";
         type string;
       }
     }
     output {
       container ipsec-total-statistics-information {
         container brief {
           container ipsec-service-set-statistics {
             leaf pic-name {
               type string;
               description "PIC name";
             }
             leaf service-set-name {
               type string;
               description "Service set name";
             }
             container ipsec-statistics {
               leaf statistics-no-information {
                 type empty;
                 description "Output string when there are no statistics to report";
               }
               container esp-statistics {
                 leaf esp-encrypted-bytes {
                   type uint64;
                   description "ESP encrypted bytes information";
                 }
                 leaf esp-decrypted-bytes {
                   type uint64;
                   description "ESP decrypted bytes information";
                 }
                 leaf esp-encrypted-packets {
                   type uint64;
                   description "ESP encrypted packets information";
                 }
                 leaf esp-decrypted-packets {
                   type uint64;
                   description "ESP decrypted packets information";
                 }
               }
               container ah-statistics {
                 leaf ah-input-bytes {
                   type uint64;
                   description "AH input bytes information";
                 }
                 leaf ah-output-bytes {
                   type uint64;
                   description "AH output bytes information";
                 }
                 leaf ah-input-packets {
                   type uint64;
                   description "AH input packets information";
                 }
                 leaf ah-output-packets {
                   type uint64;
                   description "AH output packets information";
                 }
               }
               container d3p-statistics {
                 leaf d3p-old-packets {
                   type uint64;
                   description "D3p packets information";
                 }
                 leaf d3p-new-packets {
                   type uint64;
                   description "D3p packets information";
                 }
                 leaf d3p-no-header-packets {
                   type uint64;
                   description "D3p packets information";
                 }
                 leaf d3p-unexpected-header-packets {
                   type uint64;
                   description "D3p packets information";
                 }
               }
               container fail-open-statistics {
                 leaf fail-open-packets-received {
                   type uint64;
                   description "Fail open packets information";
                 }
                 leaf fail-open-packets-sent {
                   type uint64;
                   description "Fail open packets information";
                 }
               }
               container error-statistics {
                 leaf ah-authentication-failures {
                   type int32;
                   description "AH authentication failures information";
                 }
                 leaf esp-authentication-failures {
                   type int32;
                   description "ESP authentication failures information";
                 }
                 leaf esp-decryption-failures {
                   type int32;
                   description "ESP decryption failures information";
                 }
                 leaf bad-headers {
                   type int32;
                   description "Bad header information";
                 }
                 leaf bad-trailers {
                   type int32;
                   description "Bad trailer information";
                 }
                 leaf replay-before-window-drops {
                   type int32;
                   description "Replay before window drop information";
                 }
                 leaf replay-pkts {
                   type int32;
                   description "Replayed pkt information";
                 }
                 leaf rule-lookup-fail {
                   type int32;
                   description "Rule lookup failure information";
                 }
                 leaf no-sa-errors {
                   type int32;
                   description "No SA error information";
                 }
                 leaf ip-integrity-errors {
                   type int32;
                   description "IP Integrity error information";
                 }
                 leaf exceeds-tunnel-mtu {
                   type int32;
                   description "Exceeds Tunnel MTU";
                 }
                 leaf flow-errors {
                   type int32;
                   description "Flow error information";
                 }
                 leaf misc-errors {
                   type int32;
                   description "Misc error information";
                 }
                 leaf replay-errors {
                   type int32;
                   description "Replay error information";
                 }
               }
             }
           }
         }
         container detail {
           container ipsec-service-set-statistics {
             leaf pic-name {
               type string;
               description "PIC name";
             }
             leaf service-set-name {
               type string;
               description "Service set name";
             }
             container ipsec-statistics {
               leaf local-gateway {
                 type ipaddr;
                 description "Local gateway address";
               }
               leaf remote-gateway {
                 type ipaddr;
                 description "Remote gateway address";
               }
               leaf tunnel-index {
                 type int32;
                 description "Tunnel index";
               }
               leaf statistics-no-information {
                 type empty;
                 description "Output string when there are no statistics to report";
               }
               container esp-statistics {
                 leaf esp-encrypted-bytes {
                   type uint64;
                   description "ESP encrypted bytes information";
                 }
                 leaf esp-decrypted-bytes {
                   type uint64;
                   description "ESP decrypted bytes information";
                 }
                 leaf esp-encrypted-packets {
                   type uint64;
                   description "ESP encrypted packets information";
                 }
                 leaf esp-decrypted-packets {
                   type uint64;
                   description "ESP decrypted packets information";
                 }
               }
               container ah-statistics {
                 leaf ah-input-bytes {
                   type uint64;
                   description "AH input bytes information";
                 }
                 leaf ah-output-bytes {
                   type uint64;
                   description "AH output bytes information";
                 }
                 leaf ah-input-packets {
                   type uint64;
                   description "AH input packets information";
                 }
                 leaf ah-output-packets {
                   type uint64;
                   description "AH output packets information";
                 }
               }
               container d3p-statistics {
                 leaf d3p-old-packets {
                   type uint64;
                   description "D3p packets information";
                 }
                 leaf d3p-new-packets {
                   type uint64;
                   description "D3p packets information";
                 }
                 leaf d3p-no-header-packets {
                   type uint64;
                   description "D3p packets information";
                 }
                 leaf d3p-unexpected-header-packets {
                   type uint64;
                   description "D3p packets information";
                 }
               }
               container fail-open-statistics {
                 leaf fail-open-packets-received {
                   type uint64;
                   description "Fail open packets information";
                 }
                 leaf fail-open-packets-sent {
                   type uint64;
                   description "Fail open packets information";
                 }
               }
               container error-statistics {
                 leaf ah-authentication-failures {
                   type int32;
                   description "AH authentication failures information";
                 }
                 leaf esp-authentication-failures {
                   type int32;
                   description "ESP authentication failures information";
                 }
                 leaf esp-decryption-failures {
                   type int32;
                   description "ESP decryption failures information";
                 }
                 leaf bad-headers {
                   type int32;
                   description "Bad header information";
                 }
                 leaf bad-trailers {
                   type int32;
                   description "Bad trailer information";
                 }
                 leaf replay-before-window-drops {
                   type int32;
                   description "Replay before window drop information";
                 }
                 leaf replay-pkts {
                   type int32;
                   description "Replayed pkt information";
                 }
                 leaf replay-errors {
                   type int32;
                   description "Replay error information";
                 }
               }
             }
           }
         }
       }
     }
   }
   rpc get-ike-services-security-associations-information {
     description "Show services IKE security association information";
     input {
       leaf level {
         default "brief";
         type enumeration {
           enum "brief" {
             description "Show brief output (default)";
           }
           enum "detail" {
             description "Show detailed output";
           }
         }
       }
       leaf peer-address {
         description "Name of security association";
         type ipaddr;
       }
       leaf routing-instance {
         description "Name of the local-gateway routing-instance";
         type string;
       }
     }
     output {
       container ike-security-associations-information {
         container brief {
           container ike-security-associations {
             description "Information about a single security association";
             leaf ike-sa-remote-address {
               type ipaddr;
               description "Remote address";
             }
             leaf ike-sa-state {
               type string;
               description "Status of the SA";
             }
             leaf ike-sa-initiator-cookie {
               type string;
               description "IKE SA initiator cookie";
             }
             leaf ike-sa-responder-cookie {
               type string;
               description "IKE SA responder cookie";
             }
             leaf ike-sa-exchange-type {
               type string;
               description "Exchange type";
             }
             container ike-sa-algorithms {
               description "Algorithms used with the SA information";
               leaf ike-sa-sig-key-length {
                 type uint32;
                 description "Signature Key Length";
               }
             }
             container ike-sa-traffic-statistics {
               description "Number of packets and bytes received and transmitted on the SA";
               leaf ike-sa-output-invalid-spi-packets {
                 type int32;
                 description "Number of invalid SPI notifications send";
               }
               leaf ike-sa-input-invalid-spi-packets {
                 type int32;
                 description "Number of invalid SPI notifications received";
               }
             }
           }
           container ike-security-associations-block {
             description "Information about a single security association block";
             container ike-security-associations {
               description "Information about a single security association";
               container ike-sa-algorithms {
                 description "Algorithms used with the SA information";
                 leaf ike-sa-sig-key-length {
                   type uint32;
                   description "Signature Key Length";
                 }
               }
               container ike-sa-traffic-statistics {
                 description "Number of packets and bytes received and transmitted on the SA";
                 leaf ike-sa-output-invalid-spi-packets {
                   type int32;
                   description "Number of invalid SPI notifications send";
                 }
                 leaf ike-sa-input-invalid-spi-packets {
                   type int32;
                   description "Number of invalid SPI notifications received";
                 }
               }
             }
           }
         }
         container detail {
           container ike-security-associations {
             description "Information about a single security association";
             container ike-sa-algorithms {
               description "Algorithms used with the SA information";
               leaf ike-sa-sig-key-length {
                 type uint32;
                 description "Signature Key Length";
               }
             }
             container ike-sa-traffic-statistics {
               description "Number of packets and bytes received and transmitted on the SA";
               leaf ike-sa-output-invalid-spi-packets {
                 type int32;
                 description "Number of invalid SPI notifications send";
               }
               leaf ike-sa-input-invalid-spi-packets {
                 type int32;
                 description "Number of invalid SPI notifications received";
               }
             }
           }
           container ike-security-associations-block {
             description "Information about a single security association block";
             leaf ike-sa-remote-address {
               type ipaddr;
               description "Remote address";
             }
             container ike-security-associations {
               description "Information about a single security association";
               leaf ike-sa-role {
                 type string;
                 description "Role of our end";
               }
               leaf ike-sa-state {
                 type string;
                 description "Status of the SA";
               }
               leaf ike-sa-initiator-cookie {
                 type string;
                 description "IKE SA initiator cookie";
               }
               leaf ike-sa-responder-cookie {
                 type string;
                 description "IKE SA responder cookie";
               }
               leaf ike-sa-exchange-type {
                 type string;
                 description "Exchange type";
               }
               leaf ike-sa-authentication-method {
                 type string;
               }
               leaf ike-sa-local-gateway-interface {
                 type string;
                 description "Local gateway  interface";
               }
               leaf ike-sa-routing-instance {
                 type string;
                 description "Local-gateway routing instance";
               }
               leaf ike-sa-local-address {
                 type ipaddr;
                 description "Local address";
               }
               leaf ike-sa-local-port {
                 type int32;
                 description "Local port";
               }
               leaf ike-sa-remote-port {
                 type int32;
                 description "Remote port";
               }
               leaf ike-sa-lifetime {
                 type string;
                 description "Remaining lifetime before expiration, in seconds or kilobytes";
               }
               container ike-sa-algorithms {
                 description "Algorithms used with the SA information";
                 leaf ike-sa-authentication-algorithm {
                   type string;
                   description "Authentication algorithm";
                 }
                 leaf ike-sa-encryption-algorithm {
                   type string;
                   description "Encryption algorithm";
                 }
                 leaf ike-sa-prf-algorithm {
                   type string;
                   description "PRF algorithm";
                 }
                 leaf ike-sa-dhgroup {
                   type string;
                   description "DH group";
                 }
                 leaf ike-sa-sig-key-length {
                   type uint32;
                   description "Signature Key Length";
                 }
               }
               container ike-sa-traffic-statistics {
                 description "Number of packets and bytes received and transmitted on the SA";
                 leaf ike-sa-input-bytes {
                   type int32;
                   description "Input bytes, including retransmissions";
                 }
                 leaf ike-sa-output-bytes {
                   type int32;
                   description "Output bytes, including retransmissions";
                 }
                 leaf ike-sa-input-packets {
                   type int32;
                   description "Input packets, including retransmissions";
                 }
                 leaf ike-sa-output-packets {
                   type int32;
                   description "Output packets, including retransmissions";
                 }
                 leaf ike-sa-output-invalid-spi-packets {
                   type int32;
                   description "Number of invalid SPI notifications send";
                 }
                 leaf ike-sa-input-invalid-spi-packets {
                   type int32;
                   description "Number of invalid SPI notifications received";
                 }
               }
               container ike-sa-misc {
                 description "Miscellaneous IKE SA information";
                 leaf ike-sa-flags {
                   type string;
                   description "IKE SA flags";
                 }
                 leaf ike-sa-num-ipsec-sas-created {
                   type int32;
                   description "Number of IPSec SAs created using this SA";
                 }
                 leaf ike-sa-num-ipsec-sas-deleted {
                   type int32;
                   description "Number of IPSec SAs deleted using this SA";
                 }
                 leaf ike-sa-num-phase2-negotiations {
                   type int32;
                   description "Number of negotiations in progress on this SA";
                 }
               }
               container ike-sa-phase2-information {
                 description "Information about phase 2 negotiation";
                 leaf ike-sa-phase2-type {
                   type string;
                   description "Type of phase 2 negotiation";
                 }
                 leaf ike-sa-role {
                   type string;
                   description "Role of our end";
                 }
                 leaf ike-sa-msg-id {
                   type int32;
                   description "Message ID of the quick mode negotiation";
                 }
                 leaf ike-sa-local-address {
                   type ipaddr;
                   description "Local address";
                 }
                 leaf ike-sa-local-port {
                   type int32;
                   description "Local port";
                 }
                 leaf ike-sa-remote-address {
                   type ipaddr;
                   description "Remote address";
                 }
                 leaf ike-sa-remote-port {
                   type int32;
                   description "Remote port";
                 }
                 leaf ike-sa-local-id {
                   type string;
                   description "Local end identity in phase 2";
                 }
                 leaf ike-sa-remote-id {
                   type string;
                   description "Remote end identity in phase 2";
                 }
                 leaf ike-sa-flags {
                   type string;
                   description "IKE SA flags";
                 }
               }
             }
           }
         }
       }
     }
   }
   rpc get-ike-services-statistics {
     description "Show services IKE security association statistics";
     input {
       leaf peer-address {
         description "Name of security association";
         type ipaddr;
       }
       leaf routing-instance {
         description "Name of the local-gateway routing-instance";
         type string;
       }
     }
     output {
       container ike-security-associations-statistics {
         container brief {
           container ike-security-associations {
             description "Information about a single security association";
             container ike-sa-algorithms {
               description "Algorithms used with the SA information";
               leaf ike-sa-sig-key-length {
                 type uint32;
                 description "Signature Key Length";
               }
             }
             container ike-sa-traffic-statistics {
               description "Number of packets and bytes received and transmitted on the SA";
               leaf ike-sa-output-invalid-spi-packets {
                 type int32;
                 description "Number of invalid SPI notifications send";
               }
               leaf ike-sa-input-invalid-spi-packets {
                 type int32;
                 description "Number of invalid SPI notifications received";
               }
             }
           }
           container ike-security-associations-block {
             description "Information about a single security association block";
             leaf ike-sa-remote-address {
               type ipaddr;
               description "Remote address";
             }
             container ike-security-associations {
               description "Information about a single security association";
               leaf ike-sa-initiator-cookie {
                 type string;
                 description "IKE SA initiator cookie";
               }
               leaf ike-sa-responder-cookie {
                 type string;
                 description "IKE SA responder cookie";
               }
               leaf ike-sa-routing-instance {
                 type string;
                 description "Local-gateway routing instance";
               }
               leaf ike-sa-local-address {
                 type ipaddr;
                 description "Local address";
               }
               leaf ike-sa-local-port {
                 type int32;
                 description "Local port";
               }
               leaf ike-sa-remote-port {
                 type int32;
                 description "Remote port";
               }
               container ike-sa-algorithms {
                 description "Algorithms used with the SA information";
                 leaf ike-sa-sig-key-length {
                   type uint32;
                   description "Signature Key Length";
                 }
               }
               container ike-sa-traffic-statistics {
                 description "Number of packets and bytes received and transmitted on the SA";
                 leaf ike-sa-input-bytes {
                   type int32;
                   description "Input bytes, including retransmissions";
                 }
                 leaf ike-sa-output-bytes {
                   type int32;
                   description "Output bytes, including retransmissions";
                 }
                 leaf ike-sa-input-packets {
                   type int32;
                   description "Input packets, including retransmissions";
                 }
                 leaf ike-sa-output-packets {
                   type int32;
                   description "Output packets, including retransmissions";
                 }
                 leaf ike-sa-output-invalid-spi-packets {
                   type int32;
                   description "Number of invalid SPI notifications send";
                 }
                 leaf ike-sa-input-invalid-spi-packets {
                   type int32;
                   description "Number of invalid SPI notifications received";
                 }
               }
               container ike-sa-misc {
                 description "Miscellaneous IKE SA information";
                 leaf ike-sa-num-ipsec-sas-created {
                   type int32;
                   description "Number of IPSec SAs created using this SA";
                 }
                 leaf ike-sa-num-ipsec-sas-deleted {
                   type int32;
                   description "Number of IPSec SAs deleted using this SA";
                 }
                 leaf ike-sa-num-ipsec-rekeys {
                   type int32;
                   description "Number of IPSec rekeys using this SA";
                 }
               }
               container ike-sa-payload-statistics {
                 description "Statistics related to payload types received and transmitted on this SA";
                 leaf ike-sa-delete-payloads-received {
                   type int32;
                   description "Number of delete payloads received";
                 }
                 leaf ike-sa-delete-payloads-sent {
                   type int32;
                   description "Number of delete payloads sent";
                 }
                 leaf ike-sa-r-u-there-payloads-received {
                   type int32;
                   description "Number of DPD R-U-THERE payloads received";
                 }
                 leaf ike-sa-r-u-there-payloads-sent {
                   type int32;
                   description "Number of DPD R-U-THERE payloads sent";
                 }
                 leaf ike-sa-r-u-there-ack-payloads-received {
                   type int32;
                   description "Number of DPD R-U-THERE-ACK payloads received";
                 }
                 leaf ike-sa-r-u-there-ack-payloads-sent {
                   type int32;
                   description "Number of DPD R-U-THERE-ACK payloads sent";
                 }
                 leaf ike-sa-r-u-there-ack-payloads-missed {
                   type int32;
                   description "Number of DPD R-U-THERE-ACK payloads missed";
                 }
                 leaf ike-sa-r-u-there-ack-payloads-maximum-delay {
                   type int32;
                   description "Worst case delay for the DPD R-U-THERE-ACK";
                 }
                 leaf ike-sa-invalid-spi-notifications-received {
                   type int32;
                   description "Number of invalid SPI notifications received";
                 }
                 leaf ike-sa-invalid-spi-notifications-sent {
                   type int32;
                   description "Number of invalid SPI notifications sent";
                 }
               }
             }
           }
         }
       }
     }
   }
   rpc get-fips-pic-status-information {
     description "Show FIPS PIC authorization status";
     output {
       container fips-pic-status-information {
         container fips-pic-status {
           leaf fpc-slot {
             type int32;
             description "FPC slot";
           }
           leaf pic-slot {
             type int32;
             description "PIC slot";
           }
           leaf serial-number {
             type string;
             description "PIC serial number";
           }
           leaf authorization-status {
             type string;
             description "PIC authorization status";
           }
         }
       }
     }
   }
   rpc get-ggsn-imsi-trace {
     description "Show trace information for Identifier for International Mobile Subscriber Identity";
     input {
       leaf imsi-identifier {
         description "Identifier for IMSI";
         type string {
           junos:posix-pattern "^[0-9]{5,15}$";
           junos:pattern-message "IMSI must be 5 to 15 digits.";
         }
         mandatory true;
       }
     }
     output {
       container call-trace-information {
         leaf number-enabled {
           type int32;
           description "Number of call traces that are set up";
         }
         leaf number-active {
           type int32;
           description "Number of call traces that are active";
         }
         container call-trace {
           description "Information about a GGSN node call trace";
           leaf imsi {
             type string;
             description "International Mobile Subscriber Identity for user";
           }
           leaf msisdn {
             type string;
             description "Mobile Station Integrated Services Digital Network number for user";
           }
           leaf time-started {
             type string;
             description "Time at which the service started";
           }
           container nsapi-information {
             description "List of NSAPIs associated with user";
           }
         }
       }
     }
   }
   rpc get-ggsn-msisdn-trace {
     description "Show trace information for Mobile Station Integrated Services Digital Network";
     input {
       leaf msisdn-identifier {
         description "Identifier for MSISDN";
         type string {
           junos:posix-pattern "^[0-9]{1,18}$";
           junos:pattern-message "MSISDN must be 1 to 18 digits.";
         }
         mandatory true;
       }
     }
     output {
       container call-trace-information {
         leaf number-enabled {
           type int32;
           description "Number of call traces that are set up";
         }
         leaf number-active {
           type int32;
           description "Number of call traces that are active";
         }
         container call-trace {
           description "Information about a GGSN node call trace";
           leaf imsi {
             type string;
             description "International Mobile Subscriber Identity for user";
           }
           leaf msisdn {
             type string;
             description "Mobile Station Integrated Services Digital Network number for user";
           }
           leaf time-started {
             type string;
             description "Time at which the service started";
           }
           container nsapi-information {
             description "List of NSAPIs associated with user";
           }
         }
       }
     }
   }
   rpc get-ggsn-trace {
     description "Show all trace information";
     output {
       container call-trace-information {
         leaf number-enabled {
           type int32;
           description "Number of call traces that are set up";
         }
         leaf number-active {
           type int32;
           description "Number of call traces that are active";
         }
         container call-trace {
           description "Information about a GGSN node call trace";
           leaf imsi {
             type string;
             description "International Mobile Subscriber Identity for user";
           }
           leaf msisdn {
             type string;
             description "Mobile Station Integrated Services Digital Network number for user";
           }
           leaf time-started {
             type string;
             description "Time at which the service started";
           }
           container nsapi-information {
             description "List of NSAPIs associated with user";
           }
         }
       }
     }
   }
   rpc get-ggsn-interface-information {
     description "Show GGSN operational status information";
     output {
       container ggsn-interface-information {
         container ggsn-interface {
           description "Information about GGSN-C and GGSN-U service interfaces";
           leaf service-interface {
             type string;
             description "Service interface for the information";
           }
           leaf external-address {
             type ipaddr;
             description "External address for the PIC";
           }
           leaf internal-address {
             type ipaddr;
             description "Internal address for the PIC";
           }
           leaf operating-function {
             type string;
             description "Current cluster function for the PIC";
           }
           leaf hardware-version {
             type string;
             description "PIC hardware version";
           }
           leaf software-version {
             type string;
             description "GGSN service software version";
           }
           leaf time-started {
             type string;
             description "Time at which the service started";
           }
           leaf weighted-pdp-context-load-in-control {
             type int32;
           }
           leaf weighted-pdp-context-load-in-payload {
             type int32;
           }
           container pdp {
             description "PDP context information";
           }
           container resources {
             description "CPU and memory information for a PIC";
             leaf memory-total {
               type uint32;
               description "DRAM size (megabytes)";
             }
             leaf memory-used {
               type uint32;
               description "DRAM used (megabytes)";
             }
             container cpu-info {
               description "CPU usage";
               leaf cpu-id {
                 type int32;
                 description "CPU ID";
               }
               leaf cpu-load {
                 type int32;
                 description "CPU usage (percentage)";
               }
             }
           }
           container tft-statistics {
             leaf maximum-tft-filter-depth {
               type int32;
               description "Maximum TFT filter depth per user in the last period";
             }
             leaf mean-tft-filter-depth {
               type int32;
               description "Mean TFT filter depth per user in the last period";
             }
           }
           container sbcc-statistics-information {
             description "Service-based charging statistics";
             leaf prepaid-request {
               type int32;
               description "Number of application transaction towards prepaid server";
             }
             leaf rating-request {
               type int32;
               description "Number of application transaction towards policy/rate server";
             }
             leaf prepaid-user {
               type int32;
               description "Number of prepaid users";
             }
             leaf prepaid-context {
               type int32;
               description "Number of prepaid contexts";
             }
             leaf prepaid-pdp-creates-attempted {
               type int32;
               description "Number of prepaid PDP context creates attempted";
             }
             leaf prepaid-pdp-creates-failed {
               type int32;
               description "Number of prepaid PDP context create attempts that failed";
             }
             leaf pdp-initiated-deactivation {
               type int32;
               description "Number of PDP context deactivations initiated by service-based-charging";
             }
             leaf credit-start-request-attempted {
               type int32;
               description "Number of credit start requests attempted";
             }
             leaf credit-start-request-failed {
               type int32;
               description "Number of credit start requests failed";
             }
             leaf rating-initial-request-attempted {
               type int32;
               description "Number of initial rating requests attempted";
             }
             leaf rating-initial-request-failed {
               type int32;
               description "Number of initial rating requests failed";
             }
             leaf rating-update-request-attempted {
               type int32;
               description "Number of attempted rating update requests";
             }
             leaf rating-update-request-failed {
               type int32;
               description "Number of failed rating update requests";
             }
             leaf credit-update-request-attempted {
               type int32;
               description "Number of credit update requests attempted";
             }
             leaf credit-update-request-failed {
               type int32;
               description "Number of credit update requests failed";
             }
             leaf credit-stop-request-attempted {
               type int32;
               description "Number of credit stop requests attempted";
             }
             leaf credit-stop-request-failed {
               type int32;
               description "Number of credit start requests failed";
             }
             leaf external-prs-update {
               type int32;
               description "Number of externally initiated URT updates for users using PRS";
             }
             leaf external-prs-update-no-match {
               type int32;
               description "Number of external URT updates for non-existing users or users not using PRS";
             }
             leaf external-credit-update {
               type int32;
               description "Number of externally initiated credit updates for users with prepaid service";
             }
             leaf external-credit-update-no-match {
               type int32;
               description "Number of external credit updates for non-existing users or users not using prepaid service";
             }
             leaf external-update-failed {
               type int32;
               description "Number of failed external URT/credit updates";
             }
             leaf duration-time {
               type int32;
               description "Seconds measured for duration time";
             }
             leaf activation-bearer-ctrl-accept {
               type int32;
               description "QoS accepts at activation, SGSN bearer ctrl";
             }
             leaf activation-bearer-ctrl-reject {
               type int32;
               description "PDP context rejects at activation, SGSN bearer ctrl";
             }
             leaf activation-bearer-ctrl-upgrade {
               type int32;
               description "QoS upgrades at activation, SGSN bearer ctrl";
             }
             leaf activation-bearer-ctrl-downgrade {
               type int32;
               description "QoS downgrades at activation, SGSN bearer ctrl";
             }
             leaf modification-bearer-ctrl-accept {
               type int32;
               description "QoS accepts at modification, SGSN bearer ctrl";
             }
             leaf modification-bearer-ctrl-deactivate {
               type int32;
               description "PDP ctx deactivates at modification, SGSN bearer ctrl";
             }
             leaf modification-bearer-ctrl-upgrade {
               type int32;
               description "QoS upgrades at modification, SGSN bearer ctrl";
             }
             leaf modification-bearer-ctrl-downgrade {
               type int32;
               description "QoS downgrades at modification, SGSN bearer ctrl";
             }
             leaf activation-no-bearer-ctrl-accept {
               type int32;
               description "QoS accepts at activation, no SGSN bearer ctrl";
             }
             leaf activation-no-bearer-ctrl-reject {
               type int32;
               description "PDP context rejects at activation, no SGSN bearer ctrl";
             }
             leaf activation-no-bearer-ctrl-downgrade {
               type int32;
               description "QoS downgrades at activation, no SGSN bearer ctrl";
             }
             leaf modification-no-bearer-ctrl-accept {
               type int32;
               description "QoS accepts at modification, no SGSN bearer ctrl";
             }
             leaf modification-no-bearer-ctrl-deactivate {
               type int32;
               description "PDP ctx deactivates at modification, no SGSN bearer ctrl";
             }
             leaf modification-no-bearer-ctrl-downgrade {
               type int32;
               description "QoS downgrades at modification, no SGSN bearer ctrl";
             }
             container das-information {
               description "Information about diameter application systems";
               container das-statistics {
                 description "Statistics for a diameter application system";
                 leaf das-identifier {
                   type string;
                   description "Diameter application system identifier";
                 }
                 leaf request {
                   type int32;
                   description "Requests";
                 }
               }
             }
             container pras-information {
               description "Information about policy rating application systems";
               container pras-statistics {
                 description "Statistics for a policy rating application system";
                 leaf pras-identifier {
                   type string;
                   description "Policy rating application system identifier";
                 }
                 leaf pras-start-request {
                   type int32;
                   description "PR-AS start requests";
                 }
                 leaf pras-start-request-failed {
                   type int32;
                   description "PR-AS start requests failed";
                 }
                 leaf pras-update-request {
                   type int32;
                   description "PR-AS update requests";
                 }
                 leaf pras-update-request-failed {
                   type int32;
                   description "PR-AS update requests failed";
                 }
                 leaf pras-stop-request {
                   type int32;
                   description "PR-AS stop requests";
                 }
                 leaf pras-stop-request-failed {
                   type int32;
                   description "PR-AS stop requests failed";
                 }
                 leaf pras-user-service-denied {
                   type int32;
                   description "PR-AS requests failed with user service denied";
                 }
                 leaf pras-user-unknown {
                   type int32;
                   description "PR-AS requests failed with user unknown";
                 }
               }
             }
             container ccas-information {
               description "Information about credit control application systems";
               container ccas-statistics {
                 description "Statistics for a credit control application system";
                 leaf ccas-identifier {
                   type string;
                   description "Credit control application system identifier";
                 }
                 leaf ccas-start-request {
                   type int32;
                   description "CC-AS start requests";
                 }
                 leaf ccas-start-request-failed {
                   type int32;
                   description "CC-AS start requests failed";
                 }
                 leaf ccas-update-request {
                   type int32;
                   description "CC-AS update requests";
                 }
                 leaf ccas-update-request-failed {
                   type int32;
                   description "CC-AS update requests failed";
                 }
                 leaf ccas-stop-request {
                   type int32;
                   description "CC-AS stop requests";
                 }
                 leaf ccas-stop-request-failed {
                   type int32;
                   description "CC-AS stop requests failed";
                 }
                 leaf ccas-user-service-denied {
                   type int32;
                   description "CC-AS requests failed with user service denied";
                 }
                 leaf ccas-user-unknown {
                   type int32;
                   description "CC-AS requests failed with user unknown";
                 }
                 leaf ccas-authorization-failure {
                   type int32;
                   description "Failed CC-AS requests due to result code Authorization Rejected";
                 }
                 leaf ccas-cc-not-applicable {
                   type int32;
                   description "Credit control not applicable";
                 }
               }
             }
             container service-class-information {
               description "Information about a service class";
               container service-class-statistics {
                 description "Statistics for a service class";
                 leaf service-class-identifier {
                   type int32;
                   description "Service class identifier";
                 }
                 leaf uplink-bytes {
                   type int32;
                   description "Bytes in the uplink direction";
                 }
                 leaf downlink-bytes {
                   type int32;
                   description "Bytes in the downlink direction";
                 }
                 leaf active-time {
                   type int32;
                   description "Seconds measured for active time for service class";
                 }
               }
             }
             container rate-group-information {
               description "Information about a rate group";
               container rate-group-statistics {
                 description "Statistics for a rate group";
                 leaf rate-group-identifier {
                   type int32;
                   description "Rate group identifier";
                 }
                 leaf transactions-start {
                   type int32;
                   description "Start transaction events";
                 }
                 leaf transactions-success {
                   type int32;
                   description "Successful transaction events";
                 }
               }
             }
             container authorization-discard-information {
               container authorization-discard-statistics {
                 description "Statistics for authorization-based packet discards";
                 leaf service-class-source {
                   type string;
                   description "Service class list source";
                 }
                 leaf packets {
                   type int32;
                   description "Count of packets";
                 }
                 leaf bytes {
                   type int32;
                   description "Count of bytes";
                 }
               }
             }
           }
         }
       }
     }
   }
   rpc get-ggsn-statistics {
     description "Show GGSN statistics";
     output {
       container ggsn-statistics {
         leaf time-started {
           type string;
           description "Time at which the service started";
         }
         leaf time-sampled {
           type string;
           description "Time at which GGSN statistics were updated";
         }
         leaf tft-filter-count {
           type int32;
           description "Number of traffic flow template filters in use";
         }
         leaf subscriber-count {
           type int32;
           description "Number of subscribers currently serviced by this GGSN";
         }
         leaf wlan-pdp-context-activation-procedures {
           type int32;
           description "Number of WLAN PDP context activation procedures initiaded by MS";
         }
         leaf wlan-processed-uplink-bytes {
           type int32;
           description "Total bytes for all processed uplink WLAN packets via this GGSN";
         }
         leaf wlan-dropped-uplink-packets {
           type int32;
           description "Number of dropped WLAN packets in uplink direction";
         }
         leaf wlan-processed-uplink-packets {
           type int32;
           description "Total WLAN uplink packets processed by this GGSN";
         }
         leaf wlan-completed-pdp-context-activations {
           type int32;
           description "Number of completed WLAN PDP context activations";
         }
         leaf wlan-active-pdp-contexts {
           type int32;
           description "Number of active WLAN PDP contexts";
         }
         leaf wlan-processed-downlink-bytes {
           type int32;
           description "Total WLAN downlink bytes processed by this GGSN";
         }
         leaf wlan-dropped-downlink-packets {
           type int32;
           description "Total WLAN downlink packets dropped by this GGSN";
         }
         leaf wlan-processed-downlink-packets {
           type int32;
           description "Total WLAN downlink packets processed by this GGSN";
         }
         container pdp-context-statistics {
           description "Information about PDP context events";
           leaf pdp-active {
             type int32;
             description "Number of active PDP contexts";
           }
           leaf pdp-active-msisdn {
             type int32;
             description "Number of active MSISDNs";
           }
           leaf pdp-active-imsi {
             type int32;
             description "Number of active IMSIs";
           }
           leaf pdp-active-conversational {
             type int32;
             description "Active contexts, traffic class conversational";
           }
           leaf pdp-active-streaming {
             type int32;
             description "Active contexts, traffic class streaming";
           }
           leaf pdp-active-interactive {
             type int32;
             description "Active contexts, traffic class interactive";
           }
           leaf pdp-active-background {
             type int32;
             description "Active contexts, traffic class background";
           }
           leaf pdp-active-ipv6 {
             type int32;
             description "Number of active IPv6 PDP contexts";
           }
           leaf pdp-blocked {
             type int32;
             description "Number of PDP context creates denied due to administrative block";
           }
           leaf pdp-apn-by-logical-apn-selection {
             type int32;
             description "Number of times this APN was the result of a logical APN user selection";
           }
           leaf pdp-apn-by-logical-apn-default {
             type int32;
             description "Number of times this APN was the result of a logical APN default selection";
           }
           leaf pdp-assigned-msisdn {
             type int32;
             description "Number of assigned MSISDNs";
           }
           leaf pdp-assigned-shared-msisdn {
             type int32;
             description "Number of assigned shared MSISDNs";
           }
           leaf pdp-attempted-activation {
             type int32;
             description "Number of attempted PDP activations";
           }
           leaf pdp-completed-activation {
             type int32;
             description "Number of successfully completed PDP activations";
           }
           leaf pdp-attempted-activation-ipv6 {
             type int32;
             description "Number of attempted IPv6 PDP activations";
           }
           leaf pdp-completed-activation-ipv6 {
             type int32;
             description "Number of successfully completed IPv6 PDP activations";
           }
           leaf pdp-attempted-activation-dhcp {
             type int32;
             description "Number of attempted PDP activations with DHCP address";
           }
           leaf pdp-completed-activation-dhcp {
             type int32;
             description "Number of completed PDP activations with DHCP address";
           }
           leaf pdp-attempted-activation-radius {
             type int32;
             description "Number of attempted PDP activations with RADIUS address";
           }
           leaf pdp-completed-activation-radius {
             type int32;
             description "Number of completed PDP activations with RADIUS address";
           }
           leaf pdp-attempted-activation-local-pool {
             type int32;
             description "Number of attempted PDP activations with local pool address";
           }
           leaf pdp-completed-activation-local-pool {
             type int32;
             description "Number of completed PDP activations with local pool address";
           }
           leaf pdp-attempted-activation-dynamic {
             type int32;
             description "Number of attempted PDP activations with dynamic address";
           }
           leaf pdp-completed-activation-dynamic {
             type int32;
             description "Number of completed PDP activations with dynamic address";
           }
           leaf pdp-attempted-mobile-activation {
             type int32;
             description "Number of mobile-station-initiated PDP context activations attempted";
           }
           leaf pdp-completed-mobile-activation {
             type int32;
             description "Number of mobile-station-initiated PDP context activations completed";
           }
           leaf pdp-attempted-authentication-activation {
             type int32;
             description "Number of PDP context activations attempted with user authentication required";
           }
           leaf pdp-completed-authentication-activation {
             type int32;
             description "Number of PDP context activations completed with user authentication required";
           }
           leaf pdp-attempted-mobile-sgsn-update {
             type int32;
             description "Number of mobile station or SGSN initiated PDP context updates attempted";
           }
           leaf pdp-completed-mobile-sgsn-update {
             type int32;
             description "Number of mobile station or SGSN initiated PDP context updates completed";
           }
           leaf pdp-attempted-deactivation {
             type int32;
             description "Number of attempted PDP context deactivations";
           }
           leaf pdp-completed-deactivation {
             type int32;
             description "Number of completed PDP context deactivations";
           }
           leaf pdp-attempted-node-deactivation {
             type int32;
             description "Number of GGSN-initiated PDP context deactivations attempted";
           }
           leaf pdp-completed-node-deactivation {
             type int32;
             description "Number of GGSN-initiated PDP context deactivations completed";
           }
           leaf pdp-completed-idle-deactivation {
             type int32;
             description "Number of PDP context deactivations completed due to idle timeout";
           }
           leaf pdp-completed-session-deactivation {
             type int32;
             description "Number of PDP context deactivations completed due to session timeout";
           }
           leaf pdp-attempted-mobile-deactivation {
             type int32;
             description "Number of mobile-station-initiated PDP context deactivations attempted";
           }
           leaf pdp-completed-mobile-deactivation {
             type int32;
             description "Number of mobile-station-initiated PDP context deactivations completed";
           }
           leaf pdp-created {
             type int32;
             description "Total number of PDP contexts successfully created";
           }
           leaf pdp-create-failed {
             type int32;
             description "Total number of PDP context creation failures";
           }
           leaf pdp-created-ipv6 {
             type int32;
             description "Total number of IPv6 PDP contexts successfully created";
           }
           leaf pdp-create-failed-ipv6 {
             type int32;
             description "Total number of IPv6 PDP context creation failures";
           }
           leaf pdp-secondary-created {
             type int32;
             description "Total number of secondary PDP contexts successfully created";
           }
           leaf pdp-secondary-create-failed {
             type int32;
             description "Total number of secondary PDP context creation failures";
           }
           leaf pdp-secondary-created-ipv6 {
             type int32;
             description "Total number of IPv6 secondary PDP contexts successfully created";
           }
           leaf pdp-secondary-create-failed-ipv6 {
             type int32;
             description "Total number of IPv6 secondary PDP context creation failures";
           }
           leaf pdp-secondary-attempted-ipv6 {
             type int32;
             description "Total number of attempted IPv6 secondary PDP context activations";
           }
           leaf pdp-secondary-completed-ipv6 {
             type int32;
             description "Total number of successful IPv6 secondary PDP context activations";
           }
           leaf pdp-last-create {
             type string;
             description "Time when the last PDP context was created";
           }
           leaf pdp-updates {
             type int32;
             description "Total number of successful PDP context updates";
           }
           leaf pdp-update-failed {
             type int32;
             description "Total number of failed PDP context updates";
           }
           leaf pdp-deleted {
             type int32;
             description "Total number of PDP contexts deleted";
           }
           leaf pdp-delete-failed {
             type int32;
             description "Total number of failed requests for deletion of a PDP context";
           }
           leaf pdp-last-delete {
             type string;
             description "Time when the last PDP context was deleted";
           }
           leaf pdp-deleted-by-idle-supervision {
             type int32;
             description "PDP delete requests initiated by the idle supervision function";
           }
           leaf pdp-deleted-by-session-supervision {
             type int32;
             description "PDP delete requests initiated by the session supervision function";
           }
           leaf pdp-deleted-by-command {
             type int32;
             description "PDP delete requests initiated by a node administrator";
           }
           leaf pdp-deleted-by-failure {
             type int32;
             description "PDP deletions due to system or path failure";
           }
           leaf pdp-maximum {
             type int32;
             description "Maximum PDP contexts for measured period";
           }
           leaf pdp-mean {
             type int32;
             description "Average number of PDP contexts for measured period";
           }
           leaf pdp-successful-deactivations {
             type int32;
             description "Count of successfully deactivated PDP contexts";
           }
           leaf pdp-failed-deactivations {
             type int32;
             description "Count of failed PDP context deactivations";
           }
           leaf pdp-active-l2tp-tunnels {
             type int32;
             description "Number of active L2TP tunnels";
           }
           leaf pdp-maximum-active-l2tp-tunnels {
             type int32;
             description "Maximum number of active L2TP tunnels since restart";
           }
           leaf pdp-active-l2tp-sessions {
             type int32;
             description "Number of active L2TP sessions";
           }
           leaf pdp-maximum-active-l2tp-sessions {
             type int32;
             description "Maximum number of active L2TP sessions since restart";
           }
           leaf ims-dedicated-completed-activation {
             type int32;
             description "Successful dedicated signaling PDP ctx activations";
           }
           leaf ims-dedicated-failed-activation {
             type int32;
             description "Failed dedicated signaling PDP ctx activations, APN OFF";
           }
           leaf ims-general-completed-activation {
             type int32;
             description "Successful general purpose PDP ctx activations";
           }
           leaf ims-general-failed-activation {
             type int32;
             description "Failed general purpose PDP ctx activations, APN OFF";
           }
           leaf ims-general-active-failed-activation {
             type int32;
             description "Failed general purpose PDP ctx, normal ctx is created";
           }
           leaf ims-signalling-packets-drops {
             type int32;
             description "Dropped unauthorized IMS signaling packets";
           }
           leaf pdp-minimum {
             type int32;
             description "Minimum PDP contexts for measured period";
           }
         }
         container interface-pdp-context-statistics-information {
           container interface-pdp-context-statistics {
             description "Interface-level PDP context statistics";
             leaf service-interface {
               type string;
               description "Service interface for the information";
             }
             container pdp-context-statistics {
               description "Information about PDP context events";
               leaf pdp-active {
                 type int32;
                 description "Number of active PDP contexts";
               }
               leaf pdp-active-ipv6 {
                 type int32;
                 description "Number of active IPv6 PDP contexts";
               }
               leaf pdp-created {
                 type int32;
                 description "Total number of PDP contexts successfully created";
               }
               leaf pdp-create-failed {
                 type int32;
                 description "Total number of PDP context creation failures";
               }
               leaf pdp-secondary-created {
                 type int32;
                 description "Total number of secondary PDP contexts successfully created";
               }
               leaf pdp-secondary-create-failed {
                 type int32;
                 description "Total number of secondary PDP context creation failures";
               }
               leaf pdp-secondary-attempted-ipv6 {
                 type int32;
                 description "Total number of attempted IPv6 secondary PDP context activations";
               }
               leaf pdp-secondary-completed-ipv6 {
                 type int32;
                 description "Total number of successful IPv6 secondary PDP context activations";
               }
               leaf pdp-last-create {
                 type string;
                 description "Time when the last PDP context was created";
               }
               leaf pdp-updates {
                 type int32;
                 description "Total number of successful PDP context updates";
               }
               leaf pdp-update-failed {
                 type int32;
                 description "Total number of failed PDP context updates";
               }
               leaf pdp-deleted {
                 type int32;
                 description "Total number of PDP contexts deleted";
               }
               leaf pdp-delete-failed {
                 type int32;
                 description "Total number of failed requests for deletion of a PDP context";
               }
               leaf pdp-last-delete {
                 type string;
                 description "Time when the last PDP context was deleted";
               }
               leaf pdp-maximum {
                 type int32;
                 description "Maximum PDP contexts for measured period";
               }
               leaf pdp-mean {
                 type int32;
                 description "Average number of PDP contexts for measured period";
               }
               leaf pdp-minimum {
                 type int32;
                 description "Minimum PDP contexts for measured period";
               }
             }
           }
         }
         container uplink {
           description "Link traffic in the uplink direction";
           leaf packets {
             type int32;
             description "Count of packets";
           }
           leaf packets-ipv6 {
             type int32;
             description "Count of packets for IPv6";
           }
           leaf bytes {
             type int32;
             description "Count of bytes";
           }
           leaf bytes-ipv6 {
             type int32;
             description "Count of bytes for IPv6";
           }
           leaf dropped-packets {
             type int32;
             description "Count of packet drops";
           }
           leaf dropped-packets-ipv6 {
             type int32;
             description "Count of packet drops for IPv6";
           }
           leaf dropped-bytes {
             type int32;
             description "Count of packet dropped bytes";
           }
           leaf dropped-bytes-ipv6 {
             type int32;
             description "Count of packet dropped bytes for IPv6";
           }
         }
         container downlink {
           description "Link traffic in the downlink direction";
           leaf packets {
             type int32;
             description "Count of packets";
           }
           leaf packets-ipv6 {
             type int32;
             description "Count of packets for IPv6";
           }
           leaf bytes {
             type int32;
             description "Count of bytes";
           }
           leaf bytes-ipv6 {
             type int32;
             description "Count of bytes for IPv6";
           }
           leaf dropped-packets {
             type int32;
             description "Count of packet drops";
           }
           leaf dropped-packets-ipv6 {
             type int32;
             description "Count of packet drops for IPv6";
           }
           leaf dropped-bytes {
             type int32;
             description "Count of packet dropped bytes";
           }
           leaf dropped-bytes-ipv6 {
             type int32;
             description "Count of packet dropped bytes for IPv6";
           }
         }
         container weighted-pdp-context-load {
           leaf weighted-pdp-context-load-in-control {
             type int32;
           }
           leaf weighted-pdp-context-load-in-payload {
             type int32;
           }
         }
         container sbcc-statistics-information {
           description "Service-based charging statistics";
           leaf prepaid-request {
             type int32;
             description "Number of application transaction towards prepaid server";
           }
           leaf rating-request {
             type int32;
             description "Number of application transaction towards policy/rate server";
           }
           leaf prepaid-user {
             type int32;
             description "Number of prepaid users";
           }
           leaf prepaid-context {
             type int32;
             description "Number of prepaid contexts";
           }
           leaf prepaid-pdp-creates-attempted {
             type int32;
             description "Number of prepaid PDP context creates attempted";
           }
           leaf prepaid-pdp-creates-failed {
             type int32;
             description "Number of prepaid PDP context create attempts that failed";
           }
           leaf pdp-initiated-deactivation {
             type int32;
             description "Number of PDP context deactivations initiated by service-based-charging";
           }
           leaf credit-start-request-attempted {
             type int32;
             description "Number of credit start requests attempted";
           }
           leaf credit-start-request-failed {
             type int32;
             description "Number of credit start requests failed";
           }
           leaf rating-initial-request-attempted {
             type int32;
             description "Number of initial rating requests attempted";
           }
           leaf rating-initial-request-failed {
             type int32;
             description "Number of initial rating requests failed";
           }
           leaf rating-update-request-attempted {
             type int32;
             description "Number of attempted rating update requests";
           }
           leaf rating-update-request-failed {
             type int32;
             description "Number of failed rating update requests";
           }
           leaf credit-update-request-attempted {
             type int32;
             description "Number of credit update requests attempted";
           }
           leaf credit-update-request-failed {
             type int32;
             description "Number of credit update requests failed";
           }
           leaf credit-stop-request-attempted {
             type int32;
             description "Number of credit stop requests attempted";
           }
           leaf credit-stop-request-failed {
             type int32;
             description "Number of credit start requests failed";
           }
           leaf external-prs-update {
             type int32;
             description "Number of externally initiated URT updates for users using PRS";
           }
           leaf external-prs-update-no-match {
             type int32;
             description "Number of external URT updates for non-existing users or users not using PRS";
           }
           leaf external-credit-update {
             type int32;
             description "Number of externally initiated credit updates for users with prepaid service";
           }
           leaf external-credit-update-no-match {
             type int32;
             description "Number of external credit updates for non-existing users or users not using prepaid service";
           }
           leaf external-update-failed {
             type int32;
             description "Number of failed external URT/credit updates";
           }
           leaf duration-time {
             type int32;
             description "Seconds measured for duration time";
           }
           leaf activation-bearer-ctrl-accept {
             type int32;
             description "QoS accepts at activation, SGSN bearer ctrl";
           }
           leaf activation-bearer-ctrl-reject {
             type int32;
             description "PDP context rejects at activation, SGSN bearer ctrl";
           }
           leaf activation-bearer-ctrl-upgrade {
             type int32;
             description "QoS upgrades at activation, SGSN bearer ctrl";
           }
           leaf activation-bearer-ctrl-downgrade {
             type int32;
             description "QoS downgrades at activation, SGSN bearer ctrl";
           }
           leaf modification-bearer-ctrl-accept {
             type int32;
             description "QoS accepts at modification, SGSN bearer ctrl";
           }
           leaf modification-bearer-ctrl-deactivate {
             type int32;
             description "PDP ctx deactivates at modification, SGSN bearer ctrl";
           }
           leaf modification-bearer-ctrl-upgrade {
             type int32;
             description "QoS upgrades at modification, SGSN bearer ctrl";
           }
           leaf modification-bearer-ctrl-downgrade {
             type int32;
             description "QoS downgrades at modification, SGSN bearer ctrl";
           }
           leaf activation-no-bearer-ctrl-accept {
             type int32;
             description "QoS accepts at activation, no SGSN bearer ctrl";
           }
           leaf activation-no-bearer-ctrl-reject {
             type int32;
             description "PDP context rejects at activation, no SGSN bearer ctrl";
           }
           leaf activation-no-bearer-ctrl-downgrade {
             type int32;
             description "QoS downgrades at activation, no SGSN bearer ctrl";
           }
           leaf modification-no-bearer-ctrl-accept {
             type int32;
             description "QoS accepts at modification, no SGSN bearer ctrl";
           }
           leaf modification-no-bearer-ctrl-deactivate {
             type int32;
             description "PDP ctx deactivates at modification, no SGSN bearer ctrl";
           }
           leaf modification-no-bearer-ctrl-downgrade {
             type int32;
             description "QoS downgrades at modification, no SGSN bearer ctrl";
           }
           container das-information {
             description "Information about diameter application systems";
             container das-statistics {
               description "Statistics for a diameter application system";
               leaf das-identifier {
                 type string;
                 description "Diameter application system identifier";
               }
               leaf request {
                 type int32;
                 description "Requests";
               }
             }
           }
           container pras-information {
             description "Information about policy rating application systems";
             container pras-statistics {
               description "Statistics for a policy rating application system";
               leaf pras-identifier {
                 type string;
                 description "Policy rating application system identifier";
               }
               leaf pras-start-request {
                 type int32;
                 description "PR-AS start requests";
               }
               leaf pras-start-request-failed {
                 type int32;
                 description "PR-AS start requests failed";
               }
               leaf pras-update-request {
                 type int32;
                 description "PR-AS update requests";
               }
               leaf pras-update-request-failed {
                 type int32;
                 description "PR-AS update requests failed";
               }
               leaf pras-stop-request {
                 type int32;
                 description "PR-AS stop requests";
               }
               leaf pras-stop-request-failed {
                 type int32;
                 description "PR-AS stop requests failed";
               }
               leaf pras-user-service-denied {
                 type int32;
                 description "PR-AS requests failed with user service denied";
               }
               leaf pras-user-unknown {
                 type int32;
                 description "PR-AS requests failed with user unknown";
               }
             }
           }
           container ccas-information {
             description "Information about credit control application systems";
             container ccas-statistics {
               description "Statistics for a credit control application system";
               leaf ccas-identifier {
                 type string;
                 description "Credit control application system identifier";
               }
               leaf ccas-start-request {
                 type int32;
                 description "CC-AS start requests";
               }
               leaf ccas-start-request-failed {
                 type int32;
                 description "CC-AS start requests failed";
               }
               leaf ccas-update-request {
                 type int32;
                 description "CC-AS update requests";
               }
               leaf ccas-update-request-failed {
                 type int32;
                 description "CC-AS update requests failed";
               }
               leaf ccas-stop-request {
                 type int32;
                 description "CC-AS stop requests";
               }
               leaf ccas-stop-request-failed {
                 type int32;
                 description "CC-AS stop requests failed";
               }
               leaf ccas-user-service-denied {
                 type int32;
                 description "CC-AS requests failed with user service denied";
               }
               leaf ccas-user-unknown {
                 type int32;
                 description "CC-AS requests failed with user unknown";
               }
               leaf ccas-authorization-failure {
                 type int32;
                 description "Failed CC-AS requests due to result code Authorization Rejected";
               }
               leaf ccas-cc-not-applicable {
                 type int32;
                 description "Credit control not applicable";
               }
             }
           }
           container service-class-information {
             description "Information about a service class";
             container service-class-statistics {
               description "Statistics for a service class";
               leaf service-class-identifier {
                 type int32;
                 description "Service class identifier";
               }
               leaf uplink-bytes {
                 type int32;
                 description "Bytes in the uplink direction";
               }
               leaf downlink-bytes {
                 type int32;
                 description "Bytes in the downlink direction";
               }
               leaf active-time {
                 type int32;
                 description "Seconds measured for active time for service class";
               }
             }
           }
           container rate-group-information {
             description "Information about a rate group";
             container rate-group-statistics {
               description "Statistics for a rate group";
               leaf rate-group-identifier {
                 type int32;
                 description "Rate group identifier";
               }
               leaf transactions-start {
                 type int32;
                 description "Start transaction events";
               }
               leaf transactions-success {
                 type int32;
                 description "Successful transaction events";
               }
             }
           }
           container authorization-discard-information {
             container authorization-discard-statistics {
               description "Statistics for authorization-based packet discards";
               leaf service-class-source {
                 type string;
                 description "Service class list source";
               }
               leaf packets {
                 type int32;
                 description "Count of packets";
               }
               leaf bytes {
                 type int32;
                 description "Count of bytes";
               }
             }
           }
         }
         container charging-statistics-information {
           description "Charging statistics";
           leaf encoded-cdrs {
             type int32;
             description "Number of encoded CDRs";
           }
           leaf failed-encoded-cdrs {
             type int32;
             description "Number of CDRs that failed encoding";
           }
           leaf generated-ftp-cdrs {
             type int32;
             description "Number of CDRs generated for FTP";
           }
           leaf generated-gtpp-cdrs {
             type int32;
             description "Number of CDRs generated for GTP prime";
           }
           leaf gtpp-log-cdrs {
             type int32;
             description "Number of GTP prime CDRs stored in the charging log";
           }
           leaf gtpp-send-attempted-cdrs {
             type int32;
             description "Number of CDRs attempted to be sent for GTP prime";
           }
           leaf gtpp-send-failed-cdrs {
             type int32;
             description "Number of CDRs failed to be sent for GTP prime";
           }
         }
         container radius-statistics-information {
           description "Radius statistics";
           leaf radius-authentication-failure {
             type int32;
             description "Number of failed RADIUS Authentication procedures";
           }
           leaf accounting-failure {
             type int32;
             description "Number of failed RADIUS Accounting procedures";
           }
         }
       }
     }
   }
   rpc get-ggsn-gtp-statistics-information {
     description "Show GPRS tunneling protocol statistics";
     output {
       container gtp-statistics-information {
         container gtp-statistics {
           description "GTP statistics information";
           leaf service-interface {
             type string;
             description "Service interface for the information";
           }
           leaf uplink-packets {
             type int32;
             description "Packets in the uplink direction";
           }
           leaf uplink-bytes {
             type int32;
             description "Bytes in the uplink direction";
           }
           leaf downlink-packets {
             type int32;
             description "Packets in the downlink direction";
           }
           leaf downlink-bytes {
             type int32;
             description "Bytes in the downlink direction";
           }
           leaf dropped-packets {
             type int32;
             description "Count of packet drops";
           }
           leaf active-tunnels {
             type int32;
             description "Number of currently active tunnels";
           }
           leaf created-tunnels {
             type int32;
             description "Total number of created tunnels since last node controller restart";
           }
           container echo-request-statistics {
             description "Echo request information";
             leaf request-received {
               type int32;
               description "Requests received";
             }
             leaf request-transmitted {
               type int32;
               description "Requests sent";
             }
             leaf response-received {
               type int32;
               description "Responses received";
             }
             leaf response-transmitted {
               type int32;
               description "Responses sent";
             }
           }
           container version-unsupported-statistics {
             description "Version unsupported message information";
             leaf version-unsupported-received {
               type int32;
               description "Unsupported version messages received";
             }
             leaf version-unsupported-transmitted {
               type int32;
               description "Unsupported version messages sent";
             }
           }
           container pdp-request-statistics {
             description "PDP context request statistics";
             leaf create-request-received {
               type int32;
               description "GTP PDP create requests received";
             }
             leaf create-response-transmitted {
               type int32;
               description "GTP PDP create responses sent";
             }
             leaf update-request-received {
               type int32;
               description "GTP PDP update requests received";
             }
             leaf update-request-transmitted {
               type int32;
               description "GTP PDP update requests sent";
             }
             leaf update-response-received {
               type int32;
               description "GTP PDP update responses received";
             }
             leaf update-response-transmitted {
               type int32;
               description "GTP PDP update responses sent";
             }
             leaf delete-request-received {
               type int32;
               description "GTP PDP delete requests received";
             }
             leaf delete-request-transmitted {
               type int32;
               description "GTP PDP delete requests sent";
             }
             leaf delete-response-received {
               type int32;
               description "GTP PDP delete responses received";
             }
             leaf delete-response-transmitted {
               type int32;
               description "GTP PDP delete responses sent";
             }
           }
           container gtp-error-statistics {
             description "GTP error statistics";
             leaf request-accepted {
               type int32;
               description "Requests that were accepted";
             }
             leaf error-indication-received {
               type int32;
               description "Error indications received";
             }
             leaf error-indication-transmitted {
               type int32;
               description "Error indications sent";
             }
             leaf error-version-unsupported {
               type int32;
               description "Failed with error: version unsupported";
             }
             leaf error-invalid-request-format {
               type int32;
               description "Failed with error: invalid message format";
             }
             leaf error-invalid-request-format-when-update {
               type int32;
               description "PDP context update failed with error: invalid message format";
             }
             leaf error-invalid-request-format-when-delete {
               type int32;
               description "PDP context delete failed with error: invalid message format";
             }
             leaf error-no-resources {
               type int32;
               description "Failed with error: no resources";
             }
             leaf error-no-dynamic-address-available {
               type int32;
               description "Failed with error: no dynamic address available";
             }
             leaf error-no-memory {
               type int32;
               description "Failed with error: no memory";
             }
             leaf error-unknown-apn {
               type int32;
               description "Failed with error: unknown APN";
             }
             leaf error-unknown-pdp-address-or-type {
               type int32;
               description "Failed with error: unknown PDP address or type";
             }
             leaf error-authentication-failed {
               type int32;
               description "Failed with error: authentication failed";
             }
             leaf error-system-failure {
               type int32;
               description "Failed with error: system failure";
             }
             leaf error-system-failure-when-update {
               type int32;
               description "PDP context update failed with error: system failure";
             }
             leaf error-tft-error-semantic {
               type int32;
               description "Failed with error: TFT semantic error";
             }
             leaf error-tft-error-semantic-when-update {
               type int32;
               description "PDP context update failed with error: TFT semantic error";
             }
             leaf error-tft-error-syntax {
               type int32;
               description "Failed with error: TFT syntax error";
             }
             leaf error-tft-error-syntax-when-update {
               type int32;
               description "PDP context failed with error: TFT syntax error";
             }
             leaf error-packet-filter-semantic {
               type int32;
               description "Failed with error: packet filtering semantic error";
             }
             leaf error-packet-filter-semantic-when-update {
               type int32;
               description "PDP context update failed with error: packet filtering semantic error";
             }
             leaf error-packet-filter-syntax {
               type int32;
               description "Failed with error: packet filtering syntax error";
             }
             leaf error-packet-filter-syntax-when-update {
               type int32;
               description "PDP context update failed with error: packet filtering syntax error";
             }
             leaf error-mandatory-ie-missing {
               type int32;
               description "Failed with error: mandatory information element missing";
             }
             leaf error-mandatory-ie-missing-when-update {
               type int32;
               description "PDP context update failed with error: mandatory information element missing";
             }
             leaf error-mandatory-ie-missing-when-delete {
               type int32;
               description "PDP context delete failed with error: mandatory information element missing";
             }
             leaf error-mandatory-ie-invalid {
               type int32;
               description "Failed with error: mandatory information element invalid";
             }
             leaf error-mandatory-ie-invalid-when-update {
               type int32;
               description "PDP context update failed with error: mandatory information element invalid";
             }
             leaf error-mandatory-ie-invalid-when-delete {
               type int32;
               description "PDP context update failed with error: mandatory information element invalid";
             }
             leaf error-optional-ie-invalid {
               type int32;
               description "Failed with error: optional information element invalid";
             }
             leaf error-optional-ie-invalid-when-update {
               type int32;
               description "PDP context update failed with error: optional information element invalid";
             }
             leaf error-optional-ie-invalid-when-delete {
               type int32;
               description "PDP context delete failed with error: optional information element invalid";
             }
             leaf error-reference-invalid {
               type int32;
               description "Failed with error: invalid reference";
             }
             leaf error-reference-invalid-when-update {
               type int32;
               description "PDP context update failed with error: invalid reference";
             }
             leaf error-reference-invalid-when-delete {
               type int32;
               description "PDP context delete failed with error: invalid reference";
             }
             leaf error-service-unsupported {
               type int32;
               description "Failed with error: service unsupported";
             }
             leaf error-already-activated {
               type int32;
               description "PDP context create failed with error: already activated";
             }
             leaf error-access-denied {
               type int32;
               description "PDP context create failed with error: Access denied";
             }
           }
         }
       }
     }
   }
   rpc get-ggsn-charging-statistics-information {
     description "Show charging statistics";
   }
   rpc get-ggsn-radius-statistics-information {
     description "Show RADIUS statistics";
   }
   rpc get-ggsn-gtp-prime-statistics-information {
     description "Show GPRS Tunneling Protocol Prime statistics";
     output {
       container gtp-prime-statistics-information {
         container billing-gateway {
           description "Active billing gateway information";
           leaf address {
             type ipaddr;
           }
           leaf time-connected {
             type string;
             description "Time at which a connection was made to a server";
           }
         }
         container gtp-prime-statistics {
           description "GTP Prime statistics information";
           leaf service-interface {
             type string;
             description "Service interface for the information";
           }
           container echo-request-statistics {
             description "Echo request information";
             leaf request-received {
               type int32;
               description "Requests received";
             }
             leaf request-transmitted {
               type int32;
               description "Requests sent";
             }
             leaf response-received {
               type int32;
               description "Responses received";
             }
             leaf response-transmitted {
               type int32;
               description "Responses sent";
             }
           }
           container version-unsupported-statistics {
             description "Version unsupported message information";
             leaf version-unsupported-received {
               type int32;
               description "Unsupported version messages received";
             }
             leaf version-unsupported-transmitted {
               type int32;
               description "Unsupported version messages sent";
             }
           }
           container node-alive-request-statistics {
             description "GTP Prime node alive request statistics";
             leaf request-received {
               type int32;
               description "Requests received";
             }
             leaf request-transmitted {
               type int32;
               description "Requests sent";
             }
             leaf response-received {
               type int32;
               description "Responses received";
             }
             leaf response-transmitted {
               type int32;
               description "Responses sent";
             }
           }
           container redirection-request-statistics {
             description "GTP Prime redirection request statistics";
             leaf request-received {
               type int32;
               description "Requests received";
             }
             leaf request-transmitted {
               type int32;
               description "Requests sent";
             }
             leaf response-received {
               type int32;
               description "Responses received";
             }
             leaf response-transmitted {
               type int32;
               description "Responses sent";
             }
           }
           container data-record-transfer-statistics {
             description "GTP Prime data record transfer statistics";
             leaf request-transmitted {
               type int32;
               description "Requests sent";
             }
             leaf response-received {
               type int32;
               description "Responses received";
             }
             leaf request-accepted {
               type int32;
               description "Requests that were accepted";
             }
             leaf send-data-record-packet {
               type int32;
               description "Number of data transfer request send data record packets sent";
             }
             leaf error-no-resources {
               type int32;
               description "Failed with error: no resources";
             }
             leaf error-service-unsupported {
               type int32;
               description "Failed with error: service unsupported";
             }
             leaf error-system-failure {
               type int32;
               description "Failed with error: system failure";
             }
             leaf error-invalid-request-format {
               type int32;
               description "Failed with error: invalid message format";
             }
             leaf error-version-unsupported {
               type int32;
               description "Failed with error: version unsupported";
             }
             leaf error-request-unfulfilled {
               type int32;
               description "Failed with error: request unfulfilled";
             }
             leaf error-decoding-error {
               type int32;
               description "Failed with error: decoding error";
             }
             leaf error-already-fulfilled {
               type int32;
               description "Failed with error: already fulfilled";
             }
             leaf error-duplicate-packet-fulfilled {
               type int32;
               description "Failed with error: duplicate packet fulfilled";
             }
           }
           container gtp-prime-error-statistics {
             description "GTP Prime error statistics";
             leaf error-mandatory-ie-missing {
               type int32;
               description "Failed with error: mandatory information element missing";
             }
             leaf error-mandatory-ie-invalid {
               type int32;
               description "Failed with error: mandatory information element invalid";
             }
             leaf error-optional-ie-invalid {
               type int32;
               description "Failed with error: optional information element invalid";
             }
             leaf error-reference-invalid {
               type int32;
               description "Failed with error: invalid reference";
             }
           }
         }
       }
     }
   }
   rpc get-ggsn-imsi-user-information {
     description "Show International Mobile Subscriber Identity statistics";
     input {
       leaf imsi-identifier {
         description "Identifier for IMSI";
         type string {
           junos:posix-pattern "^[0-9]{5,15}$";
           junos:pattern-message "IMSI must be 5 to 15 digits.";
         }
         mandatory true;
       }
     }
     output {
       container mobile-user-information {
         container mobile-user {
           description "Information about a mobile user";
           leaf imsi {
             type string;
             description "International Mobile Subscriber Identity for user";
           }
           leaf msisdn {
             type string;
             description "Mobile Station Integrated Services Digital Network number for user";
           }
           container pdp-context-information {
             description "List of PDP contexts associated with the user";
             container pdp-context {
               description "Information relating to an MT/MS PDP context";
               leaf nsapi {
                 type int32;
                 description "Network Service Access Point Identifier for user";
               }
               leaf nsapi-linked {
                 type int32;
                 description "NSAPI of associated primary context";
               }
               leaf apn-name {
                 type string;
                 description "APN for this context";
               }
               leaf sgsn-address {
                 type ipaddr;
                 description "SGSN for this context";
               }
               leaf address {
                 type ipaddr;
               }
               leaf charging-identifier {
                 type string;
                 description "Charging identifier associated with the user";
               }
               container quality-of-service {
                 description "PDP context quality-of-service information";
                 leaf gi-diffserv-code-point {
                   type string;
                   description "Gi DiffServ class";
                 }
                 leaf gn-diffserv-code-point {
                   type string;
                   description "Gn DiffServ class";
                 }
                 leaf downlink-bitrate {
                   type string;
                   description "Downlink bit rate";
                 }
               }
               container traffic-flow-template-information {
                 description "Traffic flow templates (TFTs)";
                 container traffic-flow-template {
                   description "TFT information";
                   container packet-filter-information {
                     description "Filters for this TFT";
                     container packet-filter {
                       leaf evaluation-precedence {
                         type int32;
                         description "Evaluation precedence for PDP context packets";
                       }
                       leaf source-address {
                         type ipaddr;
                       }
                       leaf source-mask {
                         type ipaddr;
                       }
                       leaf source-port-range {
                         type string;
                         description "Source port range";
                       }
                       leaf destination-port-range {
                         type string;
                         description "Destination port range";
                       }
                       leaf diffserv-code-point {
                         type string;
                       }
                       leaf flow-label {
                         type string;
                       }
                       leaf spi {
                         type string;
                         description "IPSec security parameters index";
                       }
                       leaf protocol {
                         type string;
                         description "Protocol for this filter";
                       }
                     }
                   }
                 }
               }
             }
           }
         }
       }
     }
   }
   rpc get-ggsn-apn-statistics-information {
     description "Show access point name statistics";
     input {
       leaf apn-name {
         description "Name of APN";
         type string;
       }
     }
     output {
       container apn-statistics-information {
         container apn-statistics {
           description "Statistics for a single APN";
           leaf name {
             type string;
           }
           leaf tft-filter-count {
             type int32;
             description "Number of traffic flow template filters in use";
           }
           leaf neighbor-solicitation-req-received {
             type int32;
             description "Number of IPv6 ND neighbor solicitation requests received by U";
           }
           leaf neighbor-solicitation-req-responded {
             type int32;
             description "Number of IPv6 ND neighbor solicitation responses sent by U";
           }
           leaf router-solicitation-req-received {
             type int32;
             description "Number of IPv6 ND router solicitation requests received by U";
           }
           leaf router-solicitation-req-responded {
             type int32;
             description "Number of IPv6 ND router solicitation responses sent by U";
           }
           container pdp-context-statistics {
             description "Information about PDP context events";
             leaf pdp-active {
               type int32;
               description "Number of active PDP contexts";
             }
             leaf pdp-active-msisdn {
               type int32;
               description "Number of active MSISDNs";
             }
             leaf pdp-active-imsi {
               type int32;
               description "Number of active IMSIs";
             }
             leaf pdp-active-conversational {
               type int32;
               description "Active contexts, traffic class conversational";
             }
             leaf pdp-active-streaming {
               type int32;
               description "Active contexts, traffic class streaming";
             }
             leaf pdp-active-interactive {
               type int32;
               description "Active contexts, traffic class interactive";
             }
             leaf pdp-active-background {
               type int32;
               description "Active contexts, traffic class background";
             }
             leaf pdp-active-ipv6 {
               type int32;
               description "Number of active IPv6 PDP contexts";
             }
             leaf pdp-blocked {
               type int32;
               description "Number of PDP context creates denied due to administrative block";
             }
             leaf pdp-apn-by-logical-apn-selection {
               type int32;
               description "Number of times this APN was the result of a logical APN user selection";
             }
             leaf pdp-apn-by-logical-apn-default {
               type int32;
               description "Number of times this APN was the result of a logical APN default selection";
             }
             leaf pdp-assigned-msisdn {
               type int32;
               description "Number of assigned MSISDNs";
             }
             leaf pdp-assigned-shared-msisdn {
               type int32;
               description "Number of assigned shared MSISDNs";
             }
             leaf pdp-attempted-activation {
               type int32;
               description "Number of attempted PDP activations";
             }
             leaf pdp-completed-activation {
               type int32;
               description "Number of successfully completed PDP activations";
             }
             leaf pdp-attempted-activation-ipv6 {
               type int32;
               description "Number of attempted IPv6 PDP activations";
             }
             leaf pdp-completed-activation-ipv6 {
               type int32;
               description "Number of successfully completed IPv6 PDP activations";
             }
             leaf pdp-attempted-activation-dhcp {
               type int32;
               description "Number of attempted PDP activations with DHCP address";
             }
             leaf pdp-completed-activation-dhcp {
               type int32;
               description "Number of completed PDP activations with DHCP address";
             }
             leaf pdp-attempted-activation-radius {
               type int32;
               description "Number of attempted PDP activations with RADIUS address";
             }
             leaf pdp-completed-activation-radius {
               type int32;
               description "Number of completed PDP activations with RADIUS address";
             }
             leaf pdp-attempted-activation-local-pool {
               type int32;
               description "Number of attempted PDP activations with local pool address";
             }
             leaf pdp-completed-activation-local-pool {
               type int32;
               description "Number of completed PDP activations with local pool address";
             }
             leaf pdp-attempted-activation-dynamic {
               type int32;
               description "Number of attempted PDP activations with dynamic address";
             }
             leaf pdp-completed-activation-dynamic {
               type int32;
               description "Number of completed PDP activations with dynamic address";
             }
             leaf pdp-attempted-mobile-activation {
               type int32;
               description "Number of mobile-station-initiated PDP context activations attempted";
             }
             leaf pdp-completed-mobile-activation {
               type int32;
               description "Number of mobile-station-initiated PDP context activations completed";
             }
             leaf pdp-attempted-authentication-activation {
               type int32;
               description "Number of PDP context activations attempted with user authentication required";
             }
             leaf pdp-completed-authentication-activation {
               type int32;
               description "Number of PDP context activations completed with user authentication required";
             }
             leaf pdp-attempted-mobile-sgsn-update {
               type int32;
               description "Number of mobile station or SGSN initiated PDP context updates attempted";
             }
             leaf pdp-completed-mobile-sgsn-update {
               type int32;
               description "Number of mobile station or SGSN initiated PDP context updates completed";
             }
             leaf pdp-attempted-deactivation {
               type int32;
               description "Number of attempted PDP context deactivations";
             }
             leaf pdp-completed-deactivation {
               type int32;
               description "Number of completed PDP context deactivations";
             }
             leaf pdp-attempted-node-deactivation {
               type int32;
               description "Number of GGSN-initiated PDP context deactivations attempted";
             }
             leaf pdp-completed-node-deactivation {
               type int32;
               description "Number of GGSN-initiated PDP context deactivations completed";
             }
             leaf pdp-completed-idle-deactivation {
               type int32;
               description "Number of PDP context deactivations completed due to idle timeout";
             }
             leaf pdp-completed-session-deactivation {
               type int32;
               description "Number of PDP context deactivations completed due to session timeout";
             }
             leaf pdp-attempted-mobile-deactivation {
               type int32;
               description "Number of mobile-station-initiated PDP context deactivations attempted";
             }
             leaf pdp-completed-mobile-deactivation {
               type int32;
               description "Number of mobile-station-initiated PDP context deactivations completed";
             }
             leaf pdp-created {
               type int32;
               description "Total number of PDP contexts successfully created";
             }
             leaf pdp-create-failed {
               type int32;
               description "Total number of PDP context creation failures";
             }
             leaf pdp-created-ipv6 {
               type int32;
               description "Total number of IPv6 PDP contexts successfully created";
             }
             leaf pdp-create-failed-ipv6 {
               type int32;
               description "Total number of IPv6 PDP context creation failures";
             }
             leaf pdp-secondary-created {
               type int32;
               description "Total number of secondary PDP contexts successfully created";
             }
             leaf pdp-secondary-create-failed {
               type int32;
               description "Total number of secondary PDP context creation failures";
             }
             leaf pdp-secondary-created-ipv6 {
               type int32;
               description "Total number of IPv6 secondary PDP contexts successfully created";
             }
             leaf pdp-secondary-create-failed-ipv6 {
               type int32;
               description "Total number of IPv6 secondary PDP context creation failures";
             }
             leaf pdp-secondary-attempted-ipv6 {
               type int32;
               description "Total number of attempted IPv6 secondary PDP context activations";
             }
             leaf pdp-secondary-completed-ipv6 {
               type int32;
               description "Total number of successful IPv6 secondary PDP context activations";
             }
             leaf pdp-last-create {
               type string;
               description "Time when the last PDP context was created";
             }
             leaf pdp-updates {
               type int32;
               description "Total number of successful PDP context updates";
             }
             leaf pdp-update-failed {
               type int32;
               description "Total number of failed PDP context updates";
             }
             leaf pdp-deleted {
               type int32;
               description "Total number of PDP contexts deleted";
             }
             leaf pdp-delete-failed {
               type int32;
               description "Total number of failed requests for deletion of a PDP context";
             }
             leaf pdp-last-delete {
               type string;
               description "Time when the last PDP context was deleted";
             }
             leaf pdp-deleted-by-idle-supervision {
               type int32;
               description "PDP delete requests initiated by the idle supervision function";
             }
             leaf pdp-deleted-by-session-supervision {
               type int32;
               description "PDP delete requests initiated by the session supervision function";
             }
             leaf pdp-deleted-by-command {
               type int32;
               description "PDP delete requests initiated by a node administrator";
             }
             leaf pdp-deleted-by-failure {
               type int32;
               description "PDP deletions due to system or path failure";
             }
             leaf pdp-maximum {
               type int32;
               description "Maximum PDP contexts for measured period";
             }
             leaf pdp-mean {
               type int32;
               description "Average number of PDP contexts for measured period";
             }
             leaf pdp-successful-deactivations {
               type int32;
               description "Count of successfully deactivated PDP contexts";
             }
             leaf pdp-failed-deactivations {
               type int32;
               description "Count of failed PDP context deactivations";
             }
             leaf pdp-active-l2tp-tunnels {
               type int32;
               description "Number of active L2TP tunnels";
             }
             leaf pdp-maximum-active-l2tp-tunnels {
               type int32;
               description "Maximum number of active L2TP tunnels since restart";
             }
             leaf pdp-active-l2tp-sessions {
               type int32;
               description "Number of active L2TP sessions";
             }
             leaf pdp-maximum-active-l2tp-sessions {
               type int32;
               description "Maximum number of active L2TP sessions since restart";
             }
             leaf ims-dedicated-completed-activation {
               type int32;
               description "Successful dedicated signaling PDP ctx activations";
             }
             leaf ims-dedicated-failed-activation {
               type int32;
               description "Failed dedicated signaling PDP ctx activations, APN OFF";
             }
             leaf ims-general-completed-activation {
               type int32;
               description "Successful general purpose PDP ctx activations";
             }
             leaf ims-general-failed-activation {
               type int32;
               description "Failed general purpose PDP ctx activations, APN OFF";
             }
             leaf ims-general-active-failed-activation {
               type int32;
               description "Failed general purpose PDP ctx, normal ctx is created";
             }
             leaf ims-signalling-packets-drops {
               type int32;
               description "Dropped unauthorized IMS signaling packets";
             }
             leaf pdp-minimum {
               type int32;
               description "Minimum PDP contexts for measured period";
             }
           }
           container gtp-error-statistics {
             description "GTP error statistics";
           }
           container uplink {
             description "Link traffic in the uplink direction";
             leaf packets {
               type int32;
               description "Count of packets";
             }
             leaf packets-ipv6 {
               type int32;
               description "Count of packets for IPv6";
             }
             leaf bytes {
               type int32;
               description "Count of bytes";
             }
             leaf bytes-ipv6 {
               type int32;
               description "Count of bytes for IPv6";
             }
             leaf dropped-packets {
               type int32;
               description "Count of packet drops";
             }
             leaf dropped-packets-ipv6 {
               type int32;
               description "Count of packet drops for IPv6";
             }
             leaf dropped-bytes {
               type int32;
               description "Count of packet dropped bytes";
             }
             leaf dropped-bytes-ipv6 {
               type int32;
               description "Count of packet dropped bytes for IPv6";
             }
           }
           container downlink {
             description "Link traffic in the downlink direction";
             leaf packets {
               type int32;
               description "Count of packets";
             }
             leaf packets-ipv6 {
               type int32;
               description "Count of packets for IPv6";
             }
             leaf bytes {
               type int32;
               description "Count of bytes";
             }
             leaf bytes-ipv6 {
               type int32;
               description "Count of bytes for IPv6";
             }
             leaf dropped-packets {
               type int32;
               description "Count of packet drops";
             }
             leaf dropped-packets-ipv6 {
               type int32;
               description "Count of packet drops for IPv6";
             }
             leaf dropped-bytes {
               type int32;
               description "Count of packet dropped bytes";
             }
             leaf dropped-bytes-ipv6 {
               type int32;
               description "Count of packet dropped bytes for IPv6";
             }
           }
           container ggsn-pdp-per-user-category {
             description "Active PDP per user category";
             container user-category-line {
               leaf user-category {
                 type string;
                 description "User category";
               }
               leaf pdp-active {
                 type int32;
                 description "Number of active PDP contexts";
               }
             }
           }
           container radius-statistics-information {
             description "Radius statistics";
             leaf radius-authentication-failure {
               type int32;
               description "Number of failed RADIUS Authentication procedures";
             }
             leaf accounting-failure {
               type int32;
               description "Number of failed RADIUS Accounting procedures";
             }
           }
           container rulespace-based-charging-statistics {
             description "Information about rule spaces";
             container rs-statistics {
               description "Statistics for a rule space";
               leaf rs-identifier {
                 type string;
                 description "Rule space identifier";
               }
               leaf uplink-statistics {
                 type int32;
                 description "Uplink bytes identified per APN and rule space";
               }
               leaf downlink-statistics {
                 type int32;
                 description "Downlink bytes identified per APN and rule space";
               }
               leaf service-instances {
                 type int32;
                 description "Service instances identified per APN and rule space";
               }
               leaf discarded-uplink {
                 type int32;
                 description "Discarded uplink packets due to authorization based on policy and credit control";
               }
               leaf discarded-downlink {
                 type int32;
                 description "Discarded downlink packets due to authorization based on policy and credit control";
               }
               leaf gate-discarded-uplink {
                 type int32;
                 description "Discarded uplink packets due to closed gate";
               }
               leaf gate-discarded-downlink {
                 type int32;
                 description "Discarded downlink packets due to closed gate";
               }
             }
           }
           container signalling {
             description "Signaling traffic";
             container incoming {
               leaf packets {
                 type int32;
                 description "Count of packets";
               }
               leaf bytes {
                 type int32;
                 description "Count of bytes";
               }
             }
             container outgoing {
               leaf packets {
                 type int32;
                 description "Count of packets";
               }
               leaf bytes {
                 type int32;
                 description "Count of bytes";
               }
             }
           }
         }
         container sbcc-statistics-information {
           description "Service-based charging statistics";
           leaf prepaid-request {
             type int32;
             description "Number of application transaction towards prepaid server";
           }
           leaf rating-request {
             type int32;
             description "Number of application transaction towards policy/rate server";
           }
           leaf prepaid-user {
             type int32;
             description "Number of prepaid users";
           }
           leaf prepaid-context {
             type int32;
             description "Number of prepaid contexts";
           }
           leaf prepaid-pdp-creates-attempted {
             type int32;
             description "Number of prepaid PDP context creates attempted";
           }
           leaf prepaid-pdp-creates-failed {
             type int32;
             description "Number of prepaid PDP context create attempts that failed";
           }
           leaf pdp-initiated-deactivation {
             type int32;
             description "Number of PDP context deactivations initiated by service-based-charging";
           }
           leaf credit-start-request-attempted {
             type int32;
             description "Number of credit start requests attempted";
           }
           leaf credit-start-request-failed {
             type int32;
             description "Number of credit start requests failed";
           }
           leaf rating-initial-request-attempted {
             type int32;
             description "Number of initial rating requests attempted";
           }
           leaf rating-initial-request-failed {
             type int32;
             description "Number of initial rating requests failed";
           }
           leaf rating-update-request-attempted {
             type int32;
             description "Number of attempted rating update requests";
           }
           leaf rating-update-request-failed {
             type int32;
             description "Number of failed rating update requests";
           }
           leaf credit-update-request-attempted {
             type int32;
             description "Number of credit update requests attempted";
           }
           leaf credit-update-request-failed {
             type int32;
             description "Number of credit update requests failed";
           }
           leaf credit-stop-request-attempted {
             type int32;
             description "Number of credit stop requests attempted";
           }
           leaf credit-stop-request-failed {
             type int32;
             description "Number of credit start requests failed";
           }
           leaf external-prs-update {
             type int32;
             description "Number of externally initiated URT updates for users using PRS";
           }
           leaf external-prs-update-no-match {
             type int32;
             description "Number of external URT updates for non-existing users or users not using PRS";
           }
           leaf external-credit-update {
             type int32;
             description "Number of externally initiated credit updates for users with prepaid service";
           }
           leaf external-credit-update-no-match {
             type int32;
             description "Number of external credit updates for non-existing users or users not using prepaid service";
           }
           leaf external-update-failed {
             type int32;
             description "Number of failed external URT/credit updates";
           }
           leaf duration-time {
             type int32;
             description "Seconds measured for duration time";
           }
           leaf activation-bearer-ctrl-accept {
             type int32;
             description "QoS accepts at activation, SGSN bearer ctrl";
           }
           leaf activation-bearer-ctrl-reject {
             type int32;
             description "PDP context rejects at activation, SGSN bearer ctrl";
           }
           leaf activation-bearer-ctrl-upgrade {
             type int32;
             description "QoS upgrades at activation, SGSN bearer ctrl";
           }
           leaf activation-bearer-ctrl-downgrade {
             type int32;
             description "QoS downgrades at activation, SGSN bearer ctrl";
           }
           leaf modification-bearer-ctrl-accept {
             type int32;
             description "QoS accepts at modification, SGSN bearer ctrl";
           }
           leaf modification-bearer-ctrl-deactivate {
             type int32;
             description "PDP ctx deactivates at modification, SGSN bearer ctrl";
           }
           leaf modification-bearer-ctrl-upgrade {
             type int32;
             description "QoS upgrades at modification, SGSN bearer ctrl";
           }
           leaf modification-bearer-ctrl-downgrade {
             type int32;
             description "QoS downgrades at modification, SGSN bearer ctrl";
           }
           leaf activation-no-bearer-ctrl-accept {
             type int32;
             description "QoS accepts at activation, no SGSN bearer ctrl";
           }
           leaf activation-no-bearer-ctrl-reject {
             type int32;
             description "PDP context rejects at activation, no SGSN bearer ctrl";
           }
           leaf activation-no-bearer-ctrl-downgrade {
             type int32;
             description "QoS downgrades at activation, no SGSN bearer ctrl";
           }
           leaf modification-no-bearer-ctrl-accept {
             type int32;
             description "QoS accepts at modification, no SGSN bearer ctrl";
           }
           leaf modification-no-bearer-ctrl-deactivate {
             type int32;
             description "PDP ctx deactivates at modification, no SGSN bearer ctrl";
           }
           leaf modification-no-bearer-ctrl-downgrade {
             type int32;
             description "QoS downgrades at modification, no SGSN bearer ctrl";
           }
           container das-information {
             description "Information about diameter application systems";
             container das-statistics {
               description "Statistics for a diameter application system";
               leaf das-identifier {
                 type string;
                 description "Diameter application system identifier";
               }
               leaf request {
                 type int32;
                 description "Requests";
               }
             }
           }
           container pras-information {
             description "Information about policy rating application systems";
             container pras-statistics {
               description "Statistics for a policy rating application system";
               leaf pras-identifier {
                 type string;
                 description "Policy rating application system identifier";
               }
               leaf pras-start-request {
                 type int32;
                 description "PR-AS start requests";
               }
               leaf pras-start-request-failed {
                 type int32;
                 description "PR-AS start requests failed";
               }
               leaf pras-update-request {
                 type int32;
                 description "PR-AS update requests";
               }
               leaf pras-update-request-failed {
                 type int32;
                 description "PR-AS update requests failed";
               }
               leaf pras-stop-request {
                 type int32;
                 description "PR-AS stop requests";
               }
               leaf pras-stop-request-failed {
                 type int32;
                 description "PR-AS stop requests failed";
               }
               leaf pras-user-service-denied {
                 type int32;
                 description "PR-AS requests failed with user service denied";
               }
               leaf pras-user-unknown {
                 type int32;
                 description "PR-AS requests failed with user unknown";
               }
             }
           }
           container ccas-information {
             description "Information about credit control application systems";
             container ccas-statistics {
               description "Statistics for a credit control application system";
               leaf ccas-identifier {
                 type string;
                 description "Credit control application system identifier";
               }
               leaf ccas-start-request {
                 type int32;
                 description "CC-AS start requests";
               }
               leaf ccas-start-request-failed {
                 type int32;
                 description "CC-AS start requests failed";
               }
               leaf ccas-update-request {
                 type int32;
                 description "CC-AS update requests";
               }
               leaf ccas-update-request-failed {
                 type int32;
                 description "CC-AS update requests failed";
               }
               leaf ccas-stop-request {
                 type int32;
                 description "CC-AS stop requests";
               }
               leaf ccas-stop-request-failed {
                 type int32;
                 description "CC-AS stop requests failed";
               }
               leaf ccas-user-service-denied {
                 type int32;
                 description "CC-AS requests failed with user service denied";
               }
               leaf ccas-user-unknown {
                 type int32;
                 description "CC-AS requests failed with user unknown";
               }
               leaf ccas-authorization-failure {
                 type int32;
                 description "Failed CC-AS requests due to result code Authorization Rejected";
               }
               leaf ccas-cc-not-applicable {
                 type int32;
                 description "Credit control not applicable";
               }
             }
           }
           container service-class-information {
             description "Information about a service class";
             container service-class-statistics {
               description "Statistics for a service class";
               leaf service-class-identifier {
                 type int32;
                 description "Service class identifier";
               }
               leaf uplink-bytes {
                 type int32;
                 description "Bytes in the uplink direction";
               }
               leaf downlink-bytes {
                 type int32;
                 description "Bytes in the downlink direction";
               }
               leaf active-time {
                 type int32;
                 description "Seconds measured for active time for service class";
               }
             }
           }
           container rate-group-information {
             description "Information about a rate group";
             container rate-group-statistics {
               description "Statistics for a rate group";
               leaf rate-group-identifier {
                 type int32;
                 description "Rate group identifier";
               }
               leaf transactions-start {
                 type int32;
                 description "Start transaction events";
               }
               leaf transactions-success {
                 type int32;
                 description "Successful transaction events";
               }
             }
           }
           container authorization-discard-information {
             container authorization-discard-statistics {
               description "Statistics for authorization-based packet discards";
               leaf service-class-source {
                 type string;
                 description "Service class list source";
               }
               leaf packets {
                 type int32;
                 description "Count of packets";
               }
               leaf bytes {
                 type int32;
                 description "Count of bytes";
               }
             }
           }
         }
         container service-based-charging-for-gx {
           description "Service-base charging statistics for the gx interface";
           leaf dynamic-charging-rules {
             type int32;
             description "Simultaneously installed dynamic charging rules";
           }
           leaf active-predifened-charging-rules {
             type int32;
             description "Active predefined charging rules per APN";
           }
           leaf active-predifened-charging-rulbases {
             type int32;
             description "Active predefined charging rule bases per APN";
           }
           container ccr-statistics {
             description "Statistics for a credit control application system";
             leaf authorization-failure {
               type int32;
               description "Failed CC requests due to result code Authorization Rejected";
             }
             leaf authentication-failure {
               type int32;
               description "Failed CC requests due to result code Authentication Rejected";
             }
             leaf session-failure {
               type int32;
               description "Failed CC requests due to result code Unknown Session ID";
             }
             leaf ccr-identifier {
               type string;
               description "Credit control application system identifier";
             }
           }
         }
       }
     }
   }
   rpc get-ggsn-sgsn-statistics-information {
     description "Show statistics for client Serving GPRS Support Node";
     input {
       leaf address {
         description "IP address and optional prefix length of SGSN";
         type ipv4prefix;
       }
     }
     output {
       container sgsn-statistics-information {
         container sgsn-statistics {
           description "Statistics information for an SGSN";
           leaf address {
             type ipaddr;
           }
           container pdp-context-statistics {
             description "Information about PDP context events";
             leaf pdp-active {
               type int32;
               description "Number of active PDP contexts";
             }
             leaf pdp-active-msisdn {
               type int32;
               description "Number of active MSISDNs";
             }
             leaf pdp-active-imsi {
               type int32;
               description "Number of active IMSIs";
             }
             leaf pdp-active-conversational {
               type int32;
               description "Active contexts, traffic class conversational";
             }
             leaf pdp-active-streaming {
               type int32;
               description "Active contexts, traffic class streaming";
             }
             leaf pdp-active-interactive {
               type int32;
               description "Active contexts, traffic class interactive";
             }
             leaf pdp-active-background {
               type int32;
               description "Active contexts, traffic class background";
             }
             leaf pdp-active-ipv6 {
               type int32;
               description "Number of active IPv6 PDP contexts";
             }
             leaf pdp-blocked {
               type int32;
               description "Number of PDP context creates denied due to administrative block";
             }
             leaf pdp-apn-by-logical-apn-selection {
               type int32;
               description "Number of times this APN was the result of a logical APN user selection";
             }
             leaf pdp-apn-by-logical-apn-default {
               type int32;
               description "Number of times this APN was the result of a logical APN default selection";
             }
             leaf pdp-assigned-msisdn {
               type int32;
               description "Number of assigned MSISDNs";
             }
             leaf pdp-assigned-shared-msisdn {
               type int32;
               description "Number of assigned shared MSISDNs";
             }
             leaf pdp-attempted-activation {
               type int32;
               description "Number of attempted PDP activations";
             }
             leaf pdp-completed-activation {
               type int32;
               description "Number of successfully completed PDP activations";
             }
             leaf pdp-attempted-activation-ipv6 {
               type int32;
               description "Number of attempted IPv6 PDP activations";
             }
             leaf pdp-completed-activation-ipv6 {
               type int32;
               description "Number of successfully completed IPv6 PDP activations";
             }
             leaf pdp-attempted-activation-dhcp {
               type int32;
               description "Number of attempted PDP activations with DHCP address";
             }
             leaf pdp-completed-activation-dhcp {
               type int32;
               description "Number of completed PDP activations with DHCP address";
             }
             leaf pdp-attempted-activation-radius {
               type int32;
               description "Number of attempted PDP activations with RADIUS address";
             }
             leaf pdp-completed-activation-radius {
               type int32;
               description "Number of completed PDP activations with RADIUS address";
             }
             leaf pdp-attempted-activation-local-pool {
               type int32;
               description "Number of attempted PDP activations with local pool address";
             }
             leaf pdp-completed-activation-local-pool {
               type int32;
               description "Number of completed PDP activations with local pool address";
             }
             leaf pdp-attempted-activation-dynamic {
               type int32;
               description "Number of attempted PDP activations with dynamic address";
             }
             leaf pdp-completed-activation-dynamic {
               type int32;
               description "Number of completed PDP activations with dynamic address";
             }
             leaf pdp-attempted-mobile-activation {
               type int32;
               description "Number of mobile-station-initiated PDP context activations attempted";
             }
             leaf pdp-completed-mobile-activation {
               type int32;
               description "Number of mobile-station-initiated PDP context activations completed";
             }
             leaf pdp-attempted-authentication-activation {
               type int32;
               description "Number of PDP context activations attempted with user authentication required";
             }
             leaf pdp-completed-authentication-activation {
               type int32;
               description "Number of PDP context activations completed with user authentication required";
             }
             leaf pdp-attempted-mobile-sgsn-update {
               type int32;
               description "Number of mobile station or SGSN initiated PDP context updates attempted";
             }
             leaf pdp-completed-mobile-sgsn-update {
               type int32;
               description "Number of mobile station or SGSN initiated PDP context updates completed";
             }
             leaf pdp-attempted-deactivation {
               type int32;
               description "Number of attempted PDP context deactivations";
             }
             leaf pdp-completed-deactivation {
               type int32;
               description "Number of completed PDP context deactivations";
             }
             leaf pdp-attempted-node-deactivation {
               type int32;
               description "Number of GGSN-initiated PDP context deactivations attempted";
             }
             leaf pdp-completed-node-deactivation {
               type int32;
               description "Number of GGSN-initiated PDP context deactivations completed";
             }
             leaf pdp-completed-idle-deactivation {
               type int32;
               description "Number of PDP context deactivations completed due to idle timeout";
             }
             leaf pdp-completed-session-deactivation {
               type int32;
               description "Number of PDP context deactivations completed due to session timeout";
             }
             leaf pdp-attempted-mobile-deactivation {
               type int32;
               description "Number of mobile-station-initiated PDP context deactivations attempted";
             }
             leaf pdp-completed-mobile-deactivation {
               type int32;
               description "Number of mobile-station-initiated PDP context deactivations completed";
             }
             leaf pdp-created {
               type int32;
               description "Total number of PDP contexts successfully created";
             }
             leaf pdp-create-failed {
               type int32;
               description "Total number of PDP context creation failures";
             }
             leaf pdp-created-ipv6 {
               type int32;
               description "Total number of IPv6 PDP contexts successfully created";
             }
             leaf pdp-create-failed-ipv6 {
               type int32;
               description "Total number of IPv6 PDP context creation failures";
             }
             leaf pdp-secondary-created {
               type int32;
               description "Total number of secondary PDP contexts successfully created";
             }
             leaf pdp-secondary-create-failed {
               type int32;
               description "Total number of secondary PDP context creation failures";
             }
             leaf pdp-secondary-created-ipv6 {
               type int32;
               description "Total number of IPv6 secondary PDP contexts successfully created";
             }
             leaf pdp-secondary-create-failed-ipv6 {
               type int32;
               description "Total number of IPv6 secondary PDP context creation failures";
             }
             leaf pdp-secondary-attempted-ipv6 {
               type int32;
               description "Total number of attempted IPv6 secondary PDP context activations";
             }
             leaf pdp-secondary-completed-ipv6 {
               type int32;
               description "Total number of successful IPv6 secondary PDP context activations";
             }
             leaf pdp-last-create {
               type string;
               description "Time when the last PDP context was created";
             }
             leaf pdp-updates {
               type int32;
               description "Total number of successful PDP context updates";
             }
             leaf pdp-update-failed {
               type int32;
               description "Total number of failed PDP context updates";
             }
             leaf pdp-deleted {
               type int32;
               description "Total number of PDP contexts deleted";
             }
             leaf pdp-delete-failed {
               type int32;
               description "Total number of failed requests for deletion of a PDP context";
             }
             leaf pdp-last-delete {
               type string;
               description "Time when the last PDP context was deleted";
             }
             leaf pdp-deleted-by-idle-supervision {
               type int32;
               description "PDP delete requests initiated by the idle supervision function";
             }
             leaf pdp-deleted-by-session-supervision {
               type int32;
               description "PDP delete requests initiated by the session supervision function";
             }
             leaf pdp-deleted-by-command {
               type int32;
               description "PDP delete requests initiated by a node administrator";
             }
             leaf pdp-deleted-by-failure {
               type int32;
               description "PDP deletions due to system or path failure";
             }
             leaf pdp-maximum {
               type int32;
               description "Maximum PDP contexts for measured period";
             }
             leaf pdp-mean {
               type int32;
               description "Average number of PDP contexts for measured period";
             }
             leaf pdp-successful-deactivations {
               type int32;
               description "Count of successfully deactivated PDP contexts";
             }
             leaf pdp-failed-deactivations {
               type int32;
               description "Count of failed PDP context deactivations";
             }
             leaf pdp-active-l2tp-tunnels {
               type int32;
               description "Number of active L2TP tunnels";
             }
             leaf pdp-maximum-active-l2tp-tunnels {
               type int32;
               description "Maximum number of active L2TP tunnels since restart";
             }
             leaf pdp-active-l2tp-sessions {
               type int32;
               description "Number of active L2TP sessions";
             }
             leaf pdp-maximum-active-l2tp-sessions {
               type int32;
               description "Maximum number of active L2TP sessions since restart";
             }
             leaf ims-dedicated-completed-activation {
               type int32;
               description "Successful dedicated signaling PDP ctx activations";
             }
             leaf ims-dedicated-failed-activation {
               type int32;
               description "Failed dedicated signaling PDP ctx activations, APN OFF";
             }
             leaf ims-general-completed-activation {
               type int32;
               description "Successful general purpose PDP ctx activations";
             }
             leaf ims-general-failed-activation {
               type int32;
               description "Failed general purpose PDP ctx activations, APN OFF";
             }
             leaf ims-general-active-failed-activation {
               type int32;
               description "Failed general purpose PDP ctx, normal ctx is created";
             }
             leaf ims-signalling-packets-drops {
               type int32;
               description "Dropped unauthorized IMS signaling packets";
             }
             leaf pdp-minimum {
               type int32;
               description "Minimum PDP contexts for measured period";
             }
           }
           container uplink {
             description "Link traffic in the uplink direction";
             leaf packets {
               type int32;
               description "Count of packets";
             }
             leaf packets-ipv6 {
               type int32;
               description "Count of packets for IPv6";
             }
             leaf bytes {
               type int32;
               description "Count of bytes";
             }
             leaf bytes-ipv6 {
               type int32;
               description "Count of bytes for IPv6";
             }
             leaf dropped-packets {
               type int32;
               description "Count of packet drops";
             }
             leaf dropped-packets-ipv6 {
               type int32;
               description "Count of packet drops for IPv6";
             }
             leaf dropped-bytes {
               type int32;
               description "Count of packet dropped bytes";
             }
             leaf dropped-bytes-ipv6 {
               type int32;
               description "Count of packet dropped bytes for IPv6";
             }
           }
           container downlink {
             description "Link traffic in the downlink direction";
             leaf packets {
               type int32;
               description "Count of packets";
             }
             leaf packets-ipv6 {
               type int32;
               description "Count of packets for IPv6";
             }
             leaf bytes {
               type int32;
               description "Count of bytes";
             }
             leaf bytes-ipv6 {
               type int32;
               description "Count of bytes for IPv6";
             }
             leaf dropped-packets {
               type int32;
               description "Count of packet drops";
             }
             leaf dropped-packets-ipv6 {
               type int32;
               description "Count of packet drops for IPv6";
             }
             leaf dropped-bytes {
               type int32;
               description "Count of packet dropped bytes";
             }
             leaf dropped-bytes-ipv6 {
               type int32;
               description "Count of packet dropped bytes for IPv6";
             }
           }
           container gtp-error-statistics {
             description "GTP error statistics";
           }
         }
       }
     }
   }
   rpc get-ggsn-l2tp-tunnel-statistics-information {
     description "Show L2TP tunnel statistics";
     input {
       leaf lac-address {
         description "IP address of LAC";
         type ipv4addr;
       }
     }
     output {
       container l2tp-tunnel-statistics-information {
         container l2tp-tunnel-statistics {
           description "L2TP tunnel-statistics for a single tunnel";
           leaf local-tid {
             type int32;
             description "Local tunnel identifier";
           }
           leaf remote-tid {
             type int32;
             description "Remote tunnel identifier";
           }
           leaf local-ip {
             type ipaddr;
             description "Local IP this tunnel is bound to";
           }
           leaf remote-ip {
             type ipaddr;
             description "Remote IP this tunnel is bound to";
           }
           leaf active-sessions {
             type int32;
             description "Number of sessions that are currently active for this tunnel";
           }
           container l2tp-tunnel-packet-statistics {
             description "L2TP tunnel statistics";
             leaf control-tx-packets {
               type int32;
               description "Number of control packets transmitted for this tunnel";
             }
             leaf control-rx-packets {
               type int32;
               description "Number of control packets received for this tunnel";
             }
             leaf data-tx-packets {
               type int32;
               description "Number of data packets transmitted for this tunnel";
             }
             leaf data-rx-packets {
               type int32;
               description "Number of data packets received for this tunnel";
             }
             leaf discard-tx-packets {
               type int32;
               description "Number of (attempted) transmitted packets that were discarded by this tunnel";
             }
             leaf discard-rx-packets {
               type int32;
               description "Number of received packets that were discarded by this tunnel";
             }
           }
         }
       }
     }
   }
   rpc get-pdp-diagnostics-per-apn {
     description "Show  PDP context diagnostics information";
     input {
       leaf apn {
         description "APN for which to show PDP Contexts";
         type string {
           junos:posix-pattern "^[.0-9A-Za-z-]{1,100}$";
           junos:pattern-message "Must be a string of 100 or fewer characters and may contain letters, numbers, decimals and dashes.";
         }
         mandatory true;
       }
     }
     output {
       container pdp-diagnostics-per-apn {
         leaf pdp-id {
           type int32;
           description "PDP id";
         }
       }
     }
   }
   rpc get-msp-ssubscriber-table {
     description "Show subscriber table entries";
   }
   rpc get-services-subscriber-session {
     description "Sessions";
     input {
       container criteria {
         choice criteria_c {
           case client-id {
             leaf client-id {
               description "Client identifier";
               type uint64;
             }
           }
           case user-id {
             leaf user-id {
               description "User identifier";
               type string;
             }
           }
           case ip-address {
             leaf ip-address {
               description "Client IP address";
               type ipaddr;
             }
           }
           case interface {
             leaf interface {
               description "Client interface name";
               type interface-name;
             }
           }
           case service-interface {
             leaf service-interface {
               description "Client MS-PIC name";
               type string;
             }
           }
           case routing-instance {
             leaf routing-instance {
               description "Routing instance name";
               type string;
             }
           }
         }
       }
       leaf level {
         default "brief";
         type enumeration {
           enum "brief" {
             description "Display brief output (default)";
           }
           enum "detail" {
             description "Display detailed output";
           }
           enum "summary" {
             description "Display summary output";
           }
         }
       }
     }
     output {
       container packet-triggered-subscribers-information {
         leaf message {
           type string;
           description "Message to be displaed";
         }
         container process-status {
           description "Process status";
           leaf num-clients {
             type int32;
           }
           leaf src-connection-state {
             type string;
             description "SRC connection state";
           }
           leaf num-diameterd-connected {
             type int32;
             description "Number of diameterd connections established";
           }
           leaf num-diameterd-disconnected {
             type int32;
             description "Number of diameterd connections disconnected";
           }
           leaf full-sync-in-progress {
             type string;
             description "Full sync in progress";
           }
           leaf fast-sync-in-progress {
             type string;
             description "Fast sync in progress";
           }
           leaf num-full-sync-abort {
             type string;
             description "Number of full sync abort";
           }
           leaf num-fast-sync-abort {
             type string;
             description "Number of fast sync abort";
           }
           leaf num-srr-received {
             type int32;
             description "Number of SRR received";
           }
           leaf num-srr-failure {
             type int32;
             description "Number failure SRR received";
           }
           leaf num-srr-queued {
             type int32;
             description "Number of SRR send attempted";
           }
           leaf num-srq-queued {
             type int32;
             description "Number of SRQ send attempted";
           }
           leaf num-srq-full-sync {
             type int32;
             description "Number of SRQ full-sync";
           }
           leaf num-srq-fast-sync {
             type int32;
             description "Number of SRQ fast-sync";
           }
           leaf num-srq-single-sync {
             type int32;
             description "Number of SRQ single-sync";
           }
           leaf num-sending-message {
             type int32;
             description "Number of queued sending messages";
           }
           leaf num-sending-queue-full {
             type int32;
             description "Number of sending queue full event";
           }
           leaf num-sending-timeout {
             type int32;
             description "Number of sending messages timed out";
           }
           leaf num-response-timeout {
             type int32;
             description "Number of pending response timed out";
           }
           leaf num-waiting-message {
             type int32;
             description "Number of messages waiting for response";
           }
           leaf num-ppr-received {
             type int32;
             description "Number of PPR received";
           }
           leaf num-asr-received {
             type int32;
             description "Number of ASR received";
           }
           leaf num-acr-received {
             type int32;
             description "Number of ACR received";
           }
           leaf num-aaa-received {
             type int32;
             description "Number of AAA received";
           }
           leaf num-sta-received {
             type int32;
             description "Number of STA received";
           }
           leaf num-sync-aaa-received {
             type int32;
             description "Number of sync AAA received";
           }
           leaf num-sync-sta-received {
             type int32;
             description "Number of sync STA received";
           }
           leaf num-aar-queued {
             type int32;
             description "Number of AAR send attempted";
           }
           leaf num-ppa-queued {
             type int32;
             description "Number of PPA send attempted";
           }
           leaf num-str-queued {
             type int32;
             description "Number of STR send attempted";
           }
           leaf num-asa-queued {
             type int32;
             description "Number of ASA send attempted";
           }
           leaf num-aca-queued {
             type int32;
             description "Number of ACA send attempted";
           }
           leaf num-sync-aar-queued {
             type int32;
             description "Number of sync AAR send attempted";
           }
           leaf num-sync-str-queued {
             type int32;
             description "Number of sync STR send attempted";
           }
           leaf num-srq-timeout {
             type int32;
             description "Number of SRQ timed out";
           }
           leaf num-str-timeout {
             type int32;
             description "Number of STR timed out";
           }
           leaf num-aar-timeout {
             type int32;
             description "Number of AAR timed out";
           }
           leaf num-aar-send-failure {
             type int32;
             description "Number of AAR send failed";
           }
           leaf num-asa-send-failure {
             type int32;
             description "Number of ASR send failed";
           }
           leaf num-aca-send-failure {
             type int32;
             description "Number of ACR send failed";
           }
           leaf num-ppa-send-failure {
             type int32;
             description "Number of PPA send failed";
           }
           leaf num-str-send-failure {
             type int32;
             description "Number of STR send failed";
           }
           leaf num-srq-send-failure {
             type int32;
             description "Number of SRQ send failed";
           }
           leaf num-srr-send-failure {
             type int32;
             description "Number of SRR send failed";
           }
           leaf num-sync-aar-send-failure {
             type int32;
             description "Number of AAR send failed";
           }
           leaf num-sync-str-send-failure {
             type int32;
             description "Number of STR send failed";
           }
           leaf num-sync-aar-timeout {
             type int32;
             description "Number of sync-AAR timed out";
           }
           leaf num-sync-str-timeout {
             type int32;
             description "Number of sync-STR timed out";
           }
           leaf num-fast-sync-queued {
             type int32;
             description "Number of fast-sync messages queued";
           }
           leaf num-queued-diameter-task {
             type int32;
             description "Number of diameter tasks queued";
           }
           leaf num-down-pic-clients {
             type int32;
             description "Number of ready-to-logout client session dur to PIC down";
           }
           leaf first-down-pic-client-id {
             type int64;
             description "First ready-to-logout client session ID";
           }
           leaf num-outstanding-diameter-message {
             type string;
             description "Number of outstanding diameter messages";
           }
           leaf num-login-retry {
             type string;
             description "Number of subscriber login retry with SRC";
           }
           leaf num-pconn {
             type int32;
             description "Number of pconn connections";
           }
           container pic-status {
             leaf pic-name {
               type string;
               description "Service PIC name";
             }
             leaf num-pic-login {
               type int32;
               description "Number of PIC login request";
             }
             leaf num-pic-logout-response {
               type int32;
               description "Number of PIC logout response";
             }
             leaf num-login-done {
               type int32;
               description "Number of PIC login done";
             }
             leaf num-pic-logout {
               type int32;
               description "Number of PIC logout request";
             }
             leaf num-policy-change {
               type int32;
               description "Number of policy changes request";
             }
             leaf num-policy-change-response {
               type int32;
               description "Number of policy changes response";
             }
             leaf num-src-logout {
               type int32;
               description "Number of SRC logout request";
             }
             leaf num-statistics-polling {
               type int32;
               description "Number of SRC statistics polling";
             }
             leaf num-sync-start {
               type int32;
               description "Number of PIC sync start request";
             }
             leaf num-sync-request {
               type int32;
               description "Number of PIC sync subscriber request";
             }
             leaf num-update-username {
               type int32;
               description "Number of username update request";
             }
             leaf num-pre-announcement {
               type int32;
               description "Number of pre-announcement";
             }
             leaf num-idle-timeout-update {
               type int32;
               description "Number of idle timeout configuraiton update";
             }
             leaf num-connection-up-event {
               type int32;
               description "Number of PCONN established event";
             }
             leaf num-pending-response {
               type int32;
               description "Number of request waiting for PIC to response";
             }
             leaf num-queued-pic-task {
               type int32;
               description "Number of PIC tasks queued";
             }
             leaf num-service-request-timeout {
               type int32;
               description "Number of service request timed out waiting for PIC response";
             }
             leaf num-logout-request-timeout {
               type int32;
               description "Number of logout request timed out waiting for PIC response";
             }
             leaf num-logout-request-send-failure {
               type int32;
               description "Number of logout request send failed";
             }
             leaf num-service-request-send-failure {
               type int32;
               description "Number of service request send failed";
             }
             leaf num-accounting-request-send-failure {
               type int32;
               description "Number of accounting request send failed";
             }
             leaf num-login-done-send-failure {
               type int32;
               description "Number of login done send failed";
             }
             leaf num-username-update-send-failure {
               type int32;
               description "Number of username update send failed";
             }
             leaf num-pre-announcement-send-failure {
               type int32;
               description "Number of pre-announcement send failed";
             }
             leaf num-idle-timeout-update-send-failure {
               type int32;
               description "Number of idle timeout configuraiton update send failed";
             }
             leaf num-service-set-update {
               type int32;
               description "Number of service-set update";
             }
             leaf num-service-set-update-send-failure {
               type int32;
               description "Number of service-set update send failed";
             }
             leaf num-partition-update-send {
               type int32;
               description "Number of partition update";
             }
             leaf num-partition-update-send-failure {
               type int32;
               description "Number of partition update send failed";
             }
             leaf num-subscriber-profiles-update {
               type int32;
               description "Number subscriber profile update";
             }
             leaf num-subscriber-profiles-update-failure {
               type int32;
               description "Number subscriber profile update send failed ";
             }
             leaf num-service-set-subscriber-profiles-mapping-update {
               type int32;
               description "Number service-set subscriber profile update";
             }
             leaf num-service-set-subscriber-profiles-mapping-update-failure {
               type int32;
               description "Number service-set subscriber profile update send failed";
             }
             leaf num-set-profile {
               type int32;
               description "Number set profile request";
             }
             leaf num-set-profile-failure {
               type int32;
               description "Number set profile request send failed";
             }
             leaf num-clear-profile {
               type int32;
               description "Number clear profile request";
             }
             leaf num-clear-profile-failure {
               type int32;
               description "Number clear profile request send failed";
             }
             leaf num-fpc-update {
               type int32;
               description "Number FPC information update";
             }
             leaf num-fpc-update-failure {
               type int32;
               description "Number FPC information update send failed";
             }
           }
           container radius-partition-status {
             leaf partition {
               type string;
               description "Partition name";
             }
             leaf num-valid-accounting-start {
               type int32;
               description "Number of valid accounting start message received";
             }
             leaf num-valid-accounting-stop {
               type int32;
               description "Number of valid accounting stop message received";
             }
             leaf num-valid-interim-accounting {
               type int32;
               description "Number of valid interim accounting message received";
             }
             leaf num-invalid-accounting-start {
               type int32;
               description "Number of invalid accounting start message received";
             }
             leaf num-invalid-accounting-stop {
               type int32;
               description "Number of invalid accounting stop message received";
             }
             leaf num-invalid-interim-accounting {
               type int32;
               description "Number of invalid interim accounting message received";
             }
             leaf num-accounting-on {
               type int32;
               description "Number of accounting-on message received";
             }
             leaf num-accounting-off {
               type int32;
               description "Number of accounting-off message received";
             }
             leaf num-accounting-start-response {
               type int32;
               description "Number of accounting stop message responses sent";
             }
             leaf num-accounting-stop-response {
               type int32;
               description "Number of accounting stop message responses sent";
             }
             leaf num-interim-accounting-response {
               type int32;
               description "Number of interim accounting message responses sent";
             }
             leaf num-tagging {
               type int32;
               description "Number of tagging recevied";
             }
           }
         }
         container subscriber-session-summary {
           description "Subscriber session summary";
           leaf num-clients {
             type int32;
           }
         }
         container subscriber-session {
           description "Subscriber session information";
           container session-detail {
             description "Subscriber session information";
             leaf client-id {
               type string;
               description "Client ID";
             }
             leaf username {
               type string;
               description "User name";
             }
             leaf user-ip-address {
               type string;
               description "User IP address";
             }
             leaf interface {
               type string;
               description "Interface name";
             }
             leaf subscriber-state {
               type string;
               description "Session state";
             }
             leaf service-interface {
               type string;
               description "Service interface";
             }
             leaf routing-instance {
               type string;
               description "Routing instance name";
             }
             leaf login-time {
               type string;
               description "Login time";
             }
             leaf partition {
               type string;
               description "Partition name";
             }
             leaf profile {
               type string;
               description "Profile name";
             }
             leaf num-services {
               type int32;
               description "Number of services";
             }
             container service-session {
               description "Service session information";
               leaf policy-name {
                 type string;
                 description "Policy name";
               }
               leaf service-state {
                 type string;
                 description "Session state";
               }
             }
           }
           container session-brief {
             description "Subscriber session information";
             leaf client-id {
               type string;
               description "Client ID";
             }
             leaf user-ip-address {
               type string;
               description "User IP address";
             }
             leaf interface {
               type string;
               description "Interface name";
             }
             leaf username {
               type string;
               description "User name";
             }
             container service-session {
               description "Service session information";
               leaf policy-name {
                 type string;
                 description "Policy name";
               }
               leaf service-state {
                 type string;
                 description "Session state";
               }
             }
           }
         }
         container session-statistics {
           description "Session statistics";
           leaf session-type {
             type string;
             description "Session type";
           }
           leaf name-id {
             type string;
             description "Name or Id";
           }
           leaf input-packets {
             type int64;
             description "Number of input packets";
           }
           leaf output-packets {
             type int64;
             description "Number of output packets";
           }
           leaf input-bytes {
             type int64;
             description "Number of input bytes";
           }
           leaf output-bytes {
             type int64;
             description "Number of output bytes";
           }
         }
         container extra-statistics {
           description "Session statistics information provided by additional source";
           leaf statistics-string {
             type string;
             description "Statistics information in string format";
           }
         }
         container subscriber-policy {
           description "Dynamic policies";
           leaf client-id {
             type string;
             description "Client ID";
           }
           container service-policy {
             description "Service dynamic policy";
             leaf policy-name {
               type string;
               description "Policy name";
             }
             leaf rpr {
               type string;
               description "Precedence";
             }
             leaf d {
               type string;
               description "Direction";
             }
             container term {
               description "Term";
               leaf template-name {
                 type string;
                 description "Rule template";
               }
               leaf tpr {
                 type int32;
                 description "Term precedence";
               }
               leaf ra {
                 type string;
                 description "Remote address";
               }
               leaf rm {
                 type int32;
                 description "Remote mask";
               }
               leaf lpl {
                 type int32;
                 description "Local port range low";
               }
               leaf lph {
                 type int32;
                 description "Local port range high";
               }
               leaf rpl {
                 type int32;
                 description "Remote port range low";
               }
               leaf rph {
                 type int32;
                 description "Remote port range high";
               }
               leaf p {
                 type int32;
                 description "Protocol";
               }
               leaf anl {
                 type string;
                 description "Application name list";
               }
               leaf agl {
                 type string;
                 description "Application group list";
               }
               leaf nanl {
                 type string;
                 description "Nested application name list";
               }
               leaf a-f {
                 type string;
                 description "Flow action";
               }
               leaf a-s {
                 type string;
                 description "Stats action";
               }
               leaf a-fc {
                 type string;
                 description "Forwarding class";
               }
               leaf a-p-i {
                 type int32;
                 description "Policer instance";
               }
               leaf a-p-bw {
                 type int32;
                 description "Policer bandwidth";
               }
               leaf a-p-mbs {
                 type int32;
                 description "Policer maximum burst size";
               }
               leaf a-fu {
                 type int32;
                 description "Forwarding unit";
               }
               leaf opt-profile {
                 type int32;
                 description "Subscriber profile";
               }
             }
           }
           container radius-policy {
             description "Dynamic RADIUS policies";
             container policy-attribute {
               leaf attribute-name {
                 type string;
                 description "Radius attribute name";
               }
               leaf attribute-value {
                 type string;
                 description "Radius attribute value";
               }
             }
           }
         }
         container subscriber-flows {
           description "Flows";
           leaf client-id {
             type string;
             description "Client ID";
           }
           leaf num-data-sessions {
             type int32;
             description "Number of data sessions";
           }
           leaf hwm {
             type int32;
             description "High water mark";
           }
           container flows {
             description "Flows";
             leaf five-tuple {
               type string;
               description "5 tuple";
             }
             leaf application-id {
               type string;
               description "Appication-id";
             }
             leaf policy-name {
               type string;
               description "Policy name";
             }
             leaf policy-direction {
               type string;
               description "Direction";
             }
             leaf packets {
               type string;
               description "Packet";
             }
             leaf bytes {
               type string;
               description "Bytes";
             }
             leaf offload {
               type string;
               description "Offload status";
             }
             leaf policy-action {
               type string;
               description "Policy action";
             }
           }
         }
         container subscriber-bandwidth {
           description "Bandwidth";
           leaf client-id {
             type string;
             description "Client ID";
           }
           leaf input-pps {
             type int32;
             description "Input pps";
           }
           leaf output-pps {
             type int32;
             description "Output pps";
           }
           leaf input-bps {
             type int32;
             description "Input bps";
           }
           leaf output-bps {
             type int32;
             description "Output bps";
           }
         }
         container clear-session-result {
           description "Result of clear session request";
           leaf num-logout-initiated {
             type int32;
             description "Number of session logout request initiated";
           }
         }
         container service-subscribers-request-result {
           description "Result for service subscriber request";
           container failed {
             description "Result for service subscriber request";
             leaf request_failure {
               type string;
               description "Service subscriber request failed";
             }
           }
           container success {
             description "Result for service subscriber request";
             leaf request_success {
               type empty;
               description "Service subscriber request succeed";
             }
           }
         }
       }
     }
   }
   rpc get-services-subscriber-statistics {
     description "Statistics";
     input {
       leaf client-id {
         description "Client identifier";
         type uint64;
         mandatory true;
       }
       leaf extensive {
         description "Display extensive output";
         type empty;
       }
     }
     output {
       container packet-triggered-subscribers-information {
         leaf message {
           type string;
           description "Message to be displaed";
         }
         container process-status {
           description "Process status";
           leaf num-clients {
             type int32;
           }
           leaf src-connection-state {
             type string;
             description "SRC connection state";
           }
           leaf num-diameterd-connected {
             type int32;
             description "Number of diameterd connections established";
           }
           leaf num-diameterd-disconnected {
             type int32;
             description "Number of diameterd connections disconnected";
           }
           leaf full-sync-in-progress {
             type string;
             description "Full sync in progress";
           }
           leaf fast-sync-in-progress {
             type string;
             description "Fast sync in progress";
           }
           leaf num-full-sync-abort {
             type string;
             description "Number of full sync abort";
           }
           leaf num-fast-sync-abort {
             type string;
             description "Number of fast sync abort";
           }
           leaf num-srr-received {
             type int32;
             description "Number of SRR received";
           }
           leaf num-srr-failure {
             type int32;
             description "Number failure SRR received";
           }
           leaf num-srr-queued {
             type int32;
             description "Number of SRR send attempted";
           }
           leaf num-srq-queued {
             type int32;
             description "Number of SRQ send attempted";
           }
           leaf num-srq-full-sync {
             type int32;
             description "Number of SRQ full-sync";
           }
           leaf num-srq-fast-sync {
             type int32;
             description "Number of SRQ fast-sync";
           }
           leaf num-srq-single-sync {
             type int32;
             description "Number of SRQ single-sync";
           }
           leaf num-sending-message {
             type int32;
             description "Number of queued sending messages";
           }
           leaf num-sending-queue-full {
             type int32;
             description "Number of sending queue full event";
           }
           leaf num-sending-timeout {
             type int32;
             description "Number of sending messages timed out";
           }
           leaf num-response-timeout {
             type int32;
             description "Number of pending response timed out";
           }
           leaf num-waiting-message {
             type int32;
             description "Number of messages waiting for response";
           }
           leaf num-ppr-received {
             type int32;
             description "Number of PPR received";
           }
           leaf num-asr-received {
             type int32;
             description "Number of ASR received";
           }
           leaf num-acr-received {
             type int32;
             description "Number of ACR received";
           }
           leaf num-aaa-received {
             type int32;
             description "Number of AAA received";
           }
           leaf num-sta-received {
             type int32;
             description "Number of STA received";
           }
           leaf num-sync-aaa-received {
             type int32;
             description "Number of sync AAA received";
           }
           leaf num-sync-sta-received {
             type int32;
             description "Number of sync STA received";
           }
           leaf num-aar-queued {
             type int32;
             description "Number of AAR send attempted";
           }
           leaf num-ppa-queued {
             type int32;
             description "Number of PPA send attempted";
           }
           leaf num-str-queued {
             type int32;
             description "Number of STR send attempted";
           }
           leaf num-asa-queued {
             type int32;
             description "Number of ASA send attempted";
           }
           leaf num-aca-queued {
             type int32;
             description "Number of ACA send attempted";
           }
           leaf num-sync-aar-queued {
             type int32;
             description "Number of sync AAR send attempted";
           }
           leaf num-sync-str-queued {
             type int32;
             description "Number of sync STR send attempted";
           }
           leaf num-srq-timeout {
             type int32;
             description "Number of SRQ timed out";
           }
           leaf num-str-timeout {
             type int32;
             description "Number of STR timed out";
           }
           leaf num-aar-timeout {
             type int32;
             description "Number of AAR timed out";
           }
           leaf num-aar-send-failure {
             type int32;
             description "Number of AAR send failed";
           }
           leaf num-asa-send-failure {
             type int32;
             description "Number of ASR send failed";
           }
           leaf num-aca-send-failure {
             type int32;
             description "Number of ACR send failed";
           }
           leaf num-ppa-send-failure {
             type int32;
             description "Number of PPA send failed";
           }
           leaf num-str-send-failure {
             type int32;
             description "Number of STR send failed";
           }
           leaf num-srq-send-failure {
             type int32;
             description "Number of SRQ send failed";
           }
           leaf num-srr-send-failure {
             type int32;
             description "Number of SRR send failed";
           }
           leaf num-sync-aar-send-failure {
             type int32;
             description "Number of AAR send failed";
           }
           leaf num-sync-str-send-failure {
             type int32;
             description "Number of STR send failed";
           }
           leaf num-sync-aar-timeout {
             type int32;
             description "Number of sync-AAR timed out";
           }
           leaf num-sync-str-timeout {
             type int32;
             description "Number of sync-STR timed out";
           }
           leaf num-fast-sync-queued {
             type int32;
             description "Number of fast-sync messages queued";
           }
           leaf num-queued-diameter-task {
             type int32;
             description "Number of diameter tasks queued";
           }
           leaf num-down-pic-clients {
             type int32;
             description "Number of ready-to-logout client session dur to PIC down";
           }
           leaf first-down-pic-client-id {
             type int64;
             description "First ready-to-logout client session ID";
           }
           leaf num-outstanding-diameter-message {
             type string;
             description "Number of outstanding diameter messages";
           }
           leaf num-login-retry {
             type string;
             description "Number of subscriber login retry with SRC";
           }
           leaf num-pconn {
             type int32;
             description "Number of pconn connections";
           }
           container pic-status {
             leaf pic-name {
               type string;
               description "Service PIC name";
             }
             leaf num-pic-login {
               type int32;
               description "Number of PIC login request";
             }
             leaf num-pic-logout-response {
               type int32;
               description "Number of PIC logout response";
             }
             leaf num-login-done {
               type int32;
               description "Number of PIC login done";
             }
             leaf num-pic-logout {
               type int32;
               description "Number of PIC logout request";
             }
             leaf num-policy-change {
               type int32;
               description "Number of policy changes request";
             }
             leaf num-policy-change-response {
               type int32;
               description "Number of policy changes response";
             }
             leaf num-src-logout {
               type int32;
               description "Number of SRC logout request";
             }
             leaf num-statistics-polling {
               type int32;
               description "Number of SRC statistics polling";
             }
             leaf num-sync-start {
               type int32;
               description "Number of PIC sync start request";
             }
             leaf num-sync-request {
               type int32;
               description "Number of PIC sync subscriber request";
             }
             leaf num-update-username {
               type int32;
               description "Number of username update request";
             }
             leaf num-pre-announcement {
               type int32;
               description "Number of pre-announcement";
             }
             leaf num-idle-timeout-update {
               type int32;
               description "Number of idle timeout configuraiton update";
             }
             leaf num-connection-up-event {
               type int32;
               description "Number of PCONN established event";
             }
             leaf num-pending-response {
               type int32;
               description "Number of request waiting for PIC to response";
             }
             leaf num-queued-pic-task {
               type int32;
               description "Number of PIC tasks queued";
             }
             leaf num-service-request-timeout {
               type int32;
               description "Number of service request timed out waiting for PIC response";
             }
             leaf num-logout-request-timeout {
               type int32;
               description "Number of logout request timed out waiting for PIC response";
             }
             leaf num-logout-request-send-failure {
               type int32;
               description "Number of logout request send failed";
             }
             leaf num-service-request-send-failure {
               type int32;
               description "Number of service request send failed";
             }
             leaf num-accounting-request-send-failure {
               type int32;
               description "Number of accounting request send failed";
             }
             leaf num-login-done-send-failure {
               type int32;
               description "Number of login done send failed";
             }
             leaf num-username-update-send-failure {
               type int32;
               description "Number of username update send failed";
             }
             leaf num-pre-announcement-send-failure {
               type int32;
               description "Number of pre-announcement send failed";
             }
             leaf num-idle-timeout-update-send-failure {
               type int32;
               description "Number of idle timeout configuraiton update send failed";
             }
             leaf num-service-set-update {
               type int32;
               description "Number of service-set update";
             }
             leaf num-service-set-update-send-failure {
               type int32;
               description "Number of service-set update send failed";
             }
             leaf num-partition-update-send {
               type int32;
               description "Number of partition update";
             }
             leaf num-partition-update-send-failure {
               type int32;
               description "Number of partition update send failed";
             }
             leaf num-subscriber-profiles-update {
               type int32;
               description "Number subscriber profile update";
             }
             leaf num-subscriber-profiles-update-failure {
               type int32;
               description "Number subscriber profile update send failed ";
             }
             leaf num-service-set-subscriber-profiles-mapping-update {
               type int32;
               description "Number service-set subscriber profile update";
             }
             leaf num-service-set-subscriber-profiles-mapping-update-failure {
               type int32;
               description "Number service-set subscriber profile update send failed";
             }
             leaf num-set-profile {
               type int32;
               description "Number set profile request";
             }
             leaf num-set-profile-failure {
               type int32;
               description "Number set profile request send failed";
             }
             leaf num-clear-profile {
               type int32;
               description "Number clear profile request";
             }
             leaf num-clear-profile-failure {
               type int32;
               description "Number clear profile request send failed";
             }
             leaf num-fpc-update {
               type int32;
               description "Number FPC information update";
             }
             leaf num-fpc-update-failure {
               type int32;
               description "Number FPC information update send failed";
             }
           }
           container radius-partition-status {
             leaf partition {
               type string;
               description "Partition name";
             }
             leaf num-valid-accounting-start {
               type int32;
               description "Number of valid accounting start message received";
             }
             leaf num-valid-accounting-stop {
               type int32;
               description "Number of valid accounting stop message received";
             }
             leaf num-valid-interim-accounting {
               type int32;
               description "Number of valid interim accounting message received";
             }
             leaf num-invalid-accounting-start {
               type int32;
               description "Number of invalid accounting start message received";
             }
             leaf num-invalid-accounting-stop {
               type int32;
               description "Number of invalid accounting stop message received";
             }
             leaf num-invalid-interim-accounting {
               type int32;
               description "Number of invalid interim accounting message received";
             }
             leaf num-accounting-on {
               type int32;
               description "Number of accounting-on message received";
             }
             leaf num-accounting-off {
               type int32;
               description "Number of accounting-off message received";
             }
             leaf num-accounting-start-response {
               type int32;
               description "Number of accounting stop message responses sent";
             }
             leaf num-accounting-stop-response {
               type int32;
               description "Number of accounting stop message responses sent";
             }
             leaf num-interim-accounting-response {
               type int32;
               description "Number of interim accounting message responses sent";
             }
             leaf num-tagging {
               type int32;
               description "Number of tagging recevied";
             }
           }
         }
         container subscriber-session-summary {
           description "Subscriber session summary";
           leaf num-clients {
             type int32;
           }
         }
         container subscriber-session {
           description "Subscriber session information";
           container session-detail {
             description "Subscriber session information";
             leaf client-id {
               type string;
               description "Client ID";
             }
             leaf username {
               type string;
               description "User name";
             }
             leaf user-ip-address {
               type string;
               description "User IP address";
             }
             leaf interface {
               type string;
               description "Interface name";
             }
             leaf subscriber-state {
               type string;
               description "Session state";
             }
             leaf service-interface {
               type string;
               description "Service interface";
             }
             leaf routing-instance {
               type string;
               description "Routing instance name";
             }
             leaf login-time {
               type string;
               description "Login time";
             }
             leaf partition {
               type string;
               description "Partition name";
             }
             leaf profile {
               type string;
               description "Profile name";
             }
             leaf num-services {
               type int32;
               description "Number of services";
             }
             container service-session {
               description "Service session information";
               leaf policy-name {
                 type string;
                 description "Policy name";
               }
               leaf service-state {
                 type string;
                 description "Session state";
               }
             }
           }
           container session-brief {
             description "Subscriber session information";
             leaf client-id {
               type string;
               description "Client ID";
             }
             leaf user-ip-address {
               type string;
               description "User IP address";
             }
             leaf interface {
               type string;
               description "Interface name";
             }
             leaf username {
               type string;
               description "User name";
             }
             container service-session {
               description "Service session information";
               leaf policy-name {
                 type string;
                 description "Policy name";
               }
               leaf service-state {
                 type string;
                 description "Session state";
               }
             }
           }
         }
         container session-statistics {
           description "Session statistics";
           leaf session-type {
             type string;
             description "Session type";
           }
           leaf name-id {
             type string;
             description "Name or Id";
           }
           leaf input-packets {
             type int64;
             description "Number of input packets";
           }
           leaf output-packets {
             type int64;
             description "Number of output packets";
           }
           leaf input-bytes {
             type int64;
             description "Number of input bytes";
           }
           leaf output-bytes {
             type int64;
             description "Number of output bytes";
           }
         }
         container extra-statistics {
           description "Session statistics information provided by additional source";
           leaf statistics-string {
             type string;
             description "Statistics information in string format";
           }
         }
         container subscriber-policy {
           description "Dynamic policies";
           leaf client-id {
             type string;
             description "Client ID";
           }
           container service-policy {
             description "Service dynamic policy";
             leaf policy-name {
               type string;
               description "Policy name";
             }
             leaf rpr {
               type string;
               description "Precedence";
             }
             leaf d {
               type string;
               description "Direction";
             }
             container term {
               description "Term";
               leaf template-name {
                 type string;
                 description "Rule template";
               }
               leaf tpr {
                 type int32;
                 description "Term precedence";
               }
               leaf ra {
                 type string;
                 description "Remote address";
               }
               leaf rm {
                 type int32;
                 description "Remote mask";
               }
               leaf lpl {
                 type int32;
                 description "Local port range low";
               }
               leaf lph {
                 type int32;
                 description "Local port range high";
               }
               leaf rpl {
                 type int32;
                 description "Remote port range low";
               }
               leaf rph {
                 type int32;
                 description "Remote port range high";
               }
               leaf p {
                 type int32;
                 description "Protocol";
               }
               leaf anl {
                 type string;
                 description "Application name list";
               }
               leaf agl {
                 type string;
                 description "Application group list";
               }
               leaf nanl {
                 type string;
                 description "Nested application name list";
               }
               leaf a-f {
                 type string;
                 description "Flow action";
               }
               leaf a-s {
                 type string;
                 description "Stats action";
               }
               leaf a-fc {
                 type string;
                 description "Forwarding class";
               }
               leaf a-p-i {
                 type int32;
                 description "Policer instance";
               }
               leaf a-p-bw {
                 type int32;
                 description "Policer bandwidth";
               }
               leaf a-p-mbs {
                 type int32;
                 description "Policer maximum burst size";
               }
               leaf a-fu {
                 type int32;
                 description "Forwarding unit";
               }
               leaf opt-profile {
                 type int32;
                 description "Subscriber profile";
               }
             }
           }
           container radius-policy {
             description "Dynamic RADIUS policies";
             container policy-attribute {
               leaf attribute-name {
                 type string;
                 description "Radius attribute name";
               }
               leaf attribute-value {
                 type string;
                 description "Radius attribute value";
               }
             }
           }
         }
         container subscriber-flows {
           description "Flows";
           leaf client-id {
             type string;
             description "Client ID";
           }
           leaf num-data-sessions {
             type int32;
             description "Number of data sessions";
           }
           leaf hwm {
             type int32;
             description "High water mark";
           }
           container flows {
             description "Flows";
             leaf five-tuple {
               type string;
               description "5 tuple";
             }
             leaf application-id {
               type string;
               description "Appication-id";
             }
             leaf policy-name {
               type string;
               description "Policy name";
             }
             leaf policy-direction {
               type string;
               description "Direction";
             }
             leaf packets {
               type string;
               description "Packet";
             }
             leaf bytes {
               type string;
               description "Bytes";
             }
             leaf offload {
               type string;
               description "Offload status";
             }
             leaf policy-action {
               type string;
               description "Policy action";
             }
           }
         }
         container subscriber-bandwidth {
           description "Bandwidth";
           leaf client-id {
             type string;
             description "Client ID";
           }
           leaf input-pps {
             type int32;
             description "Input pps";
           }
           leaf output-pps {
             type int32;
             description "Output pps";
           }
           leaf input-bps {
             type int32;
             description "Input bps";
           }
           leaf output-bps {
             type int32;
             description "Output bps";
           }
         }
         container clear-session-result {
           description "Result of clear session request";
           leaf num-logout-initiated {
             type int32;
             description "Number of session logout request initiated";
           }
         }
         container service-subscribers-request-result {
           description "Result for service subscriber request";
           container failed {
             description "Result for service subscriber request";
             leaf request_failure {
               type string;
               description "Service subscriber request failed";
             }
           }
           container success {
             description "Result for service subscriber request";
             leaf request_success {
               type empty;
               description "Service subscriber request succeed";
             }
           }
         }
       }
     }
   }
   rpc get-services-subscriber-bandwidth-by-session-id {
     description "By client identifier";
     input {
       leaf client-id {
         description "Client identifier";
         type uint64;
         mandatory true;
       }
     }
     output {
       container packet-triggered-subscribers-information {
         leaf message {
           type string;
           description "Message to be displaed";
         }
         container process-status {
           description "Process status";
           leaf num-clients {
             type int32;
           }
           leaf src-connection-state {
             type string;
             description "SRC connection state";
           }
           leaf num-diameterd-connected {
             type int32;
             description "Number of diameterd connections established";
           }
           leaf num-diameterd-disconnected {
             type int32;
             description "Number of diameterd connections disconnected";
           }
           leaf full-sync-in-progress {
             type string;
             description "Full sync in progress";
           }
           leaf fast-sync-in-progress {
             type string;
             description "Fast sync in progress";
           }
           leaf num-full-sync-abort {
             type string;
             description "Number of full sync abort";
           }
           leaf num-fast-sync-abort {
             type string;
             description "Number of fast sync abort";
           }
           leaf num-srr-received {
             type int32;
             description "Number of SRR received";
           }
           leaf num-srr-failure {
             type int32;
             description "Number failure SRR received";
           }
           leaf num-srr-queued {
             type int32;
             description "Number of SRR send attempted";
           }
           leaf num-srq-queued {
             type int32;
             description "Number of SRQ send attempted";
           }
           leaf num-srq-full-sync {
             type int32;
             description "Number of SRQ full-sync";
           }
           leaf num-srq-fast-sync {
             type int32;
             description "Number of SRQ fast-sync";
           }
           leaf num-srq-single-sync {
             type int32;
             description "Number of SRQ single-sync";
           }
           leaf num-sending-message {
             type int32;
             description "Number of queued sending messages";
           }
           leaf num-sending-queue-full {
             type int32;
             description "Number of sending queue full event";
           }
           leaf num-sending-timeout {
             type int32;
             description "Number of sending messages timed out";
           }
           leaf num-response-timeout {
             type int32;
             description "Number of pending response timed out";
           }
           leaf num-waiting-message {
             type int32;
             description "Number of messages waiting for response";
           }
           leaf num-ppr-received {
             type int32;
             description "Number of PPR received";
           }
           leaf num-asr-received {
             type int32;
             description "Number of ASR received";
           }
           leaf num-acr-received {
             type int32;
             description "Number of ACR received";
           }
           leaf num-aaa-received {
             type int32;
             description "Number of AAA received";
           }
           leaf num-sta-received {
             type int32;
             description "Number of STA received";
           }
           leaf num-sync-aaa-received {
             type int32;
             description "Number of sync AAA received";
           }
           leaf num-sync-sta-received {
             type int32;
             description "Number of sync STA received";
           }
           leaf num-aar-queued {
             type int32;
             description "Number of AAR send attempted";
           }
           leaf num-ppa-queued {
             type int32;
             description "Number of PPA send attempted";
           }
           leaf num-str-queued {
             type int32;
             description "Number of STR send attempted";
           }
           leaf num-asa-queued {
             type int32;
             description "Number of ASA send attempted";
           }
           leaf num-aca-queued {
             type int32;
             description "Number of ACA send attempted";
           }
           leaf num-sync-aar-queued {
             type int32;
             description "Number of sync AAR send attempted";
           }
           leaf num-sync-str-queued {
             type int32;
             description "Number of sync STR send attempted";
           }
           leaf num-srq-timeout {
             type int32;
             description "Number of SRQ timed out";
           }
           leaf num-str-timeout {
             type int32;
             description "Number of STR timed out";
           }
           leaf num-aar-timeout {
             type int32;
             description "Number of AAR timed out";
           }
           leaf num-aar-send-failure {
             type int32;
             description "Number of AAR send failed";
           }
           leaf num-asa-send-failure {
             type int32;
             description "Number of ASR send failed";
           }
           leaf num-aca-send-failure {
             type int32;
             description "Number of ACR send failed";
           }
           leaf num-ppa-send-failure {
             type int32;
             description "Number of PPA send failed";
           }
           leaf num-str-send-failure {
             type int32;
             description "Number of STR send failed";
           }
           leaf num-srq-send-failure {
             type int32;
             description "Number of SRQ send failed";
           }
           leaf num-srr-send-failure {
             type int32;
             description "Number of SRR send failed";
           }
           leaf num-sync-aar-send-failure {
             type int32;
             description "Number of AAR send failed";
           }
           leaf num-sync-str-send-failure {
             type int32;
             description "Number of STR send failed";
           }
           leaf num-sync-aar-timeout {
             type int32;
             description "Number of sync-AAR timed out";
           }
           leaf num-sync-str-timeout {
             type int32;
             description "Number of sync-STR timed out";
           }
           leaf num-fast-sync-queued {
             type int32;
             description "Number of fast-sync messages queued";
           }
           leaf num-queued-diameter-task {
             type int32;
             description "Number of diameter tasks queued";
           }
           leaf num-down-pic-clients {
             type int32;
             description "Number of ready-to-logout client session dur to PIC down";
           }
           leaf first-down-pic-client-id {
             type int64;
             description "First ready-to-logout client session ID";
           }
           leaf num-outstanding-diameter-message {
             type string;
             description "Number of outstanding diameter messages";
           }
           leaf num-login-retry {
             type string;
             description "Number of subscriber login retry with SRC";
           }
           leaf num-pconn {
             type int32;
             description "Number of pconn connections";
           }
           container pic-status {
             leaf pic-name {
               type string;
               description "Service PIC name";
             }
             leaf num-pic-login {
               type int32;
               description "Number of PIC login request";
             }
             leaf num-pic-logout-response {
               type int32;
               description "Number of PIC logout response";
             }
             leaf num-login-done {
               type int32;
               description "Number of PIC login done";
             }
             leaf num-pic-logout {
               type int32;
               description "Number of PIC logout request";
             }
             leaf num-policy-change {
               type int32;
               description "Number of policy changes request";
             }
             leaf num-policy-change-response {
               type int32;
               description "Number of policy changes response";
             }
             leaf num-src-logout {
               type int32;
               description "Number of SRC logout request";
             }
             leaf num-statistics-polling {
               type int32;
               description "Number of SRC statistics polling";
             }
             leaf num-sync-start {
               type int32;
               description "Number of PIC sync start request";
             }
             leaf num-sync-request {
               type int32;
               description "Number of PIC sync subscriber request";
             }
             leaf num-update-username {
               type int32;
               description "Number of username update request";
             }
             leaf num-pre-announcement {
               type int32;
               description "Number of pre-announcement";
             }
             leaf num-idle-timeout-update {
               type int32;
               description "Number of idle timeout configuraiton update";
             }
             leaf num-connection-up-event {
               type int32;
               description "Number of PCONN established event";
             }
             leaf num-pending-response {
               type int32;
               description "Number of request waiting for PIC to response";
             }
             leaf num-queued-pic-task {
               type int32;
               description "Number of PIC tasks queued";
             }
             leaf num-service-request-timeout {
               type int32;
               description "Number of service request timed out waiting for PIC response";
             }
             leaf num-logout-request-timeout {
               type int32;
               description "Number of logout request timed out waiting for PIC response";
             }
             leaf num-logout-request-send-failure {
               type int32;
               description "Number of logout request send failed";
             }
             leaf num-service-request-send-failure {
               type int32;
               description "Number of service request send failed";
             }
             leaf num-accounting-request-send-failure {
               type int32;
               description "Number of accounting request send failed";
             }
             leaf num-login-done-send-failure {
               type int32;
               description "Number of login done send failed";
             }
             leaf num-username-update-send-failure {
               type int32;
               description "Number of username update send failed";
             }
             leaf num-pre-announcement-send-failure {
               type int32;
               description "Number of pre-announcement send failed";
             }
             leaf num-idle-timeout-update-send-failure {
               type int32;
               description "Number of idle timeout configuraiton update send failed";
             }
             leaf num-service-set-update {
               type int32;
               description "Number of service-set update";
             }
             leaf num-service-set-update-send-failure {
               type int32;
               description "Number of service-set update send failed";
             }
             leaf num-partition-update-send {
               type int32;
               description "Number of partition update";
             }
             leaf num-partition-update-send-failure {
               type int32;
               description "Number of partition update send failed";
             }
             leaf num-subscriber-profiles-update {
               type int32;
               description "Number subscriber profile update";
             }
             leaf num-subscriber-profiles-update-failure {
               type int32;
               description "Number subscriber profile update send failed ";
             }
             leaf num-service-set-subscriber-profiles-mapping-update {
               type int32;
               description "Number service-set subscriber profile update";
             }
             leaf num-service-set-subscriber-profiles-mapping-update-failure {
               type int32;
               description "Number service-set subscriber profile update send failed";
             }
             leaf num-set-profile {
               type int32;
               description "Number set profile request";
             }
             leaf num-set-profile-failure {
               type int32;
               description "Number set profile request send failed";
             }
             leaf num-clear-profile {
               type int32;
               description "Number clear profile request";
             }
             leaf num-clear-profile-failure {
               type int32;
               description "Number clear profile request send failed";
             }
             leaf num-fpc-update {
               type int32;
               description "Number FPC information update";
             }
             leaf num-fpc-update-failure {
               type int32;
               description "Number FPC information update send failed";
             }
           }
           container radius-partition-status {
             leaf partition {
               type string;
               description "Partition name";
             }
             leaf num-valid-accounting-start {
               type int32;
               description "Number of valid accounting start message received";
             }
             leaf num-valid-accounting-stop {
               type int32;
               description "Number of valid accounting stop message received";
             }
             leaf num-valid-interim-accounting {
               type int32;
               description "Number of valid interim accounting message received";
             }
             leaf num-invalid-accounting-start {
               type int32;
               description "Number of invalid accounting start message received";
             }
             leaf num-invalid-accounting-stop {
               type int32;
               description "Number of invalid accounting stop message received";
             }
             leaf num-invalid-interim-accounting {
               type int32;
               description "Number of invalid interim accounting message received";
             }
             leaf num-accounting-on {
               type int32;
               description "Number of accounting-on message received";
             }
             leaf num-accounting-off {
               type int32;
               description "Number of accounting-off message received";
             }
             leaf num-accounting-start-response {
               type int32;
               description "Number of accounting stop message responses sent";
             }
             leaf num-accounting-stop-response {
               type int32;
               description "Number of accounting stop message responses sent";
             }
             leaf num-interim-accounting-response {
               type int32;
               description "Number of interim accounting message responses sent";
             }
             leaf num-tagging {
               type int32;
               description "Number of tagging recevied";
             }
           }
         }
         container subscriber-session-summary {
           description "Subscriber session summary";
           leaf num-clients {
             type int32;
           }
         }
         container subscriber-session {
           description "Subscriber session information";
           container session-detail {
             description "Subscriber session information";
             leaf client-id {
               type string;
               description "Client ID";
             }
             leaf username {
               type string;
               description "User name";
             }
             leaf user-ip-address {
               type string;
               description "User IP address";
             }
             leaf interface {
               type string;
               description "Interface name";
             }
             leaf subscriber-state {
               type string;
               description "Session state";
             }
             leaf service-interface {
               type string;
               description "Service interface";
             }
             leaf routing-instance {
               type string;
               description "Routing instance name";
             }
             leaf login-time {
               type string;
               description "Login time";
             }
             leaf partition {
               type string;
               description "Partition name";
             }
             leaf profile {
               type string;
               description "Profile name";
             }
             leaf num-services {
               type int32;
               description "Number of services";
             }
             container service-session {
               description "Service session information";
               leaf policy-name {
                 type string;
                 description "Policy name";
               }
               leaf service-state {
                 type string;
                 description "Session state";
               }
             }
           }
           container session-brief {
             description "Subscriber session information";
             leaf client-id {
               type string;
               description "Client ID";
             }
             leaf user-ip-address {
               type string;
               description "User IP address";
             }
             leaf interface {
               type string;
               description "Interface name";
             }
             leaf username {
               type string;
               description "User name";
             }
             container service-session {
               description "Service session information";
               leaf policy-name {
                 type string;
                 description "Policy name";
               }
               leaf service-state {
                 type string;
                 description "Session state";
               }
             }
           }
         }
         container session-statistics {
           description "Session statistics";
           leaf session-type {
             type string;
             description "Session type";
           }
           leaf name-id {
             type string;
             description "Name or Id";
           }
           leaf input-packets {
             type int64;
             description "Number of input packets";
           }
           leaf output-packets {
             type int64;
             description "Number of output packets";
           }
           leaf input-bytes {
             type int64;
             description "Number of input bytes";
           }
           leaf output-bytes {
             type int64;
             description "Number of output bytes";
           }
         }
         container extra-statistics {
           description "Session statistics information provided by additional source";
           leaf statistics-string {
             type string;
             description "Statistics information in string format";
           }
         }
         container subscriber-policy {
           description "Dynamic policies";
           leaf client-id {
             type string;
             description "Client ID";
           }
           container service-policy {
             description "Service dynamic policy";
             leaf policy-name {
               type string;
               description "Policy name";
             }
             leaf rpr {
               type string;
               description "Precedence";
             }
             leaf d {
               type string;
               description "Direction";
             }
             container term {
               description "Term";
               leaf template-name {
                 type string;
                 description "Rule template";
               }
               leaf tpr {
                 type int32;
                 description "Term precedence";
               }
               leaf ra {
                 type string;
                 description "Remote address";
               }
               leaf rm {
                 type int32;
                 description "Remote mask";
               }
               leaf lpl {
                 type int32;
                 description "Local port range low";
               }
               leaf lph {
                 type int32;
                 description "Local port range high";
               }
               leaf rpl {
                 type int32;
                 description "Remote port range low";
               }
               leaf rph {
                 type int32;
                 description "Remote port range high";
               }
               leaf p {
                 type int32;
                 description "Protocol";
               }
               leaf anl {
                 type string;
                 description "Application name list";
               }
               leaf agl {
                 type string;
                 description "Application group list";
               }
               leaf nanl {
                 type string;
                 description "Nested application name list";
               }
               leaf a-f {
                 type string;
                 description "Flow action";
               }
               leaf a-s {
                 type string;
                 description "Stats action";
               }
               leaf a-fc {
                 type string;
                 description "Forwarding class";
               }
               leaf a-p-i {
                 type int32;
                 description "Policer instance";
               }
               leaf a-p-bw {
                 type int32;
                 description "Policer bandwidth";
               }
               leaf a-p-mbs {
                 type int32;
                 description "Policer maximum burst size";
               }
               leaf a-fu {
                 type int32;
                 description "Forwarding unit";
               }
               leaf opt-profile {
                 type int32;
                 description "Subscriber profile";
               }
             }
           }
           container radius-policy {
             description "Dynamic RADIUS policies";
             container policy-attribute {
               leaf attribute-name {
                 type string;
                 description "Radius attribute name";
               }
               leaf attribute-value {
                 type string;
                 description "Radius attribute value";
               }
             }
           }
         }
         container subscriber-flows {
           description "Flows";
           leaf client-id {
             type string;
             description "Client ID";
           }
           leaf num-data-sessions {
             type int32;
             description "Number of data sessions";
           }
           leaf hwm {
             type int32;
             description "High water mark";
           }
           container flows {
             description "Flows";
             leaf five-tuple {
               type string;
               description "5 tuple";
             }
             leaf application-id {
               type string;
               description "Appication-id";
             }
             leaf policy-name {
               type string;
               description "Policy name";
             }
             leaf policy-direction {
               type string;
               description "Direction";
             }
             leaf packets {
               type string;
               description "Packet";
             }
             leaf bytes {
               type string;
               description "Bytes";
             }
             leaf offload {
               type string;
               description "Offload status";
             }
             leaf policy-action {
               type string;
               description "Policy action";
             }
           }
         }
         container subscriber-bandwidth {
           description "Bandwidth";
           leaf client-id {
             type string;
             description "Client ID";
           }
           leaf input-pps {
             type int32;
             description "Input pps";
           }
           leaf output-pps {
             type int32;
             description "Output pps";
           }
           leaf input-bps {
             type int32;
             description "Input bps";
           }
           leaf output-bps {
             type int32;
             description "Output bps";
           }
         }
         container clear-session-result {
           description "Result of clear session request";
           leaf num-logout-initiated {
             type int32;
             description "Number of session logout request initiated";
           }
         }
         container service-subscribers-request-result {
           description "Result for service subscriber request";
           container failed {
             description "Result for service subscriber request";
             leaf request_failure {
               type string;
               description "Service subscriber request failed";
             }
           }
           container success {
             description "Result for service subscriber request";
             leaf request_success {
               type empty;
               description "Service subscriber request succeed";
             }
           }
         }
       }
     }
   }
   rpc get-services-subscriber-bandwidth-by-ip-address {
     description "By IP address";
     input {
       leaf ip-address {
         description "Client IP address";
         type ipaddr;
       }
     }
     output {
       container packet-triggered-subscribers-information {
         leaf message {
           type string;
           description "Message to be displaed";
         }
         container process-status {
           description "Process status";
           leaf num-clients {
             type int32;
           }
           leaf src-connection-state {
             type string;
             description "SRC connection state";
           }
           leaf num-diameterd-connected {
             type int32;
             description "Number of diameterd connections established";
           }
           leaf num-diameterd-disconnected {
             type int32;
             description "Number of diameterd connections disconnected";
           }
           leaf full-sync-in-progress {
             type string;
             description "Full sync in progress";
           }
           leaf fast-sync-in-progress {
             type string;
             description "Fast sync in progress";
           }
           leaf num-full-sync-abort {
             type string;
             description "Number of full sync abort";
           }
           leaf num-fast-sync-abort {
             type string;
             description "Number of fast sync abort";
           }
           leaf num-srr-received {
             type int32;
             description "Number of SRR received";
           }
           leaf num-srr-failure {
             type int32;
             description "Number failure SRR received";
           }
           leaf num-srr-queued {
             type int32;
             description "Number of SRR send attempted";
           }
           leaf num-srq-queued {
             type int32;
             description "Number of SRQ send attempted";
           }
           leaf num-srq-full-sync {
             type int32;
             description "Number of SRQ full-sync";
           }
           leaf num-srq-fast-sync {
             type int32;
             description "Number of SRQ fast-sync";
           }
           leaf num-srq-single-sync {
             type int32;
             description "Number of SRQ single-sync";
           }
           leaf num-sending-message {
             type int32;
             description "Number of queued sending messages";
           }
           leaf num-sending-queue-full {
             type int32;
             description "Number of sending queue full event";
           }
           leaf num-sending-timeout {
             type int32;
             description "Number of sending messages timed out";
           }
           leaf num-response-timeout {
             type int32;
             description "Number of pending response timed out";
           }
           leaf num-waiting-message {
             type int32;
             description "Number of messages waiting for response";
           }
           leaf num-ppr-received {
             type int32;
             description "Number of PPR received";
           }
           leaf num-asr-received {
             type int32;
             description "Number of ASR received";
           }
           leaf num-acr-received {
             type int32;
             description "Number of ACR received";
           }
           leaf num-aaa-received {
             type int32;
             description "Number of AAA received";
           }
           leaf num-sta-received {
             type int32;
             description "Number of STA received";
           }
           leaf num-sync-aaa-received {
             type int32;
             description "Number of sync AAA received";
           }
           leaf num-sync-sta-received {
             type int32;
             description "Number of sync STA received";
           }
           leaf num-aar-queued {
             type int32;
             description "Number of AAR send attempted";
           }
           leaf num-ppa-queued {
             type int32;
             description "Number of PPA send attempted";
           }
           leaf num-str-queued {
             type int32;
             description "Number of STR send attempted";
           }
           leaf num-asa-queued {
             type int32;
             description "Number of ASA send attempted";
           }
           leaf num-aca-queued {
             type int32;
             description "Number of ACA send attempted";
           }
           leaf num-sync-aar-queued {
             type int32;
             description "Number of sync AAR send attempted";
           }
           leaf num-sync-str-queued {
             type int32;
             description "Number of sync STR send attempted";
           }
           leaf num-srq-timeout {
             type int32;
             description "Number of SRQ timed out";
           }
           leaf num-str-timeout {
             type int32;
             description "Number of STR timed out";
           }
           leaf num-aar-timeout {
             type int32;
             description "Number of AAR timed out";
           }
           leaf num-aar-send-failure {
             type int32;
             description "Number of AAR send failed";
           }
           leaf num-asa-send-failure {
             type int32;
             description "Number of ASR send failed";
           }
           leaf num-aca-send-failure {
             type int32;
             description "Number of ACR send failed";
           }
           leaf num-ppa-send-failure {
             type int32;
             description "Number of PPA send failed";
           }
           leaf num-str-send-failure {
             type int32;
             description "Number of STR send failed";
           }
           leaf num-srq-send-failure {
             type int32;
             description "Number of SRQ send failed";
           }
           leaf num-srr-send-failure {
             type int32;
             description "Number of SRR send failed";
           }
           leaf num-sync-aar-send-failure {
             type int32;
             description "Number of AAR send failed";
           }
           leaf num-sync-str-send-failure {
             type int32;
             description "Number of STR send failed";
           }
           leaf num-sync-aar-timeout {
             type int32;
             description "Number of sync-AAR timed out";
           }
           leaf num-sync-str-timeout {
             type int32;
             description "Number of sync-STR timed out";
           }
           leaf num-fast-sync-queued {
             type int32;
             description "Number of fast-sync messages queued";
           }
           leaf num-queued-diameter-task {
             type int32;
             description "Number of diameter tasks queued";
           }
           leaf num-down-pic-clients {
             type int32;
             description "Number of ready-to-logout client session dur to PIC down";
           }
           leaf first-down-pic-client-id {
             type int64;
             description "First ready-to-logout client session ID";
           }
           leaf num-outstanding-diameter-message {
             type string;
             description "Number of outstanding diameter messages";
           }
           leaf num-login-retry {
             type string;
             description "Number of subscriber login retry with SRC";
           }
           leaf num-pconn {
             type int32;
             description "Number of pconn connections";
           }
           container pic-status {
             leaf pic-name {
               type string;
               description "Service PIC name";
             }
             leaf num-pic-login {
               type int32;
               description "Number of PIC login request";
             }
             leaf num-pic-logout-response {
               type int32;
               description "Number of PIC logout response";
             }
             leaf num-login-done {
               type int32;
               description "Number of PIC login done";
             }
             leaf num-pic-logout {
               type int32;
               description "Number of PIC logout request";
             }
             leaf num-policy-change {
               type int32;
               description "Number of policy changes request";
             }
             leaf num-policy-change-response {
               type int32;
               description "Number of policy changes response";
             }
             leaf num-src-logout {
               type int32;
               description "Number of SRC logout request";
             }
             leaf num-statistics-polling {
               type int32;
               description "Number of SRC statistics polling";
             }
             leaf num-sync-start {
               type int32;
               description "Number of PIC sync start request";
             }
             leaf num-sync-request {
               type int32;
               description "Number of PIC sync subscriber request";
             }
             leaf num-update-username {
               type int32;
               description "Number of username update request";
             }
             leaf num-pre-announcement {
               type int32;
               description "Number of pre-announcement";
             }
             leaf num-idle-timeout-update {
               type int32;
               description "Number of idle timeout configuraiton update";
             }
             leaf num-connection-up-event {
               type int32;
               description "Number of PCONN established event";
             }
             leaf num-pending-response {
               type int32;
               description "Number of request waiting for PIC to response";
             }
             leaf num-queued-pic-task {
               type int32;
               description "Number of PIC tasks queued";
             }
             leaf num-service-request-timeout {
               type int32;
               description "Number of service request timed out waiting for PIC response";
             }
             leaf num-logout-request-timeout {
               type int32;
               description "Number of logout request timed out waiting for PIC response";
             }
             leaf num-logout-request-send-failure {
               type int32;
               description "Number of logout request send failed";
             }
             leaf num-service-request-send-failure {
               type int32;
               description "Number of service request send failed";
             }
             leaf num-accounting-request-send-failure {
               type int32;
               description "Number of accounting request send failed";
             }
             leaf num-login-done-send-failure {
               type int32;
               description "Number of login done send failed";
             }
             leaf num-username-update-send-failure {
               type int32;
               description "Number of username update send failed";
             }
             leaf num-pre-announcement-send-failure {
               type int32;
               description "Number of pre-announcement send failed";
             }
             leaf num-idle-timeout-update-send-failure {
               type int32;
               description "Number of idle timeout configuraiton update send failed";
             }
             leaf num-service-set-update {
               type int32;
               description "Number of service-set update";
             }
             leaf num-service-set-update-send-failure {
               type int32;
               description "Number of service-set update send failed";
             }
             leaf num-partition-update-send {
               type int32;
               description "Number of partition update";
             }
             leaf num-partition-update-send-failure {
               type int32;
               description "Number of partition update send failed";
             }
             leaf num-subscriber-profiles-update {
               type int32;
               description "Number subscriber profile update";
             }
             leaf num-subscriber-profiles-update-failure {
               type int32;
               description "Number subscriber profile update send failed ";
             }
             leaf num-service-set-subscriber-profiles-mapping-update {
               type int32;
               description "Number service-set subscriber profile update";
             }
             leaf num-service-set-subscriber-profiles-mapping-update-failure {
               type int32;
               description "Number service-set subscriber profile update send failed";
             }
             leaf num-set-profile {
               type int32;
               description "Number set profile request";
             }
             leaf num-set-profile-failure {
               type int32;
               description "Number set profile request send failed";
             }
             leaf num-clear-profile {
               type int32;
               description "Number clear profile request";
             }
             leaf num-clear-profile-failure {
               type int32;
               description "Number clear profile request send failed";
             }
             leaf num-fpc-update {
               type int32;
               description "Number FPC information update";
             }
             leaf num-fpc-update-failure {
               type int32;
               description "Number FPC information update send failed";
             }
           }
           container radius-partition-status {
             leaf partition {
               type string;
               description "Partition name";
             }
             leaf num-valid-accounting-start {
               type int32;
               description "Number of valid accounting start message received";
             }
             leaf num-valid-accounting-stop {
               type int32;
               description "Number of valid accounting stop message received";
             }
             leaf num-valid-interim-accounting {
               type int32;
               description "Number of valid interim accounting message received";
             }
             leaf num-invalid-accounting-start {
               type int32;
               description "Number of invalid accounting start message received";
             }
             leaf num-invalid-accounting-stop {
               type int32;
               description "Number of invalid accounting stop message received";
             }
             leaf num-invalid-interim-accounting {
               type int32;
               description "Number of invalid interim accounting message received";
             }
             leaf num-accounting-on {
               type int32;
               description "Number of accounting-on message received";
             }
             leaf num-accounting-off {
               type int32;
               description "Number of accounting-off message received";
             }
             leaf num-accounting-start-response {
               type int32;
               description "Number of accounting stop message responses sent";
             }
             leaf num-accounting-stop-response {
               type int32;
               description "Number of accounting stop message responses sent";
             }
             leaf num-interim-accounting-response {
               type int32;
               description "Number of interim accounting message responses sent";
             }
             leaf num-tagging {
               type int32;
               description "Number of tagging recevied";
             }
           }
         }
         container subscriber-session-summary {
           description "Subscriber session summary";
           leaf num-clients {
             type int32;
           }
         }
         container subscriber-session {
           description "Subscriber session information";
           container session-detail {
             description "Subscriber session information";
             leaf client-id {
               type string;
               description "Client ID";
             }
             leaf username {
               type string;
               description "User name";
             }
             leaf user-ip-address {
               type string;
               description "User IP address";
             }
             leaf interface {
               type string;
               description "Interface name";
             }
             leaf subscriber-state {
               type string;
               description "Session state";
             }
             leaf service-interface {
               type string;
               description "Service interface";
             }
             leaf routing-instance {
               type string;
               description "Routing instance name";
             }
             leaf login-time {
               type string;
               description "Login time";
             }
             leaf partition {
               type string;
               description "Partition name";
             }
             leaf profile {
               type string;
               description "Profile name";
             }
             leaf num-services {
               type int32;
               description "Number of services";
             }
             container service-session {
               description "Service session information";
               leaf policy-name {
                 type string;
                 description "Policy name";
               }
               leaf service-state {
                 type string;
                 description "Session state";
               }
             }
           }
           container session-brief {
             description "Subscriber session information";
             leaf client-id {
               type string;
               description "Client ID";
             }
             leaf user-ip-address {
               type string;
               description "User IP address";
             }
             leaf interface {
               type string;
               description "Interface name";
             }
             leaf username {
               type string;
               description "User name";
             }
             container service-session {
               description "Service session information";
               leaf policy-name {
                 type string;
                 description "Policy name";
               }
               leaf service-state {
                 type string;
                 description "Session state";
               }
             }
           }
         }
         container session-statistics {
           description "Session statistics";
           leaf session-type {
             type string;
             description "Session type";
           }
           leaf name-id {
             type string;
             description "Name or Id";
           }
           leaf input-packets {
             type int64;
             description "Number of input packets";
           }
           leaf output-packets {
             type int64;
             description "Number of output packets";
           }
           leaf input-bytes {
             type int64;
             description "Number of input bytes";
           }
           leaf output-bytes {
             type int64;
             description "Number of output bytes";
           }
         }
         container extra-statistics {
           description "Session statistics information provided by additional source";
           leaf statistics-string {
             type string;
             description "Statistics information in string format";
           }
         }
         container subscriber-policy {
           description "Dynamic policies";
           leaf client-id {
             type string;
             description "Client ID";
           }
           container service-policy {
             description "Service dynamic policy";
             leaf policy-name {
               type string;
               description "Policy name";
             }
             leaf rpr {
               type string;
               description "Precedence";
             }
             leaf d {
               type string;
               description "Direction";
             }
             container term {
               description "Term";
               leaf template-name {
                 type string;
                 description "Rule template";
               }
               leaf tpr {
                 type int32;
                 description "Term precedence";
               }
               leaf ra {
                 type string;
                 description "Remote address";
               }
               leaf rm {
                 type int32;
                 description "Remote mask";
               }
               leaf lpl {
                 type int32;
                 description "Local port range low";
               }
               leaf lph {
                 type int32;
                 description "Local port range high";
               }
               leaf rpl {
                 type int32;
                 description "Remote port range low";
               }
               leaf rph {
                 type int32;
                 description "Remote port range high";
               }
               leaf p {
                 type int32;
                 description "Protocol";
               }
               leaf anl {
                 type string;
                 description "Application name list";
               }
               leaf agl {
                 type string;
                 description "Application group list";
               }
               leaf nanl {
                 type string;
                 description "Nested application name list";
               }
               leaf a-f {
                 type string;
                 description "Flow action";
               }
               leaf a-s {
                 type string;
                 description "Stats action";
               }
               leaf a-fc {
                 type string;
                 description "Forwarding class";
               }
               leaf a-p-i {
                 type int32;
                 description "Policer instance";
               }
               leaf a-p-bw {
                 type int32;
                 description "Policer bandwidth";
               }
               leaf a-p-mbs {
                 type int32;
                 description "Policer maximum burst size";
               }
               leaf a-fu {
                 type int32;
                 description "Forwarding unit";
               }
               leaf opt-profile {
                 type int32;
                 description "Subscriber profile";
               }
             }
           }
           container radius-policy {
             description "Dynamic RADIUS policies";
             container policy-attribute {
               leaf attribute-name {
                 type string;
                 description "Radius attribute name";
               }
               leaf attribute-value {
                 type string;
                 description "Radius attribute value";
               }
             }
           }
         }
         container subscriber-flows {
           description "Flows";
           leaf client-id {
             type string;
             description "Client ID";
           }
           leaf num-data-sessions {
             type int32;
             description "Number of data sessions";
           }
           leaf hwm {
             type int32;
             description "High water mark";
           }
           container flows {
             description "Flows";
             leaf five-tuple {
               type string;
               description "5 tuple";
             }
             leaf application-id {
               type string;
               description "Appication-id";
             }
             leaf policy-name {
               type string;
               description "Policy name";
             }
             leaf policy-direction {
               type string;
               description "Direction";
             }
             leaf packets {
               type string;
               description "Packet";
             }
             leaf bytes {
               type string;
               description "Bytes";
             }
             leaf offload {
               type string;
               description "Offload status";
             }
             leaf policy-action {
               type string;
               description "Policy action";
             }
           }
         }
         container subscriber-bandwidth {
           description "Bandwidth";
           leaf client-id {
             type string;
             description "Client ID";
           }
           leaf input-pps {
             type int32;
             description "Input pps";
           }
           leaf output-pps {
             type int32;
             description "Output pps";
           }
           leaf input-bps {
             type int32;
             description "Input bps";
           }
           leaf output-bps {
             type int32;
             description "Output bps";
           }
         }
         container clear-session-result {
           description "Result of clear session request";
           leaf num-logout-initiated {
             type int32;
             description "Number of session logout request initiated";
           }
         }
         container service-subscribers-request-result {
           description "Result for service subscriber request";
           container failed {
             description "Result for service subscriber request";
             leaf request_failure {
               type string;
               description "Service subscriber request failed";
             }
           }
           container success {
             description "Result for service subscriber request";
             leaf request_success {
               type empty;
               description "Service subscriber request succeed";
             }
           }
         }
       }
     }
   }
   rpc get-services-subscriber-bandwidth-by-interface {
     description "By interface name";
     input {
       leaf interface-name {
         description "Client interface name";
         type interface-name;
         mandatory true;
       }
       leaf top-talkers {
         description "Top talkers";
         type uint32 {
           range "1 .. 50";
         }
         mandatory true;
       }
     }
     output {
       container packet-triggered-subscribers-information {
         leaf message {
           type string;
           description "Message to be displaed";
         }
         container process-status {
           description "Process status";
           leaf num-clients {
             type int32;
           }
           leaf src-connection-state {
             type string;
             description "SRC connection state";
           }
           leaf num-diameterd-connected {
             type int32;
             description "Number of diameterd connections established";
           }
           leaf num-diameterd-disconnected {
             type int32;
             description "Number of diameterd connections disconnected";
           }
           leaf full-sync-in-progress {
             type string;
             description "Full sync in progress";
           }
           leaf fast-sync-in-progress {
             type string;
             description "Fast sync in progress";
           }
           leaf num-full-sync-abort {
             type string;
             description "Number of full sync abort";
           }
           leaf num-fast-sync-abort {
             type string;
             description "Number of fast sync abort";
           }
           leaf num-srr-received {
             type int32;
             description "Number of SRR received";
           }
           leaf num-srr-failure {
             type int32;
             description "Number failure SRR received";
           }
           leaf num-srr-queued {
             type int32;
             description "Number of SRR send attempted";
           }
           leaf num-srq-queued {
             type int32;
             description "Number of SRQ send attempted";
           }
           leaf num-srq-full-sync {
             type int32;
             description "Number of SRQ full-sync";
           }
           leaf num-srq-fast-sync {
             type int32;
             description "Number of SRQ fast-sync";
           }
           leaf num-srq-single-sync {
             type int32;
             description "Number of SRQ single-sync";
           }
           leaf num-sending-message {
             type int32;
             description "Number of queued sending messages";
           }
           leaf num-sending-queue-full {
             type int32;
             description "Number of sending queue full event";
           }
           leaf num-sending-timeout {
             type int32;
             description "Number of sending messages timed out";
           }
           leaf num-response-timeout {
             type int32;
             description "Number of pending response timed out";
           }
           leaf num-waiting-message {
             type int32;
             description "Number of messages waiting for response";
           }
           leaf num-ppr-received {
             type int32;
             description "Number of PPR received";
           }
           leaf num-asr-received {
             type int32;
             description "Number of ASR received";
           }
           leaf num-acr-received {
             type int32;
             description "Number of ACR received";
           }
           leaf num-aaa-received {
             type int32;
             description "Number of AAA received";
           }
           leaf num-sta-received {
             type int32;
             description "Number of STA received";
           }
           leaf num-sync-aaa-received {
             type int32;
             description "Number of sync AAA received";
           }
           leaf num-sync-sta-received {
             type int32;
             description "Number of sync STA received";
           }
           leaf num-aar-queued {
             type int32;
             description "Number of AAR send attempted";
           }
           leaf num-ppa-queued {
             type int32;
             description "Number of PPA send attempted";
           }
           leaf num-str-queued {
             type int32;
             description "Number of STR send attempted";
           }
           leaf num-asa-queued {
             type int32;
             description "Number of ASA send attempted";
           }
           leaf num-aca-queued {
             type int32;
             description "Number of ACA send attempted";
           }
           leaf num-sync-aar-queued {
             type int32;
             description "Number of sync AAR send attempted";
           }
           leaf num-sync-str-queued {
             type int32;
             description "Number of sync STR send attempted";
           }
           leaf num-srq-timeout {
             type int32;
             description "Number of SRQ timed out";
           }
           leaf num-str-timeout {
             type int32;
             description "Number of STR timed out";
           }
           leaf num-aar-timeout {
             type int32;
             description "Number of AAR timed out";
           }
           leaf num-aar-send-failure {
             type int32;
             description "Number of AAR send failed";
           }
           leaf num-asa-send-failure {
             type int32;
             description "Number of ASR send failed";
           }
           leaf num-aca-send-failure {
             type int32;
             description "Number of ACR send failed";
           }
           leaf num-ppa-send-failure {
             type int32;
             description "Number of PPA send failed";
           }
           leaf num-str-send-failure {
             type int32;
             description "Number of STR send failed";
           }
           leaf num-srq-send-failure {
             type int32;
             description "Number of SRQ send failed";
           }
           leaf num-srr-send-failure {
             type int32;
             description "Number of SRR send failed";
           }
           leaf num-sync-aar-send-failure {
             type int32;
             description "Number of AAR send failed";
           }
           leaf num-sync-str-send-failure {
             type int32;
             description "Number of STR send failed";
           }
           leaf num-sync-aar-timeout {
             type int32;
             description "Number of sync-AAR timed out";
           }
           leaf num-sync-str-timeout {
             type int32;
             description "Number of sync-STR timed out";
           }
           leaf num-fast-sync-queued {
             type int32;
             description "Number of fast-sync messages queued";
           }
           leaf num-queued-diameter-task {
             type int32;
             description "Number of diameter tasks queued";
           }
           leaf num-down-pic-clients {
             type int32;
             description "Number of ready-to-logout client session dur to PIC down";
           }
           leaf first-down-pic-client-id {
             type int64;
             description "First ready-to-logout client session ID";
           }
           leaf num-outstanding-diameter-message {
             type string;
             description "Number of outstanding diameter messages";
           }
           leaf num-login-retry {
             type string;
             description "Number of subscriber login retry with SRC";
           }
           leaf num-pconn {
             type int32;
             description "Number of pconn connections";
           }
           container pic-status {
             leaf pic-name {
               type string;
               description "Service PIC name";
             }
             leaf num-pic-login {
               type int32;
               description "Number of PIC login request";
             }
             leaf num-pic-logout-response {
               type int32;
               description "Number of PIC logout response";
             }
             leaf num-login-done {
               type int32;
               description "Number of PIC login done";
             }
             leaf num-pic-logout {
               type int32;
               description "Number of PIC logout request";
             }
             leaf num-policy-change {
               type int32;
               description "Number of policy changes request";
             }
             leaf num-policy-change-response {
               type int32;
               description "Number of policy changes response";
             }
             leaf num-src-logout {
               type int32;
               description "Number of SRC logout request";
             }
             leaf num-statistics-polling {
               type int32;
               description "Number of SRC statistics polling";
             }
             leaf num-sync-start {
               type int32;
               description "Number of PIC sync start request";
             }
             leaf num-sync-request {
               type int32;
               description "Number of PIC sync subscriber request";
             }
             leaf num-update-username {
               type int32;
               description "Number of username update request";
             }
             leaf num-pre-announcement {
               type int32;
               description "Number of pre-announcement";
             }
             leaf num-idle-timeout-update {
               type int32;
               description "Number of idle timeout configuraiton update";
             }
             leaf num-connection-up-event {
               type int32;
               description "Number of PCONN established event";
             }
             leaf num-pending-response {
               type int32;
               description "Number of request waiting for PIC to response";
             }
             leaf num-queued-pic-task {
               type int32;
               description "Number of PIC tasks queued";
             }
             leaf num-service-request-timeout {
               type int32;
               description "Number of service request timed out waiting for PIC response";
             }
             leaf num-logout-request-timeout {
               type int32;
               description "Number of logout request timed out waiting for PIC response";
             }
             leaf num-logout-request-send-failure {
               type int32;
               description "Number of logout request send failed";
             }
             leaf num-service-request-send-failure {
               type int32;
               description "Number of service request send failed";
             }
             leaf num-accounting-request-send-failure {
               type int32;
               description "Number of accounting request send failed";
             }
             leaf num-login-done-send-failure {
               type int32;
               description "Number of login done send failed";
             }
             leaf num-username-update-send-failure {
               type int32;
               description "Number of username update send failed";
             }
             leaf num-pre-announcement-send-failure {
               type int32;
               description "Number of pre-announcement send failed";
             }
             leaf num-idle-timeout-update-send-failure {
               type int32;
               description "Number of idle timeout configuraiton update send failed";
             }
             leaf num-service-set-update {
               type int32;
               description "Number of service-set update";
             }
             leaf num-service-set-update-send-failure {
               type int32;
               description "Number of service-set update send failed";
             }
             leaf num-partition-update-send {
               type int32;
               description "Number of partition update";
             }
             leaf num-partition-update-send-failure {
               type int32;
               description "Number of partition update send failed";
             }
             leaf num-subscriber-profiles-update {
               type int32;
               description "Number subscriber profile update";
             }
             leaf num-subscriber-profiles-update-failure {
               type int32;
               description "Number subscriber profile update send failed ";
             }
             leaf num-service-set-subscriber-profiles-mapping-update {
               type int32;
               description "Number service-set subscriber profile update";
             }
             leaf num-service-set-subscriber-profiles-mapping-update-failure {
               type int32;
               description "Number service-set subscriber profile update send failed";
             }
             leaf num-set-profile {
               type int32;
               description "Number set profile request";
             }
             leaf num-set-profile-failure {
               type int32;
               description "Number set profile request send failed";
             }
             leaf num-clear-profile {
               type int32;
               description "Number clear profile request";
             }
             leaf num-clear-profile-failure {
               type int32;
               description "Number clear profile request send failed";
             }
             leaf num-fpc-update {
               type int32;
               description "Number FPC information update";
             }
             leaf num-fpc-update-failure {
               type int32;
               description "Number FPC information update send failed";
             }
           }
           container radius-partition-status {
             leaf partition {
               type string;
               description "Partition name";
             }
             leaf num-valid-accounting-start {
               type int32;
               description "Number of valid accounting start message received";
             }
             leaf num-valid-accounting-stop {
               type int32;
               description "Number of valid accounting stop message received";
             }
             leaf num-valid-interim-accounting {
               type int32;
               description "Number of valid interim accounting message received";
             }
             leaf num-invalid-accounting-start {
               type int32;
               description "Number of invalid accounting start message received";
             }
             leaf num-invalid-accounting-stop {
               type int32;
               description "Number of invalid accounting stop message received";
             }
             leaf num-invalid-interim-accounting {
               type int32;
               description "Number of invalid interim accounting message received";
             }
             leaf num-accounting-on {
               type int32;
               description "Number of accounting-on message received";
             }
             leaf num-accounting-off {
               type int32;
               description "Number of accounting-off message received";
             }
             leaf num-accounting-start-response {
               type int32;
               description "Number of accounting stop message responses sent";
             }
             leaf num-accounting-stop-response {
               type int32;
               description "Number of accounting stop message responses sent";
             }
             leaf num-interim-accounting-response {
               type int32;
               description "Number of interim accounting message responses sent";
             }
             leaf num-tagging {
               type int32;
               description "Number of tagging recevied";
             }
           }
         }
         container subscriber-session-summary {
           description "Subscriber session summary";
           leaf num-clients {
             type int32;
           }
         }
         container subscriber-session {
           description "Subscriber session information";
           container session-detail {
             description "Subscriber session information";
             leaf client-id {
               type string;
               description "Client ID";
             }
             leaf username {
               type string;
               description "User name";
             }
             leaf user-ip-address {
               type string;
               description "User IP address";
             }
             leaf interface {
               type string;
               description "Interface name";
             }
             leaf subscriber-state {
               type string;
               description "Session state";
             }
             leaf service-interface {
               type string;
               description "Service interface";
             }
             leaf routing-instance {
               type string;
               description "Routing instance name";
             }
             leaf login-time {
               type string;
               description "Login time";
             }
             leaf partition {
               type string;
               description "Partition name";
             }
             leaf profile {
               type string;
               description "Profile name";
             }
             leaf num-services {
               type int32;
               description "Number of services";
             }
             container service-session {
               description "Service session information";
               leaf policy-name {
                 type string;
                 description "Policy name";
               }
               leaf service-state {
                 type string;
                 description "Session state";
               }
             }
           }
           container session-brief {
             description "Subscriber session information";
             leaf client-id {
               type string;
               description "Client ID";
             }
             leaf user-ip-address {
               type string;
               description "User IP address";
             }
             leaf interface {
               type string;
               description "Interface name";
             }
             leaf username {
               type string;
               description "User name";
             }
             container service-session {
               description "Service session information";
               leaf policy-name {
                 type string;
                 description "Policy name";
               }
               leaf service-state {
                 type string;
                 description "Session state";
               }
             }
           }
         }
         container session-statistics {
           description "Session statistics";
           leaf session-type {
             type string;
             description "Session type";
           }
           leaf name-id {
             type string;
             description "Name or Id";
           }
           leaf input-packets {
             type int64;
             description "Number of input packets";
           }
           leaf output-packets {
             type int64;
             description "Number of output packets";
           }
           leaf input-bytes {
             type int64;
             description "Number of input bytes";
           }
           leaf output-bytes {
             type int64;
             description "Number of output bytes";
           }
         }
         container extra-statistics {
           description "Session statistics information provided by additional source";
           leaf statistics-string {
             type string;
             description "Statistics information in string format";
           }
         }
         container subscriber-policy {
           description "Dynamic policies";
           leaf client-id {
             type string;
             description "Client ID";
           }
           container service-policy {
             description "Service dynamic policy";
             leaf policy-name {
               type string;
               description "Policy name";
             }
             leaf rpr {
               type string;
               description "Precedence";
             }
             leaf d {
               type string;
               description "Direction";
             }
             container term {
               description "Term";
               leaf template-name {
                 type string;
                 description "Rule template";
               }
               leaf tpr {
                 type int32;
                 description "Term precedence";
               }
               leaf ra {
                 type string;
                 description "Remote address";
               }
               leaf rm {
                 type int32;
                 description "Remote mask";
               }
               leaf lpl {
                 type int32;
                 description "Local port range low";
               }
               leaf lph {
                 type int32;
                 description "Local port range high";
               }
               leaf rpl {
                 type int32;
                 description "Remote port range low";
               }
               leaf rph {
                 type int32;
                 description "Remote port range high";
               }
               leaf p {
                 type int32;
                 description "Protocol";
               }
               leaf anl {
                 type string;
                 description "Application name list";
               }
               leaf agl {
                 type string;
                 description "Application group list";
               }
               leaf nanl {
                 type string;
                 description "Nested application name list";
               }
               leaf a-f {
                 type string;
                 description "Flow action";
               }
               leaf a-s {
                 type string;
                 description "Stats action";
               }
               leaf a-fc {
                 type string;
                 description "Forwarding class";
               }
               leaf a-p-i {
                 type int32;
                 description "Policer instance";
               }
               leaf a-p-bw {
                 type int32;
                 description "Policer bandwidth";
               }
               leaf a-p-mbs {
                 type int32;
                 description "Policer maximum burst size";
               }
               leaf a-fu {
                 type int32;
                 description "Forwarding unit";
               }
               leaf opt-profile {
                 type int32;
                 description "Subscriber profile";
               }
             }
           }
           container radius-policy {
             description "Dynamic RADIUS policies";
             container policy-attribute {
               leaf attribute-name {
                 type string;
                 description "Radius attribute name";
               }
               leaf attribute-value {
                 type string;
                 description "Radius attribute value";
               }
             }
           }
         }
         container subscriber-flows {
           description "Flows";
           leaf client-id {
             type string;
             description "Client ID";
           }
           leaf num-data-sessions {
             type int32;
             description "Number of data sessions";
           }
           leaf hwm {
             type int32;
             description "High water mark";
           }
           container flows {
             description "Flows";
             leaf five-tuple {
               type string;
               description "5 tuple";
             }
             leaf application-id {
               type string;
               description "Appication-id";
             }
             leaf policy-name {
               type string;
               description "Policy name";
             }
             leaf policy-direction {
               type string;
               description "Direction";
             }
             leaf packets {
               type string;
               description "Packet";
             }
             leaf bytes {
               type string;
               description "Bytes";
             }
             leaf offload {
               type string;
               description "Offload status";
             }
             leaf policy-action {
               type string;
               description "Policy action";
             }
           }
         }
         container subscriber-bandwidth {
           description "Bandwidth";
           leaf client-id {
             type string;
             description "Client ID";
           }
           leaf input-pps {
             type int32;
             description "Input pps";
           }
           leaf output-pps {
             type int32;
             description "Output pps";
           }
           leaf input-bps {
             type int32;
             description "Input bps";
           }
           leaf output-bps {
             type int32;
             description "Output bps";
           }
         }
         container clear-session-result {
           description "Result of clear session request";
           leaf num-logout-initiated {
             type int32;
             description "Number of session logout request initiated";
           }
         }
         container service-subscribers-request-result {
           description "Result for service subscriber request";
           container failed {
             description "Result for service subscriber request";
             leaf request_failure {
               type string;
               description "Service subscriber request failed";
             }
           }
           container success {
             description "Result for service subscriber request";
             leaf request_success {
               type empty;
               description "Service subscriber request succeed";
             }
           }
         }
       }
     }
   }
   rpc get-services-subscriber-bandwidth-by-service-interface {
     description "By MS-PIC name";
     input {
       leaf service-interface {
         description "Client MS-PIC name";
         type string;
         mandatory true;
       }
       leaf top-talkers {
         description "Top talkers";
         type uint32 {
           range "1 .. 50";
         }
         mandatory true;
       }
     }
     output {
       container packet-triggered-subscribers-information {
         leaf message {
           type string;
           description "Message to be displaed";
         }
         container process-status {
           description "Process status";
           leaf num-clients {
             type int32;
           }
           leaf src-connection-state {
             type string;
             description "SRC connection state";
           }
           leaf num-diameterd-connected {
             type int32;
             description "Number of diameterd connections established";
           }
           leaf num-diameterd-disconnected {
             type int32;
             description "Number of diameterd connections disconnected";
           }
           leaf full-sync-in-progress {
             type string;
             description "Full sync in progress";
           }
           leaf fast-sync-in-progress {
             type string;
             description "Fast sync in progress";
           }
           leaf num-full-sync-abort {
             type string;
             description "Number of full sync abort";
           }
           leaf num-fast-sync-abort {
             type string;
             description "Number of fast sync abort";
           }
           leaf num-srr-received {
             type int32;
             description "Number of SRR received";
           }
           leaf num-srr-failure {
             type int32;
             description "Number failure SRR received";
           }
           leaf num-srr-queued {
             type int32;
             description "Number of SRR send attempted";
           }
           leaf num-srq-queued {
             type int32;
             description "Number of SRQ send attempted";
           }
           leaf num-srq-full-sync {
             type int32;
             description "Number of SRQ full-sync";
           }
           leaf num-srq-fast-sync {
             type int32;
             description "Number of SRQ fast-sync";
           }
           leaf num-srq-single-sync {
             type int32;
             description "Number of SRQ single-sync";
           }
           leaf num-sending-message {
             type int32;
             description "Number of queued sending messages";
           }
           leaf num-sending-queue-full {
             type int32;
             description "Number of sending queue full event";
           }
           leaf num-sending-timeout {
             type int32;
             description "Number of sending messages timed out";
           }
           leaf num-response-timeout {
             type int32;
             description "Number of pending response timed out";
           }
           leaf num-waiting-message {
             type int32;
             description "Number of messages waiting for response";
           }
           leaf num-ppr-received {
             type int32;
             description "Number of PPR received";
           }
           leaf num-asr-received {
             type int32;
             description "Number of ASR received";
           }
           leaf num-acr-received {
             type int32;
             description "Number of ACR received";
           }
           leaf num-aaa-received {
             type int32;
             description "Number of AAA received";
           }
           leaf num-sta-received {
             type int32;
             description "Number of STA received";
           }
           leaf num-sync-aaa-received {
             type int32;
             description "Number of sync AAA received";
           }
           leaf num-sync-sta-received {
             type int32;
             description "Number of sync STA received";
           }
           leaf num-aar-queued {
             type int32;
             description "Number of AAR send attempted";
           }
           leaf num-ppa-queued {
             type int32;
             description "Number of PPA send attempted";
           }
           leaf num-str-queued {
             type int32;
             description "Number of STR send attempted";
           }
           leaf num-asa-queued {
             type int32;
             description "Number of ASA send attempted";
           }
           leaf num-aca-queued {
             type int32;
             description "Number of ACA send attempted";
           }
           leaf num-sync-aar-queued {
             type int32;
             description "Number of sync AAR send attempted";
           }
           leaf num-sync-str-queued {
             type int32;
             description "Number of sync STR send attempted";
           }
           leaf num-srq-timeout {
             type int32;
             description "Number of SRQ timed out";
           }
           leaf num-str-timeout {
             type int32;
             description "Number of STR timed out";
           }
           leaf num-aar-timeout {
             type int32;
             description "Number of AAR timed out";
           }
           leaf num-aar-send-failure {
             type int32;
             description "Number of AAR send failed";
           }
           leaf num-asa-send-failure {
             type int32;
             description "Number of ASR send failed";
           }
           leaf num-aca-send-failure {
             type int32;
             description "Number of ACR send failed";
           }
           leaf num-ppa-send-failure {
             type int32;
             description "Number of PPA send failed";
           }
           leaf num-str-send-failure {
             type int32;
             description "Number of STR send failed";
           }
           leaf num-srq-send-failure {
             type int32;
             description "Number of SRQ send failed";
           }
           leaf num-srr-send-failure {
             type int32;
             description "Number of SRR send failed";
           }
           leaf num-sync-aar-send-failure {
             type int32;
             description "Number of AAR send failed";
           }
           leaf num-sync-str-send-failure {
             type int32;
             description "Number of STR send failed";
           }
           leaf num-sync-aar-timeout {
             type int32;
             description "Number of sync-AAR timed out";
           }
           leaf num-sync-str-timeout {
             type int32;
             description "Number of sync-STR timed out";
           }
           leaf num-fast-sync-queued {
             type int32;
             description "Number of fast-sync messages queued";
           }
           leaf num-queued-diameter-task {
             type int32;
             description "Number of diameter tasks queued";
           }
           leaf num-down-pic-clients {
             type int32;
             description "Number of ready-to-logout client session dur to PIC down";
           }
           leaf first-down-pic-client-id {
             type int64;
             description "First ready-to-logout client session ID";
           }
           leaf num-outstanding-diameter-message {
             type string;
             description "Number of outstanding diameter messages";
           }
           leaf num-login-retry {
             type string;
             description "Number of subscriber login retry with SRC";
           }
           leaf num-pconn {
             type int32;
             description "Number of pconn connections";
           }
           container pic-status {
             leaf pic-name {
               type string;
               description "Service PIC name";
             }
             leaf num-pic-login {
               type int32;
               description "Number of PIC login request";
             }
             leaf num-pic-logout-response {
               type int32;
               description "Number of PIC logout response";
             }
             leaf num-login-done {
               type int32;
               description "Number of PIC login done";
             }
             leaf num-pic-logout {
               type int32;
               description "Number of PIC logout request";
             }
             leaf num-policy-change {
               type int32;
               description "Number of policy changes request";
             }
             leaf num-policy-change-response {
               type int32;
               description "Number of policy changes response";
             }
             leaf num-src-logout {
               type int32;
               description "Number of SRC logout request";
             }
             leaf num-statistics-polling {
               type int32;
               description "Number of SRC statistics polling";
             }
             leaf num-sync-start {
               type int32;
               description "Number of PIC sync start request";
             }
             leaf num-sync-request {
               type int32;
               description "Number of PIC sync subscriber request";
             }
             leaf num-update-username {
               type int32;
               description "Number of username update request";
             }
             leaf num-pre-announcement {
               type int32;
               description "Number of pre-announcement";
             }
             leaf num-idle-timeout-update {
               type int32;
               description "Number of idle timeout configuraiton update";
             }
             leaf num-connection-up-event {
               type int32;
               description "Number of PCONN established event";
             }
             leaf num-pending-response {
               type int32;
               description "Number of request waiting for PIC to response";
             }
             leaf num-queued-pic-task {
               type int32;
               description "Number of PIC tasks queued";
             }
             leaf num-service-request-timeout {
               type int32;
               description "Number of service request timed out waiting for PIC response";
             }
             leaf num-logout-request-timeout {
               type int32;
               description "Number of logout request timed out waiting for PIC response";
             }
             leaf num-logout-request-send-failure {
               type int32;
               description "Number of logout request send failed";
             }
             leaf num-service-request-send-failure {
               type int32;
               description "Number of service request send failed";
             }
             leaf num-accounting-request-send-failure {
               type int32;
               description "Number of accounting request send failed";
             }
             leaf num-login-done-send-failure {
               type int32;
               description "Number of login done send failed";
             }
             leaf num-username-update-send-failure {
               type int32;
               description "Number of username update send failed";
             }
             leaf num-pre-announcement-send-failure {
               type int32;
               description "Number of pre-announcement send failed";
             }
             leaf num-idle-timeout-update-send-failure {
               type int32;
               description "Number of idle timeout configuraiton update send failed";
             }
             leaf num-service-set-update {
               type int32;
               description "Number of service-set update";
             }
             leaf num-service-set-update-send-failure {
               type int32;
               description "Number of service-set update send failed";
             }
             leaf num-partition-update-send {
               type int32;
               description "Number of partition update";
             }
             leaf num-partition-update-send-failure {
               type int32;
               description "Number of partition update send failed";
             }
             leaf num-subscriber-profiles-update {
               type int32;
               description "Number subscriber profile update";
             }
             leaf num-subscriber-profiles-update-failure {
               type int32;
               description "Number subscriber profile update send failed ";
             }
             leaf num-service-set-subscriber-profiles-mapping-update {
               type int32;
               description "Number service-set subscriber profile update";
             }
             leaf num-service-set-subscriber-profiles-mapping-update-failure {
               type int32;
               description "Number service-set subscriber profile update send failed";
             }
             leaf num-set-profile {
               type int32;
               description "Number set profile request";
             }
             leaf num-set-profile-failure {
               type int32;
               description "Number set profile request send failed";
             }
             leaf num-clear-profile {
               type int32;
               description "Number clear profile request";
             }
             leaf num-clear-profile-failure {
               type int32;
               description "Number clear profile request send failed";
             }
             leaf num-fpc-update {
               type int32;
               description "Number FPC information update";
             }
             leaf num-fpc-update-failure {
               type int32;
               description "Number FPC information update send failed";
             }
           }
           container radius-partition-status {
             leaf partition {
               type string;
               description "Partition name";
             }
             leaf num-valid-accounting-start {
               type int32;
               description "Number of valid accounting start message received";
             }
             leaf num-valid-accounting-stop {
               type int32;
               description "Number of valid accounting stop message received";
             }
             leaf num-valid-interim-accounting {
               type int32;
               description "Number of valid interim accounting message received";
             }
             leaf num-invalid-accounting-start {
               type int32;
               description "Number of invalid accounting start message received";
             }
             leaf num-invalid-accounting-stop {
               type int32;
               description "Number of invalid accounting stop message received";
             }
             leaf num-invalid-interim-accounting {
               type int32;
               description "Number of invalid interim accounting message received";
             }
             leaf num-accounting-on {
               type int32;
               description "Number of accounting-on message received";
             }
             leaf num-accounting-off {
               type int32;
               description "Number of accounting-off message received";
             }
             leaf num-accounting-start-response {
               type int32;
               description "Number of accounting stop message responses sent";
             }
             leaf num-accounting-stop-response {
               type int32;
               description "Number of accounting stop message responses sent";
             }
             leaf num-interim-accounting-response {
               type int32;
               description "Number of interim accounting message responses sent";
             }
             leaf num-tagging {
               type int32;
               description "Number of tagging recevied";
             }
           }
         }
         container subscriber-session-summary {
           description "Subscriber session summary";
           leaf num-clients {
             type int32;
           }
         }
         container subscriber-session {
           description "Subscriber session information";
           container session-detail {
             description "Subscriber session information";
             leaf client-id {
               type string;
               description "Client ID";
             }
             leaf username {
               type string;
               description "User name";
             }
             leaf user-ip-address {
               type string;
               description "User IP address";
             }
             leaf interface {
               type string;
               description "Interface name";
             }
             leaf subscriber-state {
               type string;
               description "Session state";
             }
             leaf service-interface {
               type string;
               description "Service interface";
             }
             leaf routing-instance {
               type string;
               description "Routing instance name";
             }
             leaf login-time {
               type string;
               description "Login time";
             }
             leaf partition {
               type string;
               description "Partition name";
             }
             leaf profile {
               type string;
               description "Profile name";
             }
             leaf num-services {
               type int32;
               description "Number of services";
             }
             container service-session {
               description "Service session information";
               leaf policy-name {
                 type string;
                 description "Policy name";
               }
               leaf service-state {
                 type string;
                 description "Session state";
               }
             }
           }
           container session-brief {
             description "Subscriber session information";
             leaf client-id {
               type string;
               description "Client ID";
             }
             leaf user-ip-address {
               type string;
               description "User IP address";
             }
             leaf interface {
               type string;
               description "Interface name";
             }
             leaf username {
               type string;
               description "User name";
             }
             container service-session {
               description "Service session information";
               leaf policy-name {
                 type string;
                 description "Policy name";
               }
               leaf service-state {
                 type string;
                 description "Session state";
               }
             }
           }
         }
         container session-statistics {
           description "Session statistics";
           leaf session-type {
             type string;
             description "Session type";
           }
           leaf name-id {
             type string;
             description "Name or Id";
           }
           leaf input-packets {
             type int64;
             description "Number of input packets";
           }
           leaf output-packets {
             type int64;
             description "Number of output packets";
           }
           leaf input-bytes {
             type int64;
             description "Number of input bytes";
           }
           leaf output-bytes {
             type int64;
             description "Number of output bytes";
           }
         }
         container extra-statistics {
           description "Session statistics information provided by additional source";
           leaf statistics-string {
             type string;
             description "Statistics information in string format";
           }
         }
         container subscriber-policy {
           description "Dynamic policies";
           leaf client-id {
             type string;
             description "Client ID";
           }
           container service-policy {
             description "Service dynamic policy";
             leaf policy-name {
               type string;
               description "Policy name";
             }
             leaf rpr {
               type string;
               description "Precedence";
             }
             leaf d {
               type string;
               description "Direction";
             }
             container term {
               description "Term";
               leaf template-name {
                 type string;
                 description "Rule template";
               }
               leaf tpr {
                 type int32;
                 description "Term precedence";
               }
               leaf ra {
                 type string;
                 description "Remote address";
               }
               leaf rm {
                 type int32;
                 description "Remote mask";
               }
               leaf lpl {
                 type int32;
                 description "Local port range low";
               }
               leaf lph {
                 type int32;
                 description "Local port range high";
               }
               leaf rpl {
                 type int32;
                 description "Remote port range low";
               }
               leaf rph {
                 type int32;
                 description "Remote port range high";
               }
               leaf p {
                 type int32;
                 description "Protocol";
               }
               leaf anl {
                 type string;
                 description "Application name list";
               }
               leaf agl {
                 type string;
                 description "Application group list";
               }
               leaf nanl {
                 type string;
                 description "Nested application name list";
               }
               leaf a-f {
                 type string;
                 description "Flow action";
               }
               leaf a-s {
                 type string;
                 description "Stats action";
               }
               leaf a-fc {
                 type string;
                 description "Forwarding class";
               }
               leaf a-p-i {
                 type int32;
                 description "Policer instance";
               }
               leaf a-p-bw {
                 type int32;
                 description "Policer bandwidth";
               }
               leaf a-p-mbs {
                 type int32;
                 description "Policer maximum burst size";
               }
               leaf a-fu {
                 type int32;
                 description "Forwarding unit";
               }
               leaf opt-profile {
                 type int32;
                 description "Subscriber profile";
               }
             }
           }
           container radius-policy {
             description "Dynamic RADIUS policies";
             container policy-attribute {
               leaf attribute-name {
                 type string;
                 description "Radius attribute name";
               }
               leaf attribute-value {
                 type string;
                 description "Radius attribute value";
               }
             }
           }
         }
         container subscriber-flows {
           description "Flows";
           leaf client-id {
             type string;
             description "Client ID";
           }
           leaf num-data-sessions {
             type int32;
             description "Number of data sessions";
           }
           leaf hwm {
             type int32;
             description "High water mark";
           }
           container flows {
             description "Flows";
             leaf five-tuple {
               type string;
               description "5 tuple";
             }
             leaf application-id {
               type string;
               description "Appication-id";
             }
             leaf policy-name {
               type string;
               description "Policy name";
             }
             leaf policy-direction {
               type string;
               description "Direction";
             }
             leaf packets {
               type string;
               description "Packet";
             }
             leaf bytes {
               type string;
               description "Bytes";
             }
             leaf offload {
               type string;
               description "Offload status";
             }
             leaf policy-action {
               type string;
               description "Policy action";
             }
           }
         }
         container subscriber-bandwidth {
           description "Bandwidth";
           leaf client-id {
             type string;
             description "Client ID";
           }
           leaf input-pps {
             type int32;
             description "Input pps";
           }
           leaf output-pps {
             type int32;
             description "Output pps";
           }
           leaf input-bps {
             type int32;
             description "Input bps";
           }
           leaf output-bps {
             type int32;
             description "Output bps";
           }
         }
         container clear-session-result {
           description "Result of clear session request";
           leaf num-logout-initiated {
             type int32;
             description "Number of session logout request initiated";
           }
         }
         container service-subscribers-request-result {
           description "Result for service subscriber request";
           container failed {
             description "Result for service subscriber request";
             leaf request_failure {
               type string;
               description "Service subscriber request failed";
             }
           }
           container success {
             description "Result for service subscriber request";
             leaf request_success {
               type empty;
               description "Service subscriber request succeed";
             }
           }
         }
       }
     }
   }
   rpc get-services-subscriber-dynamic-policies {
     description "Dynamic policy";
     input {
       leaf client-id {
         description "Client identifier";
         type uint64;
         mandatory true;
       }
     }
     output {
       container packet-triggered-subscribers-information {
         leaf message {
           type string;
           description "Message to be displaed";
         }
         container process-status {
           description "Process status";
           leaf num-clients {
             type int32;
           }
           leaf src-connection-state {
             type string;
             description "SRC connection state";
           }
           leaf num-diameterd-connected {
             type int32;
             description "Number of diameterd connections established";
           }
           leaf num-diameterd-disconnected {
             type int32;
             description "Number of diameterd connections disconnected";
           }
           leaf full-sync-in-progress {
             type string;
             description "Full sync in progress";
           }
           leaf fast-sync-in-progress {
             type string;
             description "Fast sync in progress";
           }
           leaf num-full-sync-abort {
             type string;
             description "Number of full sync abort";
           }
           leaf num-fast-sync-abort {
             type string;
             description "Number of fast sync abort";
           }
           leaf num-srr-received {
             type int32;
             description "Number of SRR received";
           }
           leaf num-srr-failure {
             type int32;
             description "Number failure SRR received";
           }
           leaf num-srr-queued {
             type int32;
             description "Number of SRR send attempted";
           }
           leaf num-srq-queued {
             type int32;
             description "Number of SRQ send attempted";
           }
           leaf num-srq-full-sync {
             type int32;
             description "Number of SRQ full-sync";
           }
           leaf num-srq-fast-sync {
             type int32;
             description "Number of SRQ fast-sync";
           }
           leaf num-srq-single-sync {
             type int32;
             description "Number of SRQ single-sync";
           }
           leaf num-sending-message {
             type int32;
             description "Number of queued sending messages";
           }
           leaf num-sending-queue-full {
             type int32;
             description "Number of sending queue full event";
           }
           leaf num-sending-timeout {
             type int32;
             description "Number of sending messages timed out";
           }
           leaf num-response-timeout {
             type int32;
             description "Number of pending response timed out";
           }
           leaf num-waiting-message {
             type int32;
             description "Number of messages waiting for response";
           }
           leaf num-ppr-received {
             type int32;
             description "Number of PPR received";
           }
           leaf num-asr-received {
             type int32;
             description "Number of ASR received";
           }
           leaf num-acr-received {
             type int32;
             description "Number of ACR received";
           }
           leaf num-aaa-received {
             type int32;
             description "Number of AAA received";
           }
           leaf num-sta-received {
             type int32;
             description "Number of STA received";
           }
           leaf num-sync-aaa-received {
             type int32;
             description "Number of sync AAA received";
           }
           leaf num-sync-sta-received {
             type int32;
             description "Number of sync STA received";
           }
           leaf num-aar-queued {
             type int32;
             description "Number of AAR send attempted";
           }
           leaf num-ppa-queued {
             type int32;
             description "Number of PPA send attempted";
           }
           leaf num-str-queued {
             type int32;
             description "Number of STR send attempted";
           }
           leaf num-asa-queued {
             type int32;
             description "Number of ASA send attempted";
           }
           leaf num-aca-queued {
             type int32;
             description "Number of ACA send attempted";
           }
           leaf num-sync-aar-queued {
             type int32;
             description "Number of sync AAR send attempted";
           }
           leaf num-sync-str-queued {
             type int32;
             description "Number of sync STR send attempted";
           }
           leaf num-srq-timeout {
             type int32;
             description "Number of SRQ timed out";
           }
           leaf num-str-timeout {
             type int32;
             description "Number of STR timed out";
           }
           leaf num-aar-timeout {
             type int32;
             description "Number of AAR timed out";
           }
           leaf num-aar-send-failure {
             type int32;
             description "Number of AAR send failed";
           }
           leaf num-asa-send-failure {
             type int32;
             description "Number of ASR send failed";
           }
           leaf num-aca-send-failure {
             type int32;
             description "Number of ACR send failed";
           }
           leaf num-ppa-send-failure {
             type int32;
             description "Number of PPA send failed";
           }
           leaf num-str-send-failure {
             type int32;
             description "Number of STR send failed";
           }
           leaf num-srq-send-failure {
             type int32;
             description "Number of SRQ send failed";
           }
           leaf num-srr-send-failure {
             type int32;
             description "Number of SRR send failed";
           }
           leaf num-sync-aar-send-failure {
             type int32;
             description "Number of AAR send failed";
           }
           leaf num-sync-str-send-failure {
             type int32;
             description "Number of STR send failed";
           }
           leaf num-sync-aar-timeout {
             type int32;
             description "Number of sync-AAR timed out";
           }
           leaf num-sync-str-timeout {
             type int32;
             description "Number of sync-STR timed out";
           }
           leaf num-fast-sync-queued {
             type int32;
             description "Number of fast-sync messages queued";
           }
           leaf num-queued-diameter-task {
             type int32;
             description "Number of diameter tasks queued";
           }
           leaf num-down-pic-clients {
             type int32;
             description "Number of ready-to-logout client session dur to PIC down";
           }
           leaf first-down-pic-client-id {
             type int64;
             description "First ready-to-logout client session ID";
           }
           leaf num-outstanding-diameter-message {
             type string;
             description "Number of outstanding diameter messages";
           }
           leaf num-login-retry {
             type string;
             description "Number of subscriber login retry with SRC";
           }
           leaf num-pconn {
             type int32;
             description "Number of pconn connections";
           }
           container pic-status {
             leaf pic-name {
               type string;
               description "Service PIC name";
             }
             leaf num-pic-login {
               type int32;
               description "Number of PIC login request";
             }
             leaf num-pic-logout-response {
               type int32;
               description "Number of PIC logout response";
             }
             leaf num-login-done {
               type int32;
               description "Number of PIC login done";
             }
             leaf num-pic-logout {
               type int32;
               description "Number of PIC logout request";
             }
             leaf num-policy-change {
               type int32;
               description "Number of policy changes request";
             }
             leaf num-policy-change-response {
               type int32;
               description "Number of policy changes response";
             }
             leaf num-src-logout {
               type int32;
               description "Number of SRC logout request";
             }
             leaf num-statistics-polling {
               type int32;
               description "Number of SRC statistics polling";
             }
             leaf num-sync-start {
               type int32;
               description "Number of PIC sync start request";
             }
             leaf num-sync-request {
               type int32;
               description "Number of PIC sync subscriber request";
             }
             leaf num-update-username {
               type int32;
               description "Number of username update request";
             }
             leaf num-pre-announcement {
               type int32;
               description "Number of pre-announcement";
             }
             leaf num-idle-timeout-update {
               type int32;
               description "Number of idle timeout configuraiton update";
             }
             leaf num-connection-up-event {
               type int32;
               description "Number of PCONN established event";
             }
             leaf num-pending-response {
               type int32;
               description "Number of request waiting for PIC to response";
             }
             leaf num-queued-pic-task {
               type int32;
               description "Number of PIC tasks queued";
             }
             leaf num-service-request-timeout {
               type int32;
               description "Number of service request timed out waiting for PIC response";
             }
             leaf num-logout-request-timeout {
               type int32;
               description "Number of logout request timed out waiting for PIC response";
             }
             leaf num-logout-request-send-failure {
               type int32;
               description "Number of logout request send failed";
             }
             leaf num-service-request-send-failure {
               type int32;
               description "Number of service request send failed";
             }
             leaf num-accounting-request-send-failure {
               type int32;
               description "Number of accounting request send failed";
             }
             leaf num-login-done-send-failure {
               type int32;
               description "Number of login done send failed";
             }
             leaf num-username-update-send-failure {
               type int32;
               description "Number of username update send failed";
             }
             leaf num-pre-announcement-send-failure {
               type int32;
               description "Number of pre-announcement send failed";
             }
             leaf num-idle-timeout-update-send-failure {
               type int32;
               description "Number of idle timeout configuraiton update send failed";
             }
             leaf num-service-set-update {
               type int32;
               description "Number of service-set update";
             }
             leaf num-service-set-update-send-failure {
               type int32;
               description "Number of service-set update send failed";
             }
             leaf num-partition-update-send {
               type int32;
               description "Number of partition update";
             }
             leaf num-partition-update-send-failure {
               type int32;
               description "Number of partition update send failed";
             }
             leaf num-subscriber-profiles-update {
               type int32;
               description "Number subscriber profile update";
             }
             leaf num-subscriber-profiles-update-failure {
               type int32;
               description "Number subscriber profile update send failed ";
             }
             leaf num-service-set-subscriber-profiles-mapping-update {
               type int32;
               description "Number service-set subscriber profile update";
             }
             leaf num-service-set-subscriber-profiles-mapping-update-failure {
               type int32;
               description "Number service-set subscriber profile update send failed";
             }
             leaf num-set-profile {
               type int32;
               description "Number set profile request";
             }
             leaf num-set-profile-failure {
               type int32;
               description "Number set profile request send failed";
             }
             leaf num-clear-profile {
               type int32;
               description "Number clear profile request";
             }
             leaf num-clear-profile-failure {
               type int32;
               description "Number clear profile request send failed";
             }
             leaf num-fpc-update {
               type int32;
               description "Number FPC information update";
             }
             leaf num-fpc-update-failure {
               type int32;
               description "Number FPC information update send failed";
             }
           }
           container radius-partition-status {
             leaf partition {
               type string;
               description "Partition name";
             }
             leaf num-valid-accounting-start {
               type int32;
               description "Number of valid accounting start message received";
             }
             leaf num-valid-accounting-stop {
               type int32;
               description "Number of valid accounting stop message received";
             }
             leaf num-valid-interim-accounting {
               type int32;
               description "Number of valid interim accounting message received";
             }
             leaf num-invalid-accounting-start {
               type int32;
               description "Number of invalid accounting start message received";
             }
             leaf num-invalid-accounting-stop {
               type int32;
               description "Number of invalid accounting stop message received";
             }
             leaf num-invalid-interim-accounting {
               type int32;
               description "Number of invalid interim accounting message received";
             }
             leaf num-accounting-on {
               type int32;
               description "Number of accounting-on message received";
             }
             leaf num-accounting-off {
               type int32;
               description "Number of accounting-off message received";
             }
             leaf num-accounting-start-response {
               type int32;
               description "Number of accounting stop message responses sent";
             }
             leaf num-accounting-stop-response {
               type int32;
               description "Number of accounting stop message responses sent";
             }
             leaf num-interim-accounting-response {
               type int32;
               description "Number of interim accounting message responses sent";
             }
             leaf num-tagging {
               type int32;
               description "Number of tagging recevied";
             }
           }
         }
         container subscriber-session-summary {
           description "Subscriber session summary";
           leaf num-clients {
             type int32;
           }
         }
         container subscriber-session {
           description "Subscriber session information";
           container session-detail {
             description "Subscriber session information";
             leaf client-id {
               type string;
               description "Client ID";
             }
             leaf username {
               type string;
               description "User name";
             }
             leaf user-ip-address {
               type string;
               description "User IP address";
             }
             leaf interface {
               type string;
               description "Interface name";
             }
             leaf subscriber-state {
               type string;
               description "Session state";
             }
             leaf service-interface {
               type string;
               description "Service interface";
             }
             leaf routing-instance {
               type string;
               description "Routing instance name";
             }
             leaf login-time {
               type string;
               description "Login time";
             }
             leaf partition {
               type string;
               description "Partition name";
             }
             leaf profile {
               type string;
               description "Profile name";
             }
             leaf num-services {
               type int32;
               description "Number of services";
             }
             container service-session {
               description "Service session information";
               leaf policy-name {
                 type string;
                 description "Policy name";
               }
               leaf service-state {
                 type string;
                 description "Session state";
               }
             }
           }
           container session-brief {
             description "Subscriber session information";
             leaf client-id {
               type string;
               description "Client ID";
             }
             leaf user-ip-address {
               type string;
               description "User IP address";
             }
             leaf interface {
               type string;
               description "Interface name";
             }
             leaf username {
               type string;
               description "User name";
             }
             container service-session {
               description "Service session information";
               leaf policy-name {
                 type string;
                 description "Policy name";
               }
               leaf service-state {
                 type string;
                 description "Session state";
               }
             }
           }
         }
         container session-statistics {
           description "Session statistics";
           leaf session-type {
             type string;
             description "Session type";
           }
           leaf name-id {
             type string;
             description "Name or Id";
           }
           leaf input-packets {
             type int64;
             description "Number of input packets";
           }
           leaf output-packets {
             type int64;
             description "Number of output packets";
           }
           leaf input-bytes {
             type int64;
             description "Number of input bytes";
           }
           leaf output-bytes {
             type int64;
             description "Number of output bytes";
           }
         }
         container extra-statistics {
           description "Session statistics information provided by additional source";
           leaf statistics-string {
             type string;
             description "Statistics information in string format";
           }
         }
         container subscriber-policy {
           description "Dynamic policies";
           leaf client-id {
             type string;
             description "Client ID";
           }
           container service-policy {
             description "Service dynamic policy";
             leaf policy-name {
               type string;
               description "Policy name";
             }
             leaf rpr {
               type string;
               description "Precedence";
             }
             leaf d {
               type string;
               description "Direction";
             }
             container term {
               description "Term";
               leaf template-name {
                 type string;
                 description "Rule template";
               }
               leaf tpr {
                 type int32;
                 description "Term precedence";
               }
               leaf ra {
                 type string;
                 description "Remote address";
               }
               leaf rm {
                 type int32;
                 description "Remote mask";
               }
               leaf lpl {
                 type int32;
                 description "Local port range low";
               }
               leaf lph {
                 type int32;
                 description "Local port range high";
               }
               leaf rpl {
                 type int32;
                 description "Remote port range low";
               }
               leaf rph {
                 type int32;
                 description "Remote port range high";
               }
               leaf p {
                 type int32;
                 description "Protocol";
               }
               leaf anl {
                 type string;
                 description "Application name list";
               }
               leaf agl {
                 type string;
                 description "Application group list";
               }
               leaf nanl {
                 type string;
                 description "Nested application name list";
               }
               leaf a-f {
                 type string;
                 description "Flow action";
               }
               leaf a-s {
                 type string;
                 description "Stats action";
               }
               leaf a-fc {
                 type string;
                 description "Forwarding class";
               }
               leaf a-p-i {
                 type int32;
                 description "Policer instance";
               }
               leaf a-p-bw {
                 type int32;
                 description "Policer bandwidth";
               }
               leaf a-p-mbs {
                 type int32;
                 description "Policer maximum burst size";
               }
               leaf a-fu {
                 type int32;
                 description "Forwarding unit";
               }
               leaf opt-profile {
                 type int32;
                 description "Subscriber profile";
               }
             }
           }
           container radius-policy {
             description "Dynamic RADIUS policies";
             container policy-attribute {
               leaf attribute-name {
                 type string;
                 description "Radius attribute name";
               }
               leaf attribute-value {
                 type string;
                 description "Radius attribute value";
               }
             }
           }
         }
         container subscriber-flows {
           description "Flows";
           leaf client-id {
             type string;
             description "Client ID";
           }
           leaf num-data-sessions {
             type int32;
             description "Number of data sessions";
           }
           leaf hwm {
             type int32;
             description "High water mark";
           }
           container flows {
             description "Flows";
             leaf five-tuple {
               type string;
               description "5 tuple";
             }
             leaf application-id {
               type string;
               description "Appication-id";
             }
             leaf policy-name {
               type string;
               description "Policy name";
             }
             leaf policy-direction {
               type string;
               description "Direction";
             }
             leaf packets {
               type string;
               description "Packet";
             }
             leaf bytes {
               type string;
               description "Bytes";
             }
             leaf offload {
               type string;
               description "Offload status";
             }
             leaf policy-action {
               type string;
               description "Policy action";
             }
           }
         }
         container subscriber-bandwidth {
           description "Bandwidth";
           leaf client-id {
             type string;
             description "Client ID";
           }
           leaf input-pps {
             type int32;
             description "Input pps";
           }
           leaf output-pps {
             type int32;
             description "Output pps";
           }
           leaf input-bps {
             type int32;
             description "Input bps";
           }
           leaf output-bps {
             type int32;
             description "Output bps";
           }
         }
         container clear-session-result {
           description "Result of clear session request";
           leaf num-logout-initiated {
             type int32;
             description "Number of session logout request initiated";
           }
         }
         container service-subscribers-request-result {
           description "Result for service subscriber request";
           container failed {
             description "Result for service subscriber request";
             leaf request_failure {
               type string;
               description "Service subscriber request failed";
             }
           }
           container success {
             description "Result for service subscriber request";
             leaf request_success {
               type empty;
               description "Service subscriber request succeed";
             }
           }
         }
       }
     }
   }
   rpc get-services-subscriber-flows {
     description "Flows";
     input {
       leaf client-id {
         description "Client identifier";
         type uint64;
         mandatory true;
       }
     }
     output {
       container packet-triggered-subscribers-information {
         leaf message {
           type string;
           description "Message to be displaed";
         }
         container process-status {
           description "Process status";
           leaf num-clients {
             type int32;
           }
           leaf src-connection-state {
             type string;
             description "SRC connection state";
           }
           leaf num-diameterd-connected {
             type int32;
             description "Number of diameterd connections established";
           }
           leaf num-diameterd-disconnected {
             type int32;
             description "Number of diameterd connections disconnected";
           }
           leaf full-sync-in-progress {
             type string;
             description "Full sync in progress";
           }
           leaf fast-sync-in-progress {
             type string;
             description "Fast sync in progress";
           }
           leaf num-full-sync-abort {
             type string;
             description "Number of full sync abort";
           }
           leaf num-fast-sync-abort {
             type string;
             description "Number of fast sync abort";
           }
           leaf num-srr-received {
             type int32;
             description "Number of SRR received";
           }
           leaf num-srr-failure {
             type int32;
             description "Number failure SRR received";
           }
           leaf num-srr-queued {
             type int32;
             description "Number of SRR send attempted";
           }
           leaf num-srq-queued {
             type int32;
             description "Number of SRQ send attempted";
           }
           leaf num-srq-full-sync {
             type int32;
             description "Number of SRQ full-sync";
           }
           leaf num-srq-fast-sync {
             type int32;
             description "Number of SRQ fast-sync";
           }
           leaf num-srq-single-sync {
             type int32;
             description "Number of SRQ single-sync";
           }
           leaf num-sending-message {
             type int32;
             description "Number of queued sending messages";
           }
           leaf num-sending-queue-full {
             type int32;
             description "Number of sending queue full event";
           }
           leaf num-sending-timeout {
             type int32;
             description "Number of sending messages timed out";
           }
           leaf num-response-timeout {
             type int32;
             description "Number of pending response timed out";
           }
           leaf num-waiting-message {
             type int32;
             description "Number of messages waiting for response";
           }
           leaf num-ppr-received {
             type int32;
             description "Number of PPR received";
           }
           leaf num-asr-received {
             type int32;
             description "Number of ASR received";
           }
           leaf num-acr-received {
             type int32;
             description "Number of ACR received";
           }
           leaf num-aaa-received {
             type int32;
             description "Number of AAA received";
           }
           leaf num-sta-received {
             type int32;
             description "Number of STA received";
           }
           leaf num-sync-aaa-received {
             type int32;
             description "Number of sync AAA received";
           }
           leaf num-sync-sta-received {
             type int32;
             description "Number of sync STA received";
           }
           leaf num-aar-queued {
             type int32;
             description "Number of AAR send attempted";
           }
           leaf num-ppa-queued {
             type int32;
             description "Number of PPA send attempted";
           }
           leaf num-str-queued {
             type int32;
             description "Number of STR send attempted";
           }
           leaf num-asa-queued {
             type int32;
             description "Number of ASA send attempted";
           }
           leaf num-aca-queued {
             type int32;
             description "Number of ACA send attempted";
           }
           leaf num-sync-aar-queued {
             type int32;
             description "Number of sync AAR send attempted";
           }
           leaf num-sync-str-queued {
             type int32;
             description "Number of sync STR send attempted";
           }
           leaf num-srq-timeout {
             type int32;
             description "Number of SRQ timed out";
           }
           leaf num-str-timeout {
             type int32;
             description "Number of STR timed out";
           }
           leaf num-aar-timeout {
             type int32;
             description "Number of AAR timed out";
           }
           leaf num-aar-send-failure {
             type int32;
             description "Number of AAR send failed";
           }
           leaf num-asa-send-failure {
             type int32;
             description "Number of ASR send failed";
           }
           leaf num-aca-send-failure {
             type int32;
             description "Number of ACR send failed";
           }
           leaf num-ppa-send-failure {
             type int32;
             description "Number of PPA send failed";
           }
           leaf num-str-send-failure {
             type int32;
             description "Number of STR send failed";
           }
           leaf num-srq-send-failure {
             type int32;
             description "Number of SRQ send failed";
           }
           leaf num-srr-send-failure {
             type int32;
             description "Number of SRR send failed";
           }
           leaf num-sync-aar-send-failure {
             type int32;
             description "Number of AAR send failed";
           }
           leaf num-sync-str-send-failure {
             type int32;
             description "Number of STR send failed";
           }
           leaf num-sync-aar-timeout {
             type int32;
             description "Number of sync-AAR timed out";
           }
           leaf num-sync-str-timeout {
             type int32;
             description "Number of sync-STR timed out";
           }
           leaf num-fast-sync-queued {
             type int32;
             description "Number of fast-sync messages queued";
           }
           leaf num-queued-diameter-task {
             type int32;
             description "Number of diameter tasks queued";
           }
           leaf num-down-pic-clients {
             type int32;
             description "Number of ready-to-logout client session dur to PIC down";
           }
           leaf first-down-pic-client-id {
             type int64;
             description "First ready-to-logout client session ID";
           }
           leaf num-outstanding-diameter-message {
             type string;
             description "Number of outstanding diameter messages";
           }
           leaf num-login-retry {
             type string;
             description "Number of subscriber login retry with SRC";
           }
           leaf num-pconn {
             type int32;
             description "Number of pconn connections";
           }
           container pic-status {
             leaf pic-name {
               type string;
               description "Service PIC name";
             }
             leaf num-pic-login {
               type int32;
               description "Number of PIC login request";
             }
             leaf num-pic-logout-response {
               type int32;
               description "Number of PIC logout response";
             }
             leaf num-login-done {
               type int32;
               description "Number of PIC login done";
             }
             leaf num-pic-logout {
               type int32;
               description "Number of PIC logout request";
             }
             leaf num-policy-change {
               type int32;
               description "Number of policy changes request";
             }
             leaf num-policy-change-response {
               type int32;
               description "Number of policy changes response";
             }
             leaf num-src-logout {
               type int32;
               description "Number of SRC logout request";
             }
             leaf num-statistics-polling {
               type int32;
               description "Number of SRC statistics polling";
             }
             leaf num-sync-start {
               type int32;
               description "Number of PIC sync start request";
             }
             leaf num-sync-request {
               type int32;
               description "Number of PIC sync subscriber request";
             }
             leaf num-update-username {
               type int32;
               description "Number of username update request";
             }
             leaf num-pre-announcement {
               type int32;
               description "Number of pre-announcement";
             }
             leaf num-idle-timeout-update {
               type int32;
               description "Number of idle timeout configuraiton update";
             }
             leaf num-connection-up-event {
               type int32;
               description "Number of PCONN established event";
             }
             leaf num-pending-response {
               type int32;
               description "Number of request waiting for PIC to response";
             }
             leaf num-queued-pic-task {
               type int32;
               description "Number of PIC tasks queued";
             }
             leaf num-service-request-timeout {
               type int32;
               description "Number of service request timed out waiting for PIC response";
             }
             leaf num-logout-request-timeout {
               type int32;
               description "Number of logout request timed out waiting for PIC response";
             }
             leaf num-logout-request-send-failure {
               type int32;
               description "Number of logout request send failed";
             }
             leaf num-service-request-send-failure {
               type int32;
               description "Number of service request send failed";
             }
             leaf num-accounting-request-send-failure {
               type int32;
               description "Number of accounting request send failed";
             }
             leaf num-login-done-send-failure {
               type int32;
               description "Number of login done send failed";
             }
             leaf num-username-update-send-failure {
               type int32;
               description "Number of username update send failed";
             }
             leaf num-pre-announcement-send-failure {
               type int32;
               description "Number of pre-announcement send failed";
             }
             leaf num-idle-timeout-update-send-failure {
               type int32;
               description "Number of idle timeout configuraiton update send failed";
             }
             leaf num-service-set-update {
               type int32;
               description "Number of service-set update";
             }
             leaf num-service-set-update-send-failure {
               type int32;
               description "Number of service-set update send failed";
             }
             leaf num-partition-update-send {
               type int32;
               description "Number of partition update";
             }
             leaf num-partition-update-send-failure {
               type int32;
               description "Number of partition update send failed";
             }
             leaf num-subscriber-profiles-update {
               type int32;
               description "Number subscriber profile update";
             }
             leaf num-subscriber-profiles-update-failure {
               type int32;
               description "Number subscriber profile update send failed ";
             }
             leaf num-service-set-subscriber-profiles-mapping-update {
               type int32;
               description "Number service-set subscriber profile update";
             }
             leaf num-service-set-subscriber-profiles-mapping-update-failure {
               type int32;
               description "Number service-set subscriber profile update send failed";
             }
             leaf num-set-profile {
               type int32;
               description "Number set profile request";
             }
             leaf num-set-profile-failure {
               type int32;
               description "Number set profile request send failed";
             }
             leaf num-clear-profile {
               type int32;
               description "Number clear profile request";
             }
             leaf num-clear-profile-failure {
               type int32;
               description "Number clear profile request send failed";
             }
             leaf num-fpc-update {
               type int32;
               description "Number FPC information update";
             }
             leaf num-fpc-update-failure {
               type int32;
               description "Number FPC information update send failed";
             }
           }
           container radius-partition-status {
             leaf partition {
               type string;
               description "Partition name";
             }
             leaf num-valid-accounting-start {
               type int32;
               description "Number of valid accounting start message received";
             }
             leaf num-valid-accounting-stop {
               type int32;
               description "Number of valid accounting stop message received";
             }
             leaf num-valid-interim-accounting {
               type int32;
               description "Number of valid interim accounting message received";
             }
             leaf num-invalid-accounting-start {
               type int32;
               description "Number of invalid accounting start message received";
             }
             leaf num-invalid-accounting-stop {
               type int32;
               description "Number of invalid accounting stop message received";
             }
             leaf num-invalid-interim-accounting {
               type int32;
               description "Number of invalid interim accounting message received";
             }
             leaf num-accounting-on {
               type int32;
               description "Number of accounting-on message received";
             }
             leaf num-accounting-off {
               type int32;
               description "Number of accounting-off message received";
             }
             leaf num-accounting-start-response {
               type int32;
               description "Number of accounting stop message responses sent";
             }
             leaf num-accounting-stop-response {
               type int32;
               description "Number of accounting stop message responses sent";
             }
             leaf num-interim-accounting-response {
               type int32;
               description "Number of interim accounting message responses sent";
             }
             leaf num-tagging {
               type int32;
               description "Number of tagging recevied";
             }
           }
         }
         container subscriber-session-summary {
           description "Subscriber session summary";
           leaf num-clients {
             type int32;
           }
         }
         container subscriber-session {
           description "Subscriber session information";
           container session-detail {
             description "Subscriber session information";
             leaf client-id {
               type string;
               description "Client ID";
             }
             leaf username {
               type string;
               description "User name";
             }
             leaf user-ip-address {
               type string;
               description "User IP address";
             }
             leaf interface {
               type string;
               description "Interface name";
             }
             leaf subscriber-state {
               type string;
               description "Session state";
             }
             leaf service-interface {
               type string;
               description "Service interface";
             }
             leaf routing-instance {
               type string;
               description "Routing instance name";
             }
             leaf login-time {
               type string;
               description "Login time";
             }
             leaf partition {
               type string;
               description "Partition name";
             }
             leaf profile {
               type string;
               description "Profile name";
             }
             leaf num-services {
               type int32;
               description "Number of services";
             }
             container service-session {
               description "Service session information";
               leaf policy-name {
                 type string;
                 description "Policy name";
               }
               leaf service-state {
                 type string;
                 description "Session state";
               }
             }
           }
           container session-brief {
             description "Subscriber session information";
             leaf client-id {
               type string;
               description "Client ID";
             }
             leaf user-ip-address {
               type string;
               description "User IP address";
             }
             leaf interface {
               type string;
               description "Interface name";
             }
             leaf username {
               type string;
               description "User name";
             }
             container service-session {
               description "Service session information";
               leaf policy-name {
                 type string;
                 description "Policy name";
               }
               leaf service-state {
                 type string;
                 description "Session state";
               }
             }
           }
         }
         container session-statistics {
           description "Session statistics";
           leaf session-type {
             type string;
             description "Session type";
           }
           leaf name-id {
             type string;
             description "Name or Id";
           }
           leaf input-packets {
             type int64;
             description "Number of input packets";
           }
           leaf output-packets {
             type int64;
             description "Number of output packets";
           }
           leaf input-bytes {
             type int64;
             description "Number of input bytes";
           }
           leaf output-bytes {
             type int64;
             description "Number of output bytes";
           }
         }
         container extra-statistics {
           description "Session statistics information provided by additional source";
           leaf statistics-string {
             type string;
             description "Statistics information in string format";
           }
         }
         container subscriber-policy {
           description "Dynamic policies";
           leaf client-id {
             type string;
             description "Client ID";
           }
           container service-policy {
             description "Service dynamic policy";
             leaf policy-name {
               type string;
               description "Policy name";
             }
             leaf rpr {
               type string;
               description "Precedence";
             }
             leaf d {
               type string;
               description "Direction";
             }
             container term {
               description "Term";
               leaf template-name {
                 type string;
                 description "Rule template";
               }
               leaf tpr {
                 type int32;
                 description "Term precedence";
               }
               leaf ra {
                 type string;
                 description "Remote address";
               }
               leaf rm {
                 type int32;
                 description "Remote mask";
               }
               leaf lpl {
                 type int32;
                 description "Local port range low";
               }
               leaf lph {
                 type int32;
                 description "Local port range high";
               }
               leaf rpl {
                 type int32;
                 description "Remote port range low";
               }
               leaf rph {
                 type int32;
                 description "Remote port range high";
               }
               leaf p {
                 type int32;
                 description "Protocol";
               }
               leaf anl {
                 type string;
                 description "Application name list";
               }
               leaf agl {
                 type string;
                 description "Application group list";
               }
               leaf nanl {
                 type string;
                 description "Nested application name list";
               }
               leaf a-f {
                 type string;
                 description "Flow action";
               }
               leaf a-s {
                 type string;
                 description "Stats action";
               }
               leaf a-fc {
                 type string;
                 description "Forwarding class";
               }
               leaf a-p-i {
                 type int32;
                 description "Policer instance";
               }
               leaf a-p-bw {
                 type int32;
                 description "Policer bandwidth";
               }
               leaf a-p-mbs {
                 type int32;
                 description "Policer maximum burst size";
               }
               leaf a-fu {
                 type int32;
                 description "Forwarding unit";
               }
               leaf opt-profile {
                 type int32;
                 description "Subscriber profile";
               }
             }
           }
           container radius-policy {
             description "Dynamic RADIUS policies";
             container policy-attribute {
               leaf attribute-name {
                 type string;
                 description "Radius attribute name";
               }
               leaf attribute-value {
                 type string;
                 description "Radius attribute value";
               }
             }
           }
         }
         container subscriber-flows {
           description "Flows";
           leaf client-id {
             type string;
             description "Client ID";
           }
           leaf num-data-sessions {
             type int32;
             description "Number of data sessions";
           }
           leaf hwm {
             type int32;
             description "High water mark";
           }
           container flows {
             description "Flows";
             leaf five-tuple {
               type string;
               description "5 tuple";
             }
             leaf application-id {
               type string;
               description "Appication-id";
             }
             leaf policy-name {
               type string;
               description "Policy name";
             }
             leaf policy-direction {
               type string;
               description "Direction";
             }
             leaf packets {
               type string;
               description "Packet";
             }
             leaf bytes {
               type string;
               description "Bytes";
             }
             leaf offload {
               type string;
               description "Offload status";
             }
             leaf policy-action {
               type string;
               description "Policy action";
             }
           }
         }
         container subscriber-bandwidth {
           description "Bandwidth";
           leaf client-id {
             type string;
             description "Client ID";
           }
           leaf input-pps {
             type int32;
             description "Input pps";
           }
           leaf output-pps {
             type int32;
             description "Output pps";
           }
           leaf input-bps {
             type int32;
             description "Input bps";
           }
           leaf output-bps {
             type int32;
             description "Output bps";
           }
         }
         container clear-session-result {
           description "Result of clear session request";
           leaf num-logout-initiated {
             type int32;
             description "Number of session logout request initiated";
           }
         }
         container service-subscribers-request-result {
           description "Result for service subscriber request";
           container failed {
             description "Result for service subscriber request";
             leaf request_failure {
               type string;
               description "Service subscriber request failed";
             }
           }
           container success {
             description "Result for service subscriber request";
             leaf request_success {
               type empty;
               description "Service subscriber request succeed";
             }
           }
         }
       }
     }
   }
   rpc get-service-subscriber-analysis-information {
     description "Show service subscribers statistics";
     input {
       leaf interface {
         description "Name of extension provider interface";
         type string;
       }
     }
   }
   rpc get-probe-results {
     description "Show probe results";
     input {
       leaf owner {
         description "Name of owner";
         type string {
           length "1 .. 32";
         }
       }
       leaf test {
         description "Name of test";
         type string {
           length "1 .. 32";
         }
       }
     }
     output {
       container probe-results {
         container probe-test-results {
           leaf owner {
             type string;
             description "Test owner name";
           }
           leaf test-name {
             type string;
             description "Name of test";
           }
           leaf target-address {
             type string;
             description "Target address of test";
           }
           leaf target-url {
             type string;
             description "Target URL of test";
           }
           leaf source-address {
             type string;
             description "Source address of test";
           }
           leaf probe-type {
             type string;
             description "Name of the probe";
           }
           leaf icmp-id {
             type uint32;
             description "Icmp id for icmp-ping probes";
           }
           leaf test-size {
             type uint32;
             description "Number of probes in test";
           }
           leaf server-address {
             type ipaddr;
             description "Server address";
           }
           leaf server-port {
             type uint32;
             description "Server port";
           }
           leaf client-address {
             type ipaddr;
             description "Client address";
           }
           leaf client-port {
             type uint32;
             description "Client port";
           }
           leaf reflector-address {
             type ipaddr;
             description "Reflector address";
           }
           leaf reflector-port {
             type uint32;
             description "Reflector port";
           }
           leaf sender-address {
             type ipaddr;
             description "Sender address";
           }
           leaf sender-port {
             type uint32;
             description "Sender port";
           }
           leaf routing-instance-name {
             type string;
             description "Routing Instance Name";
           }
           leaf destination-interface {
             type string;
             description "Name of output interface for probes";
           }
           leaf http-status {
             type uint32;
             description "HTTP Status Code";
           }
           leaf loss-thresh-total {
             type uint32;
             description "Maximum number of all lost probes";
           }
           leaf loss-thresh-succ {
             type uint32;
             description "Maximum number of successive lost probes";
           }
           leaf delay-thresh {
             type uint32;
             description "Maximum delay threshold";
           }
           leaf jitter-thresh {
             type uint32;
             description "Maximum jitter threshold";
           }
           leaf stddev-thresh {
             type uint32;
             description "Maximum standard deviation threshold";
           }
           leaf egress-thresh {
             type uint32;
             description "Maximum egress delay threshold";
           }
           leaf egress-jitter-thresh {
             type uint32;
             description "Maximum egress jitter threshold";
           }
           leaf egress-stddev-thresh {
             type uint32;
             description "Maximum egress standard deviation threshold";
           }
           leaf ingress-thresh {
             type uint32;
             description "Maximum ingress delay threshold";
           }
           leaf ingress-jitter-thresh {
             type uint32;
             description "Maximum ingress jitter threshold";
           }
           leaf ingress-stddev-thresh {
             type uint32;
             description "Maximum ingress standard deviation threshold";
           }
           container probe-single-results {
             leaf probe-sent-time {
               type string;
               description "Time at which probe was sent";
             }
             leaf probe-status {
               type string;
               description "Operation response status from probes";
             }
             leaf probe-time {
               type string;
               description "Time at which probe response was received or timed out";
             }
             leaf hardware-timestamp-status {
               type string;
               description "Use of hardware timestamps in probes";
             }
             leaf rtt {
               type uint32;
               description "Round trip time of probes";
             }
             leaf ingress {
               type uint32;
               description "Ingress trip time of probes";
             }
             leaf egress {
               type uint32;
               description "Egress trip time of probes";
             }
             leaf egress-jitter {
               type int32;
               description "Egress jitter of probes";
             }
             leaf ingress-jitter {
               type int32;
               description "Ingress jitter of probes";
             }
             leaf round-trip-jitter {
               type int32;
               description "Round trip jitter of probes";
             }
             leaf egress-interarrival-jitter {
               type int32;
               description "Egress interarrival jitter of probes";
             }
             leaf ingress-interarrival-jitter {
               type int32;
               description "Ingress interarrival jitter of probes";
             }
             leaf round-trip-interarrival-jitter {
               type int32;
               description "Round trip interarrival jitter of probes";
             }
             container verbose {
             }
             container brief {
               leaf owner {
                 type string;
                 description "Test owner name";
               }
               leaf test-name {
                 type string;
                 description "Name of test";
               }
               leaf probe-sent-time {
                 type string;
                 description "Time at which probe was sent";
               }
               leaf probe-time {
                 type string;
                 description "Time at which probe response was received or timed out";
               }
               leaf rtt {
                 type uint32;
                 description "Round trip time of probes";
               }
               leaf probe-status {
                 type string;
                 description "Operation response status from probes";
               }
             }
           }
           container probe-test-current-results {
             container probe-test-generic-results {
               leaf results-scope {
                 type string;
                 description "Scope of results";
               }
               leaf probes-sent {
                 type uint32;
                 description "Number of probes sent";
               }
               leaf probe-responses {
                 type uint32;
                 description "Responses from probes";
               }
               leaf loss-percentage {
                 type string;
                 description "Percentage of probes lost (no response)";
               }
               container probe-last-test-info {
                 leaf last-test-time {
                   type string;
                   description "Time at which last test was completed";
                 }
               }
               container probe-test-rtt {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-egress {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-ingress {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-positive-egress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-negative-egress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-positive-ingress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-negative-ingress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-positive-round-trip-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-negative-round-trip-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
             }
           }
           container probe-last-test-results {
             container probe-test-generic-results {
               leaf results-scope {
                 type string;
                 description "Scope of results";
               }
               leaf probes-sent {
                 type uint32;
                 description "Number of probes sent";
               }
               leaf probe-responses {
                 type uint32;
                 description "Responses from probes";
               }
               leaf loss-percentage {
                 type string;
                 description "Percentage of probes lost (no response)";
               }
               container probe-last-test-info {
                 leaf last-test-time {
                   type string;
                   description "Time at which last test was completed";
                 }
               }
               container probe-test-rtt {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-egress {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-ingress {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-positive-egress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-negative-egress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-positive-ingress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-negative-ingress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-positive-round-trip-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-negative-round-trip-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
             }
           }
           container probe-test-moving-results {
             container probe-test-generic-results {
               leaf results-scope {
                 type string;
                 description "Scope of results";
               }
               leaf probes-sent {
                 type uint32;
                 description "Number of probes sent";
               }
               leaf probe-responses {
                 type uint32;
                 description "Responses from probes";
               }
               leaf loss-percentage {
                 type string;
                 description "Percentage of probes lost (no response)";
               }
               container probe-last-test-info {
                 leaf last-test-time {
                   type string;
                   description "Time at which last test was completed";
                 }
               }
               container probe-test-rtt {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-egress {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-ingress {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-positive-egress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-negative-egress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-positive-ingress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-negative-ingress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-positive-round-trip-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-negative-round-trip-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
             }
           }
           container probe-test-global-results {
             container probe-test-generic-results {
               leaf results-scope {
                 type string;
                 description "Scope of results";
               }
               leaf probes-sent {
                 type uint32;
                 description "Number of probes sent";
               }
               leaf probe-responses {
                 type uint32;
                 description "Responses from probes";
               }
               leaf loss-percentage {
                 type string;
                 description "Percentage of probes lost (no response)";
               }
               container probe-last-test-info {
                 leaf last-test-time {
                   type string;
                   description "Time at which last test was completed";
                 }
               }
               container probe-test-rtt {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-egress {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-ingress {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-positive-egress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-negative-egress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-positive-ingress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-negative-ingress-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-positive-round-trip-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
               container probe-test-negative-round-trip-jitter {
                 container probe-summary-results {
                   leaf probe-results-type {
                     type string;
                     description "Results type";
                   }
                   leaf samples {
                     type uint32;
                     description "Number of samples";
                   }
                   leaf min-delay {
                     type uint32;
                     description "Minimum delay time";
                   }
                   leaf max-delay {
                     type uint32;
                     description "Maximum delay time";
                   }
                   leaf avg-delay {
                     type uint32;
                     description "Average delay time";
                   }
                   leaf jitter-delay {
                     type uint32;
                     description "Difference between maximum and minimum delay times";
                   }
                   leaf stddev-delay {
                     type uint64;
                     description "Standard deviation of delay time";
                   }
                   leaf sum-delay {
                     type uint64;
                     description "Sum of delay times";
                   }
                 }
               }
             }
           }
           container probe-test-hwts-err-stats {
             leaf invalid-client-recv-ts-cntr {
               type uint32;
               description "Client recv timestamp less than Client send timestamp";
             }
             leaf invalid-server-send-ts-cntr {
               type uint32;
               description "Server send timestamp less than Server recv timestamp";
             }
             leaf invalid-server-spent-time-cntr {
               type uint32;
               description "Server side spent time greater than RTT";
             }
           }
         }
       }
     }
   }
   rpc get-history-results {
     description "Show history results";
     input {
       leaf verbosity_level {
         default "brief";
         type enumeration {
           enum "brief" {
             description "Display brief output (default)";
           }
           enum "detail" {
             description "Display detailed output";
           }
         }
       }
       leaf owner {
         description "Name of owner";
         type string {
           length "1 .. 32";
         }
       }
       leaf test {
         description "Name of test";
         type string {
           length "1 .. 32";
         }
       }
       leaf since {
         description "Show history since YYYY-MM-DD.HH:MM:SS";
         type time;
       }
     }
     output {
       container history-results {
         container history-test-results {
           container verbose {
             leaf owner {
               type string;
               description "Test owner name";
             }
             leaf test-name {
               type string;
               description "Name of test";
             }
             leaf probe-type {
               type string;
               description "Name of the probe";
             }
             leaf icmp-id {
               type uint32;
               description "Icmp id for icmp-ping probes";
             }
             leaf target-address {
               type string;
               description "Target address of test";
             }
             leaf target-url {
               type string;
               description "Target URL of test";
             }
             leaf source-address {
               type string;
               description "Source address of test";
             }
             leaf destination-interface {
               type string;
               description "Name of output interface for probes";
             }
             leaf loss-thresh-total {
               type uint32;
               description "Maximum number of all lost probes";
             }
             leaf loss-thresh-succ {
               type uint32;
               description "Maximum number of successive lost probes";
             }
             leaf delay-thresh {
               type uint32;
               description "Maximum delay threshold";
             }
             leaf jitter-thresh {
               type uint32;
               description "Maximum jitter threshold";
             }
             leaf stddev-thresh {
               type uint32;
               description "Maximum standard deviation threshold";
             }
             leaf egress-thresh {
               type uint32;
               description "Maximum egress delay threshold";
             }
             leaf egress-jitter-thresh {
               type uint32;
               description "Maximum egress jitter threshold";
             }
             leaf ingress-thresh {
               type uint32;
               description "Maximum ingress delay threshold";
             }
             leaf ingress-jitter-thresh {
               type uint32;
               description "Maximum ingress jitter threshold";
             }
             container probe-single-results {
               container brief {
                 leaf probe-sent-time {
                   type string;
                   description "Time at which probe was sent";
                 }
                 leaf probe-time {
                   type string;
                   description "Time at which probe response was received or timed out";
                 }
                 leaf rtt {
                   type uint32;
                   description "Round trip time of probes";
                 }
                 leaf probe-status {
                   type string;
                   description "Operation response status from probes";
                 }
               }
             }
             container probe-test-current-results {
               container probe-test-generic-results {
                 leaf results-scope {
                   type string;
                   description "Scope of results";
                 }
                 leaf probes-sent {
                   type uint32;
                   description "Number of probes sent";
                 }
                 leaf probe-responses {
                   type uint32;
                   description "Responses from probes";
                 }
                 leaf loss-percentage {
                   type string;
                   description "Percentage of probes lost (no response)";
                 }
                 container probe-last-test-info {
                   leaf last-test-time {
                     type string;
                     description "Time at which last test was completed";
                   }
                 }
                 container probe-test-rtt {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-egress {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-ingress {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-positive-egress-jitter {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-negative-egress-jitter {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-positive-ingress-jitter {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-negative-ingress-jitter {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-positive-round-trip-jitter {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-negative-round-trip-jitter {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
               }
             }
           }
           container brief {
             container probe-single-results {
               container verbose {
                 leaf probe-sent-time {
                   type string;
                   description "Time at which probe was sent";
                 }
                 leaf probe-status {
                   type string;
                   description "Operation response status from probes";
                 }
                 leaf probe-time {
                   type string;
                   description "Time at which probe response was received or timed out";
                 }
                 leaf hardware-timestamp-status {
                   type string;
                   description "Use of hardware timestamps in probes";
                 }
                 leaf http-status {
                   type uint32;
                   description "HTTP Status Code";
                 }
                 leaf rtt {
                   type uint32;
                   description "Round trip time of probes";
                 }
                 leaf ingress {
                   type uint32;
                   description "Ingress trip time of probes";
                 }
                 leaf egress {
                   type uint32;
                   description "Egress trip time of probes";
                 }
                 leaf egress-jitter {
                   type int32;
                   description "Egress jitter of probes";
                 }
                 leaf ingress-jitter {
                   type int32;
                   description "Ingress jitter of probes";
                 }
                 leaf round-trip-jitter {
                   type int32;
                   description "Round trip jitter of probes";
                 }
                 leaf egress-interarrival-jitter {
                   type int32;
                   description "Egress interarrival jitter of probes";
                 }
                 leaf ingress-interarrival-jitter {
                   type int32;
                   description "Ingress interarrival jitter of probes";
                 }
                 leaf round-trip-interarrival-jitter {
                   type int32;
                   description "Round trip interarrival jitter of probes";
                 }
               }
               container brief {
                 leaf owner {
                   type string;
                   description "Test owner name";
                 }
                 leaf test-name {
                   type string;
                   description "Name of test";
                 }
                 leaf probe-sent-time {
                   type string;
                   description "Time at which probe was sent";
                 }
                 leaf probe-time {
                   type string;
                   description "Time at which probe response was received or timed out";
                 }
                 leaf rtt {
                   type uint32;
                   description "Round trip time of probes";
                 }
                 leaf probe-status {
                   type string;
                   description "Operation response status from probes";
                 }
               }
             }
             container probe-test-current-results {
               container probe-test-generic-results {
                 leaf results-scope {
                   type string;
                   description "Scope of results";
                 }
                 leaf probes-sent {
                   type uint32;
                   description "Number of probes sent";
                 }
                 leaf probe-responses {
                   type uint32;
                   description "Responses from probes";
                 }
                 leaf loss-percentage {
                   type string;
                   description "Percentage of probes lost (no response)";
                 }
                 container probe-last-test-info {
                   leaf last-test-time {
                     type string;
                     description "Time at which last test was completed";
                   }
                 }
                 container probe-test-rtt {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-egress {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-ingress {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-positive-egress-jitter {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-negative-egress-jitter {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-positive-ingress-jitter {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-negative-ingress-jitter {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-positive-round-trip-jitter {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
                 container probe-test-negative-round-trip-jitter {
                   container probe-summary-results {
                     leaf probe-results-type {
                       type string;
                       description "Results type";
                     }
                     leaf samples {
                       type uint32;
                       description "Number of samples";
                     }
                     leaf min-delay {
                       type uint32;
                       description "Minimum delay time";
                     }
                     leaf max-delay {
                       type uint32;
                       description "Maximum delay time";
                     }
                     leaf avg-delay {
                       type uint32;
                       description "Average delay time";
                     }
                     leaf jitter-delay {
                       type uint32;
                       description "Difference between maximum and minimum delay times";
                     }
                     leaf stddev-delay {
                       type uint64;
                       description "Standard deviation of delay time";
                     }
                     leaf sum-delay {
                       type uint64;
                       description "Sum of delay times";
                     }
                   }
                 }
               }
             }
           }
         }
       }
     }
   }
   rpc get-active-servers {
     description "Show configured servers";
     output {
       container active-servers {
         container configured-servers {
           leaf protocol {
             type string;
             description "Protocol";
           }
           leaf port {
             type uint32;
             description "Port";
           }
           leaf destination-interface {
             type string;
             description "Name of output interface for probes";
           }
         }
       }
     }
   }
   rpc get-pcef-subscribers {
     description "Show subscriber information";
     input {
       leaf address {
         description "IPv4 or IPv6 address of subscriber";
         type string;
       }
       leaf interface {
         description "Interface name, or with wildcards (e.g. fe-0/0/*, fe-0/*/*)";
         type interface-wildcard;
       }
       leaf physical-interface {
         description "Physical Interface name";
         type interface-wildcard;
       }
       leaf user-name {
         description "Username of subscriber";
         type string;
       }
       leaf logical-system {
         description "Logical system where subscriber resides";
         type string;
       }
       leaf routing-instance {
         description "Routing instance where subscriber resides";
         type string;
       }
       leaf profile-name {
         description "Profile with which subscriber has been activated";
         type string {
           length "1 .. 80";
         }
       }
       leaf agent-circuit-identifier {
         description "Display summary for specified agent circuit identifier";
         type string;
       }
       leaf aci-interface-set-name {
         description "Display summary for specified ACI interface set";
         type string;
       }
       leaf stacked-vlan-id {
         description "Stacked VLAN identifier of subscriber";
         type uint16 {
           range "0 .. 4094";
         }
       }
       leaf vlan-id {
         description "VLAN identifier of subscriber";
         type uint16 {
           range "0 .. 4094";
         }
       }
       leaf vpi {
         description "ATM VPI of subscriber";
         type uint16 {
           range "0 .. 255";
         }
       }
       leaf vci {
         description "ATM VCI of subscriber";
         type uint16 {
           range "0 .. 65535";
         }
       }
       leaf id {
         description "Identifier of subscriber";
         type string;
       }
       leaf mac-address {
         description "MAC address of subscriber";
         type mac-addr;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "vpls-pw" {
             description "VPLS-PW clients only";
           }
           enum "mlppp" {
             description "MLPPP clients only";
           }
           enum "xauth" {
             description "XAuth clients only";
           }
           enum "fwauth" {
             description "FwAuth clients only";
           }
           enum "dot1x" {
             description "Dot1x clients only";
           }
           enum "essm" {
             description "ESSM clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
           enum "terminated" {
             description "TERMINATED state only";
           }
         }
       }
       leaf display {
         default "terse";
         type enumeration {
           enum "terse" {
             description "Display terse output";
           }
           enum "detail" {
             description "Display detailed output";
           }
           enum "extensive" {
             description "Display extensive output";
           }
           enum "count" {
             description "Display number of subscribers";
           }
         }
       }
     }
   }
   rpc get-pcef-subscribers-summary {
     description "Display pcef subscriber summary";
     input {
       leaf logical-system {
         description "Display summary for specified logical system";
         type string;
       }
       leaf routing-instance {
         description "Display summary for specified routing instance";
         type string;
       }
       leaf physical-interface {
         description "Physical Interface name";
         type interface-wildcard;
       }
       leaf port {
         description "Display full subscriber port summary";
         type empty;
       }
       leaf pic {
         description "Display full subscriber pic summary";
         type empty;
       }
       leaf slot {
         description "Display full subscriber slot summary";
         type empty;
       }
       leaf all {
         description "Display full subscriber summary";
         type empty;
       }
     }
   }
   rpc get-pcef-pic {
     description "Show physical interface card information";
     input {
       leaf fpc-slot {
         description "FPC slot number";
         type uint32 {
           range "0 .. 63";
         }
       }
       leaf pic-slot {
         description "PIC slot number";
         type uint32 {
           range "0 .. 3";
         }
       }
       leaf display {
         default "terse";
         type enumeration {
           enum "terse" {
             description "Display terse output";
           }
         }
       }
     }
   }
   rpc get-lrf-statistics {
     description "Show lrf statistics";
     output {
       container lrf-statistics-summary {
         container lrf-statistics {
           description "LRF statistics";
           leaf interface-name {
             type string;
             description "Name of the adaptive services interface";
           }
           leaf flow-packets {
             type int32;
             description "Flow packets";
           }
           leaf flow-bytes {
             type int32;
             description "Flow bytes";
           }
           leaf active-flows {
             type int32;
             description "Active flows";
           }
           leaf total-flows {
             type int32;
             description "Total flows";
           }
         }
       }
     }
   }
   rpc get-lrf-collector-statistics {
     description "Show lrf collector statistics";
     input {
       leaf collector-name {
         description "Name of collector";
         type string;
       }
     }
     output {
       container lrf-collector-statistics-summary {
         container lrf-collector-statistics {
           description "LRF collector statistics";
           leaf interface-name {
             type string;
             description "Name of the adaptive services interface";
           }
           leaf tmpl-reg {
             type int32;
             description "Templates registered";
           }
           leaf tmpl-reg-failures {
             type int32;
             description "Template registration failures";
           }
           leaf tmpl-active {
             type int32;
             description "Templates active";
           }
           leaf sessions-received {
             type int32;
             description "Sessions received";
           }
           leaf sessions-ignored {
             type int32;
             description "Sessions ignored";
           }
           leaf sessions-logged {
             type int32;
             description "Sessions logged";
           }
           leaf rec-export {
             type int32;
             description "Records exported";
           }
           leaf rec-export-failures {
             type int32;
             description "Record export failures";
           }
           leaf rec-export-volume {
             type int32;
             description "Records exported for volume";
           }
           leaf rec-export-time {
             type int32;
             description "Records exported for time";
           }
           leaf rec-export-session-close {
             type int32;
             description "Records exported for session close";
           }
         }
       }
     }
   }
   rpc get-lrf-rule-statistics {
     description "Show lrf rule statistics";
     input {
       leaf rule-name {
         description "Name of rule";
         type string;
       }
     }
     output {
       container lrf-rule-statistics-summary {
         container lrf-rule-statistics {
           description "LRF rule statistics";
           leaf interface-name {
             type string;
             description "Name of the adaptive services interface";
           }
           leaf rule-name {
             type string;
             description "Rule name";
           }
           leaf rule-tmpl-name {
             type string;
             description "Template name";
           }
           leaf rule-tmpl-reg {
             type int32;
             description "Templates registered";
           }
           leaf rule-tmpl-reg-failures {
             type int32;
             description "Template registration failures";
           }
           leaf rule-coll-name {
             type string;
             description "Collector name";
           }
           leaf rule-sessions-received {
             type int32;
             description "Sessions received";
           }
           leaf rule-sessions-ignored {
             type int32;
             description "Sessions ignored";
           }
           leaf rule-sessions-logged {
             type int32;
             description "Sessions logged";
           }
           leaf rule-rec-export {
             type int32;
             description "Records exported";
           }
           leaf rule-rec-export-failures {
             type int32;
             description "Record export failures";
           }
           leaf rule-rec-export-volume {
             type int32;
             description "Records exported for volume";
           }
           leaf rule-rec-export-time {
             type int32;
             description "Records exported for time";
           }
           leaf rule-rec-export-session-close {
             type int32;
             description "Records exported for session close";
           }
         }
       }
     }
   }
   rpc get-lrf-template {
     description "Show lrf template";
     input {
       leaf template-type {
         description "Template type";
         type enumeration {
           enum "ipv4" {
             description "Ipv4 template type";
           }
           enum "ipv4-extended" {
             description "Ipv4 extended template type";
           }
           enum "ipv6" {
             description "Ipv6 template type";
           }
           enum "ipv6-extended" {
             description "Ipv6 extended template type";
           }
           enum "transport-layer" {
             description "Transport layer template type";
           }
           enum "flow-id" {
             description "Flow id template type";
           }
           enum "ipflow" {
             description "IPFlow type";
           }
           enum "ipflow-ts" {
             description "IPFlow TS type";
           }
           enum "ipflow-extended" {
             description "IPFlow extended type";
           }
           enum "device-data" {
             description "Device data template type";
           }
           enum "l7-app" {
             description "L7 APP template type";
           }
           enum "http" {
             description "HTTP type";
           }
           enum "mobile-subscriber" {
             description "Mobile subscriber type";
           }
           enum "subscriber-data" {
             description "Subscriber data type";
           }
           enum "ifl-subscriber" {
             description "IFL based subscriber type";
           }
           enum "wireline-subscriber" {
             description "Wireline subscriber type";
           }
           enum "ipflow-tcp-ts" {
             description "IPFLOW TCP timestamp type";
           }
           enum "video" {
             description "Video type";
           }
           enum "dns" {
             description "DNS type";
           }
           enum "status-code-distribution" {
             description "Status code distribution for HTTP and DNS";
           }
           enum "pcc" {
             description "PCC type";
           }
         }
         mandatory true;
       }
     }
     output {
       container lrf-template {
         leaf export-field {
           type string;
         }
         leaf export-field-id {
           type int32;
         }
         leaf export-field-len {
           type int32;
         }
         leaf export-field-vendor {
           type string;
         }
       }
     }
   }
   rpc get-service-accounting-information {
     description "Show sampled accounting service";
   }
   rpc get-service-accounting-status-information {
     description "Show service accounting parameters";
     input {
       leaf status-information {
         description "Name of service, wildcard, or 'all'";
         type string;
       }
     }
   }
   rpc get-service-accounting-status-inline-jflow-information {
     description "Show service accounting inline Jflow parameters";
     input {
       leaf inline-jflow-information {
         description "FPC Slot for inline Jflow";
         type uint32 {
           range "0 .. 63";
         }
       }
     }
   }
   rpc get-service-accounting-usage-information {
     description "Show CPU usage";
     input {
       leaf usage-information {
         description "Name of service, wildcard, or 'all'";
         type string;
       }
     }
   }
   rpc get-service-accounting-memory-information {
     description "Show memory information";
     input {
       leaf memory-information {
         description "Name of service, wildcard, or 'all'";
         type string;
       }
     }
   }
   rpc get-service-accounting-flow-information {
     description "Show flow information";
     input {
       leaf flow-information {
         description "Name of service, wildcard, or 'all'";
         type string;
       }
       leaf logical-system {
         description "Name of logical system";
         type string {
           junos:posix-pattern "^[a-zA-Z0-9_-]{1,63}$";
           junos:pattern-message "Logical-system name is a string consisting of up         to 63 letters, numbers, dashes and underscores";
         }
       }
     }
   }
   rpc get-service-accounting-status-inline-jflow-flow-information {
     description "Show service accounting inline Jflow flow information";
     input {
       leaf inline-jflow-flow-information {
         description "FPC Slot for inline Jflow";
         type uint32 {
           range "0 .. 63";
         }
       }
     }
   }
   rpc get-service-accounting-flow-detail {
     description "Show flow detail";
     input {
       leaf flow-detail-information {
         description "Name of service, wildcard, or 'all'";
         type string;
       }
       leaf limit {
         description "Maximum number of flows to display";
         type uint32;
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf destination-prefix {
         description "Filter term destination prefix";
         type string;
       }
       leaf source-port {
         description "Filter term source port";
         type uint32;
       }
       leaf destination-port {
         description "Filter term destination port";
         type uint32;
       }
       leaf input-snmp-interface-index {
         description "Filter term input SNMP interface index";
         type uint32;
       }
       leaf output-snmp-interface-index {
         description "Filter term output SNMP interface index";
         type uint32;
       }
       leaf source-as {
         description "Filter term source AS";
         type uint32;
       }
       leaf destination-as {
         description "Filter term destination AS";
         type uint32;
       }
       leaf tos {
         description "Filter term ToS";
         type uint32;
       }
       leaf proto {
         description "Filter term protocol";
         type uint32;
       }
     }
   }
   rpc get-service-accounting-aggregation-information {
     description "Show aggregation information";
   }
   rpc get-service-accounting-aggregation-as-information {
     description "Show aggregation type AS";
     input {
       leaf as-information {
         description "Name of service, wildcard, or 'all'";
         type string;
       }
       leaf limit {
         description "Maximum number of flows to display";
         type uint32;
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-as {
         description "Filter term source-as";
         type uint32;
       }
       leaf destination-as {
         description "Filter term destination AS";
         type uint32;
       }
       leaf input-snmp-interface-index {
         description "Filter term input SNMP interface index";
         type uint32;
       }
       leaf output-snmp-interface-index {
         description "Filter term output SNMP interface index";
         type uint32;
       }
     }
   }
   rpc get-service-accounting-aggregation-protocol-port-information {
     description "Show aggregation type protocol-port";
     input {
       leaf protocol-port-information {
         description "Name of service, wildcard, or 'all'";
         type string;
       }
       leaf limit {
         description "Maximum number of flows to display";
         type uint32;
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf proto {
         description "Filter term protocol";
         type uint32;
       }
       leaf source-port {
         description "Filter term source port";
         type uint32;
       }
       leaf destination-port {
         description "Filter term destination port";
         type uint32;
       }
     }
   }
   rpc get-service-accounting-aggregation-source-prefix-information {
     description "Show aggregation type source-prefix";
     input {
       leaf source-prefix-information {
         description "Name of service, wildcard, or 'all'";
         type string;
       }
       leaf limit {
         description "Maximum number of flows to display";
         type uint32;
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf source-as {
         description "Filter term source-as";
         type uint32;
       }
       leaf input-snmp-interface-index {
         description "Filter term input SNMP interface index";
         type uint32;
       }
     }
   }
   rpc get-service-accounting-aggregation-destination-prefix-information {
     description "Show aggregation type destination-prefix";
     input {
       leaf destination-prefix-information {
         description "Name of service, wildcard, or 'all'";
         type string;
       }
       leaf limit {
         description "Maximum number of flows to display";
         type uint32;
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf destination-prefix {
         description "Filter term destination prefix";
         type string;
       }
       leaf destination-as {
         description "Filter term destination-as";
         type uint32;
       }
       leaf output-snmp-interface-index {
         description "Filter term output SNMP interface index";
         type uint32;
       }
     }
   }
   rpc get-service-accounting-aggregation-source-destination-prefix-information {
     description "Show aggregation type source-destination-prefix";
     input {
       leaf source-destination-prefix-information {
         description "Name of service, wildcard, or 'all'";
         type string;
       }
       leaf limit {
         description "Maximum number of flows to display";
         type uint32;
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf source-as {
         description "Filter term source-as";
         type uint32;
       }
       leaf input-snmp-interface-index {
         description "Filter term input SNMP interface index";
         type uint32;
       }
       leaf destination-prefix {
         description "Filter term destination prefix";
         type string;
       }
       leaf destination-as {
         description "Filter term destination-as";
         type uint32;
       }
       leaf output-snmp-interface-index {
         description "Filter term output SNMP interface index";
         type uint32;
       }
     }
   }
   rpc get-service-accounting-aggregation-template-information {
     description "Show aggregation type template";
     input {
       leaf template-name {
         description "Name of template";
         type string;
         mandatory true;
       }
       leaf logical-system {
         description "Name of logical system";
         type string {
           junos:posix-pattern "^[a-zA-Z0-9_-]{1,63}$";
           junos:pattern-message "Logical-system name is a string consisting of up         to 63 letters, numbers, dashes and underscores";
         }
       }
       leaf display {
         default "terse";
         type enumeration {
           enum "extensive" {
             description "Display extensive output";
           }
           enum "detail" {
             description "Display detailed output";
           }
           enum "terse" {
             description "Display terse output (default)";
           }
         }
       }
     }
   }
   rpc get-service-accounting-errors-information {
     description "Show error statistics";
     input {
       leaf error-information {
         description "Name of service, wildcard, or 'all'";
         type string;
       }
     }
   }
   rpc get-service-accounting-error-inline-jflow-information {
     description "Show service accounting inline Jflow error information";
     input {
       leaf inline-jflow-error-information {
         description "FPC Slot for inline Jflow";
         type uint32 {
           range "0 .. 63";
         }
       }
     }
   }
   rpc get-packet-distribution-information {
     description "Show packet size distribution";
     input {
       leaf packet-size-distribution-information {
         description "Name of service, wildcard, or 'all'";
         type string;
       }
     }
   }
   rpc get-service-video-monitoring-information {
     description "Show video-monitoring information";
   }
   rpc get-service-video-monitoring-mdi-information {
     description "Show MDI flows information";
   }
   rpc get-service-video-monitoring-mdi-stats-information {
     description "Show MDI flows stats information";
     input {
       leaf fpc-slot {
         description "FPC Slot number";
         type uint32 {
           range "0 .. 63";
         }
         mandatory true;
       }
     }
   }
   rpc get-service-video-monitoring-mdi-errors-information {
     description "Show MDI flows error information";
     input {
       leaf fpc-slot {
         description "FPC Slot number";
         type uint32 {
           range "0 .. 63";
         }
         mandatory true;
       }
     }
   }
   rpc get-service-video-monitoring-mdi-flows-information {
     description "Show MDI flows information";
     input {
       leaf fpc-slot {
         description "FPC Slot number";
         type uint32 {
           range "0 .. 63";
         }
         mandatory true;
       }
       leaf flow-count {
         description "Count of flows to display";
         type uint32 {
           range "1 .. 10000";
         }
       }
       leaf flow-identifier {
         description "Flow Identifier";
         type uint32;
       }
       leaf source-address {
         description "Source address of flow";
         type ipv4addr;
       }
       leaf destination-address {
         description "Destination address of flow";
         type ipv4addr;
       }
       leaf source-port {
         description "Source port of flow";
         type uint32;
       }
       leaf destination-port {
         description "Destination port of flow";
         type uint32;
       }
       leaf template-name {
         description "Template name";
         type string;
       }
       leaf ifl-name {
         description "Interface name";
         type interface-name;
       }
       leaf flow-direction {
         description "Direction of flow";
         type enumeration {
           enum "input" {
             description "Input flows";
           }
           enum "output" {
             description "Output flows";
           }
         }
       }
       leaf flow-type {
         description "Type of flow";
         type enumeration {
           enum "udp" {
             description "UDP flows";
           }
           enum "rtp" {
             description "RTP flows";
           }
         }
       }
       leaf flow-display {
         description "Display terse/details output";
         type enumeration {
           enum "detail" {
             description "Display detailed output";
           }
           enum "brief" {
             description "Display breif output (default)";
           }
         }
       }
     }
   }
   rpc get-services-video-monitoring-mdi-alarms-information {
     description "Show Alarm information";
   }
   rpc get-services-video-monitoring-mdi-alarms-stats-information {
     description "Show MDI alarm stats information";
     input {
       leaf fpc-slot {
         description "FPC Slot number";
         type uint32 {
           range "0 .. 63";
         }
         mandatory true;
       }
     }
   }
   rpc get-service-set-memory-statistics {
     description "Show service interface memory utilization";
     input {
       leaf service-set {
         description "Name of service set";
         type string;
       }
       leaf interface {
         description "Name of adaptive services interface";
         type string;
       }
     }
     output {
       container service-set-memory-statistics-information {
         container service-set-memory-statistics {
           description "Memory usage statistics";
           leaf interface-name {
             type string;
             description "Name of the adaptive services interface";
           }
           leaf service-set-name {
             type string;
             description "Name of the service set";
           }
           leaf bytes-used {
             type uint64;
             description "Memory used (bytes)";
           }
         }
       }
     }
   }
   rpc get-service-set-cpu-statistics {
     description "Show service interface CPU utilization as a percentage";
     input {
       leaf service-set {
         description "Name of service set";
         type string;
       }
       leaf interface {
         description "Name of adaptive services interface";
         type string;
       }
     }
     output {
       container service-set-cpu-statistics-information {
         container service-set-cpu-statistics {
           description "CPU usage statistics";
           leaf interface-name {
             type string;
             description "Name of the adaptive services interface";
           }
           leaf service-set-name {
             type string;
             description "Name of the service set";
           }
           leaf cpu-utilization-percent {
             type uint32;
             description "CPU utilization (percent)";
           }
         }
       }
     }
   }
   rpc get-service-set-summary-information {
     description "Show service set summary information";
     input {
       leaf interface {
         description "Name of adaptive services interface";
         type string;
       }
     }
     output {
       container service-set-summary-information {
         container summary {
           description "Service set summary information";
           container service-set-summary-information-entry {
             description "Service set summary information entry";
             leaf interface-name {
               type string;
               description "Name of the adaptive services interface";
             }
             container service-set-service-type-entry {
               description "Service set service type entry";
             }
           }
         }
         container interface-summary {
           description "Service set summary information";
           container service-set-summary-information-entry {
             description "Service set summary information entry";
             leaf interface-name {
               type string;
               description "Name of the adaptive services interface";
             }
             container service-set-service-type-entry {
               description "Service set service type entry";
             }
           }
         }
       }
     }
   }
   rpc get-service-set-packet-drop-statistics {
     description "Show service set packet drop statistics";
     input {
       leaf interface {
         description "Name of adaptive services interface";
         type string;
       }
     }
     output {
       container service-set-packet-drop-statistics {
         container brief {
           container service-set-packet-drops {
             description "Packet-drop statistics";
             leaf interface-name {
               type string;
               description "Name of the adaptive services interface";
             }
             leaf service-set-name {
               type string;
               description "Name of the service set";
             }
             leaf cpulimit-drops {
               type uint32;
               description "Drops because CPU usage limit is reached";
             }
             leaf memlimit-drops {
               type uint32;
               description "Drops because Memory usage limit is reached";
             }
             leaf flowlimit-drops {
               type uint32;
               description "Drops because Flow limit is reached";
             }
           }
         }
         container detail {
           container service-set-packet-drops {
             description "Packet-drop statistics";
             leaf interface-name {
               type string;
               description "Name of the adaptive services interface";
             }
             leaf service-set-name {
               type string;
               description "Name of the service set";
             }
             leaf cpulimit-drops {
               type uint32;
               description "Drops because CPU usage limit is reached";
             }
             leaf memlimit-drops {
               type uint32;
               description "Drops because Memory usage limit is reached";
             }
             leaf flowlimit-drops {
               type uint32;
               description "Drops because Flow limit is reached";
             }
             leaf tcpalg-drops {
               type uint32;
               description "Drops because tcp alg control packet is too big";
             }
           }
         }
       }
     }
   }
   rpc get-service-set-drop-flow-statistics {
     description "Show drop flow stats";
     input {
       leaf interface {
         description "Name of adaptive services interface";
         type string;
       }
     }
     output {
       container service-set-drop-flow-statistics {
         container brief {
           container service-set-drop-flows {
             description "Drop flow statistics";
             leaf interface-name {
               type string;
               description "Name of the adaptive services interface";
             }
             leaf service-set-name {
               type string;
               description "Name of the service set";
             }
             leaf current-ingress-drop-flow {
               type uint32;
               description "Current number of ingress drop flows";
             }
             leaf current-egress-drop-flow {
               type uint32;
               description "Current number of egress drop flows";
             }
             leaf pkt-drop-exceed-ingress-drop-flow-limit {
               type uint32;
               description "Number of packets dropped due to ingress drop flow limit";
             }
             leaf pkt-drop-exceed-egress-drop-flow-limit {
               type uint32;
               description "Number of packets dropped due to egress drop flow limit";
             }
           }
         }
         container detail {
           container service-set-drop-flows {
             description "Drop flow statistics";
             leaf interface-name {
               type string;
               description "Name of the adaptive services interface";
             }
             leaf service-set-name {
               type string;
               description "Name of the service set";
             }
             leaf current-ingress-drop-flow {
               type uint32;
               description "Current number of ingress drop flows";
             }
             leaf current-egress-drop-flow {
               type uint32;
               description "Current number of egress drop flows";
             }
             leaf pkt-drop-exceed-ingress-drop-flow-limit {
               type uint32;
               description "Number of packets dropped due to ingress drop flow limit";
             }
             leaf pkt-drop-exceed-egress-drop-flow-limit {
               type uint32;
               description "Number of packets dropped due to egress drop flow limit";
             }
           }
         }
       }
     }
   }
   rpc get-service-set-integrity-drops-statistics {
     description "Show header integrity drops";
     input {
       leaf service-set {
         description "Name of service set";
         type string;
       }
       leaf interface {
         description "Name of adaptive services interface";
         type string;
       }
     }
     output {
       container service-set-integrity-drops-statistics {
         container extensive {
           description "Statistics of packet drops due to failed header integrity checks";
           container service-set-integrity-drops-entry {
             description "Packet drops due to integrity-checks entry";
             leaf interface-name {
               type string;
               description "Name of the adaptive services interface";
             }
             container sset-integrity-drops-service-set-entry {
               description "Header integrity check drops statistics entry";
               container error-counters {
                 description "Summarized protocol processing errors";
                 leaf ip-errors {
                   type uint32;
                   description "IP processing errors";
                 }
                 leaf tcp-errors {
                   type uint32;
                   description "TCP processing errors";
                 }
                 leaf udp-errors {
                   type uint32;
                   description "UDP processing errors";
                 }
                 leaf icmp-errors {
                   type uint32;
                   description "ICMP processing errors";
                 }
                 leaf non-ip-packets {
                   type uint32;
                   description "Non-IP packets";
                 }
                 leaf alg-errors {
                   type uint32;
                   description "ALG processing errors";
                 }
               }
               container ip-error-counters {
                 description "Extensive output of IP processing errors";
                 leaf ip-length-error {
                   type uint32;
                   description "IP packet length inconsistencies";
                 }
                 leaf ip-header-length-error {
                   type uint32;
                   description "Minimum IP header length check failures";
                 }
                 leaf long-packet {
                   type uint32;
                   description "Reassembled packet exceeds maximum IP length (65,535 bytes)";
                 }
                 leaf illegal-destination-address {
                   type uint32;
                   description "Illegal destination address";
                 }
                 leaf illegal-source-address {
                   type uint32;
                   description "Illegal source address";
                 }
                 leaf ttl-zero {
                   type uint32;
                   description "IP packets received with a TTL value of 0";
                 }
                 leaf illegal-ip-protocol {
                   type uint32;
                   description "Illegal IP protocol number ";
                 }
                 leaf non-ipv6 {
                   type uint32;
                   description "Non-IPv6 packets";
                 }
                 leaf land-attack {
                   type uint32;
                   description "IP source address same as destination address";
                 }
                 leaf not-ip-packet {
                   type uint32;
                   description "Not IP Packet";
                 }
                 leaf non-ipv4 {
                   type uint32;
                   description "Non-IPv4 packets";
                 }
                 leaf bad-checksum {
                   type uint32;
                   description "Bad checksum";
                 }
                 leaf illegal-fragment-length {
                   type uint32;
                   description "Illegal IP fragment length";
                 }
                 leaf fragment-overlap {
                   type uint32;
                   description "IP fragment overlap";
                 }
                 leaf fragment-reassembly-timeout {
                   type uint32;
                   description "IP fragment reassembly timeout";
                 }
                 leaf fragment-limit-exceeded {
                   type uint32;
                   description "IP fragment limit exceeded";
                 }
                 leaf unknown {
                   type uint32;
                   description "Unknown errors";
                 }
               }
               container tcp-error-counters {
                 description "Extensive output of TCP processing errors";
                 leaf tcp-header-length-error {
                   type uint32;
                   description "TCP header length inconsistencies";
                 }
                 leaf tcp-zero-port {
                   type uint32;
                   description "Source or destination port number is zero";
                 }
                 leaf illegal-sequence-number-flags {
                   type uint32;
                   description "Illegal sequence number and flags combinations";
                 }
                 leaf syn-attack {
                   type uint32;
                   description "SYN attack";
                 }
                 leaf non-syn-first-packet {
                   type uint32;
                   description "First packet not a SYN message";
                 }
                 leaf tcp-port-scan {
                   type uint32;
                   description "TCP port scan";
                 }
                 leaf bad-syn-cookie-response {
                   type uint32;
                   description "Bad SYN cookie response";
                 }
                 leaf tcp-recon-sequence-number-error {
                   type uint32;
                   description "TCP reconstructor sequence number error";
                 }
                 leaf tcp-recon-retransmits {
                   type uint32;
                   description "TCP reconstructor retransmissions";
                 }
                 leaf tcp-partially-opened-connection-timeout-syn-rcvd {
                   type uint32;
                   description "TCP partially opened connection timeout";
                 }
                 leaf tcp-partially-opened-connection-timeout-syn-ack-rcvd {
                   type uint32;
                   description "TCP partially opened connection timeout";
                 }
                 leaf tcp-partially-closed-connection-reuse {
                   type uint32;
                   description "TCP partially closed connection reuse";
                 }
                 leaf tcp-3way-error-client-sent-syn-ack {
                   type uint32;
                   description "TCP 3-way error - client sent SYN+ACK";
                 }
                 leaf tcp-3way-error-server-sent-ack {
                   type uint32;
                   description "TCP 3-way error - server sent ACK";
                 }
                 leaf tcp-3way-error-syn-seq-num-retrans-mismatch {
                   type uint32;
                   description "TCP 3-way error - SYN seq number retransmission mismatch";
                 }
                 leaf tcp-3way-error-rst-seq-num-mismatch {
                   type uint32;
                   description "TCP 3-way error - RST seq number mismatch";
                 }
                 leaf tcp-3way-error-fin-received {
                   type uint32;
                   description "TCP 3-way error - FIN received";
                 }
                 leaf tcp-3way-error-invalid-flags {
                   type uint32;
                   description "TCP 3-way error - invalid TCP flag combination";
                 }
                 leaf tcp-3way-error-syn-no-flow-initiator {
                   type uint32;
                   description "TCP 3-way error - SYN recvd but no client flows";
                 }
                 leaf tcp-3way-error-first-packet-syn-ack {
                   type uint32;
                   description "TCP 3-way error - first packet SYN+ACK";
                 }
                 leaf tcp-3way-error-first-packet-fin-ack {
                   type uint32;
                   description "TCP 3-way error - first packet FIN+ACK";
                 }
                 leaf tcp-3way-error-first-packet-fin {
                   type uint32;
                   description "TCP 3-way error - first packet FIN";
                 }
                 leaf tcp-3way-error-first-packet-rst {
                   type uint32;
                   description "TCP 3-way error - first packet RST";
                 }
                 leaf tcp-3way-error-first-packet-ack {
                   type uint32;
                   description "TCP 3-way error - first packet ack";
                 }
                 leaf tcp-3way-error-first-packet-invalid-flags {
                   type uint32;
                   description "TCP 3-way error - first packet ack";
                 }
                 leaf tcp-close-error-no-final-ack {
                   type uint32;
                   description "TCP close error - no final ack";
                 }
                 leaf tcp-resumed-flow {
                   type uint32;
                   description "TCP Resumed Flow";
                 }
               }
               container udp-error-counters {
                 description "Extensive output of UDP processing errors";
                 leaf udp-header-length-error {
                   type uint32;
                   description "IP data length is less than minimum UDP header length (8 bytes)";
                 }
                 leaf udp-zero-port {
                   type uint32;
                   description "Source or destination port number is zero";
                 }
                 leaf udp-port-scan {
                   type uint32;
                   description "UDP port scan (ICMP error seen for UDP flow)";
                 }
               }
               container icmp-error-counters {
                 description "Extensive output of ICMP processing errors";
                 leaf icmp-length-error {
                   type uint32;
                   description "IP data length less than minimum ICMP header length (8 bytes)";
                 }
                 leaf icmp-error-length-error {
                   type uint32;
                   description "ICMP error length inconsistencies";
                 }
                 leaf ping-duplicate-sequence-number {
                   type uint32;
                   description "Duplicate ping sequence number";
                 }
                 leaf ping-mismatched-sequence-number {
                   type uint32;
                   description "Mismatched ping sequence number";
                 }
                 leaf icmp-error-no-matching-flow {
                   type uint32;
                   description "No matching flow for ICMP error packet";
                 }
               }
             }
           }
         }
       }
     }
   }
   rpc get-service-set-tcp-tracker-statistics {
     description "Show tcp tracker statistics";
     input {
       leaf service-set {
         description "Name of service set";
         type string;
       }
       leaf interface {
         description "Name of adaptive services interface";
         type string;
       }
     }
     output {
       container msp-service-set-tcp-statistics {
         container extensive {
           description "Service set TCP statistics";
           container msp-service-set-tcp-statistics-entry {
             description "Service set TCP statistics entry";
             leaf interface-name {
               type string;
               description "Name of the adaptive services interface";
             }
             container msp-sset-tcp-statistics-service-set-entry {
               description "Service set TCP statistics entry";
               container tcp-open-close-counters {
                 description "Extensive output of TCP open close counters";
                 leaf tcp-first-pkt-not-syn {
                   type uint32;
                   description "TCP first packet non-syn";
                 }
                 leaf tcp-first-pkt-rst {
                   type uint32;
                   description "TCP first packet reset";
                 }
                 leaf tcp-first-pkt-fin {
                   type uint32;
                   description "TCP first packet FIN";
                 }
                 leaf tcp-non-syn-discard {
                   type uint32;
                   description "TCP non syn discard";
                 }
                 leaf tcp-ext-alloc-fail {
                   type uint32;
                   description "TCP extension alloc fail";
                 }
               }
               container tcp-sequence-error-counters {
                 description "Extensive output of TCP sequence error counters";
                 leaf tcp-invalid-syn-ack {
                   type uint32;
                   description "TCP invalid syn ack";
                 }
                 leaf tcp-invalid-ack-win-check {
                   type uint32;
                   description "TCP invalid ack window check";
                 }
                 leaf tcp-invalid-xmit-syn {
                   type uint32;
                   description "TCP invalid syn transmit";
                 }
                 leaf tcp-invalid-rst-in-listen {
                   type uint32;
                   description "TCP invalid reset in listen";
                 }
                 leaf tcp-invalid-rst-in-syn-recv {
                   type uint32;
                   description "TCP invalid reset in syn received";
                 }
                 leaf tcp-invalid-rst-in-syn-sent {
                   type uint32;
                   description "TCP invalid reset in syn sent";
                 }
                 leaf tcp-invalid-flags-handshake {
                   type uint32;
                   description "TCP invalid flags handshake";
                 }
                 leaf tcp-reverse-flow-null-first-pkt-non-syn {
                   type uint32;
                   description "TCP reverse flow is null and first packet is not syn";
                 }
                 leaf tcp-reverse-flow-null {
                   type uint32;
                   description "TCP reverse flow null";
                 }
               }
             }
           }
         }
       }
     }
   }
   rpc get-service-set-tcp-mss-statistics {
     description "Show service set TCP MSS statistics";
     input {
       leaf interface {
         description "Name of adaptive services interface";
         type string;
       }
     }
     output {
       container service-set-tcp-mss-statistics {
         container service-set-tcp-mss {
           description "TCP MSS statistics";
           leaf interface-name {
             type string;
             description "Name of the adaptive services interface";
           }
           leaf service-set-name {
             type string;
             description "Name of the service set";
           }
           leaf syn-received {
             type uint32;
             description "Number of SYN packets received for the service set";
           }
           leaf syn-modified {
             type uint32;
             description "Number of SYN packets whose MSS setting was modified";
           }
         }
       }
     }
   }
   rpc get-service-set-syslog-statistics {
     description "Show service set syslog statistics";
     input {
       leaf service-set {
         description "Name of service set";
         type string;
       }
       leaf interface {
         description "Name of adaptive services interface";
         type string;
       }
       leaf display {
         default "brief";
         type enumeration {
           enum "brief" {
             description "Display brief output (default)";
           }
           enum "detail" {
             description "Display detailed output";
           }
         }
       }
     }
     output {
       container syslog-stats-interface {
         leaf syslog-stats-interface-name {
           type string;
           description "Interface name";
         }
       }
     }
   }
   rpc get-service-set-jflow-log-statistics {
     description "Show service set jflow-log statistics";
     input {
       leaf service-set {
         description "Name of service set";
         type string;
       }
       leaf interface {
         description "Name of adaptive services interface";
         type string;
       }
       leaf display {
         default "brief";
         type enumeration {
           enum "brief" {
             description "Display brief output (default)";
           }
           enum "detail" {
             description "Display detailed output";
           }
         }
       }
     }
     output {
       container jflow-log-stats-interface {
         leaf jflow-log-stats-interface-name {
           type string;
           description "Interface name";
         }
       }
     }
   }
   rpc get-service-set-ids-drops-statistics {
     description "Show service set IDS drops statistics";
     input {
       leaf service-set {
         description "Name of service set";
         type string;
       }
       leaf interface {
         description "Name of adaptive services interface";
         type string;
       }
     }
   }
   rpc get-service-set-ids-session-limits-counters-statistics {
     description "Show the session-limits counters";
     input {
       leaf service-set {
         description "Name of service set";
         type string;
       }
       leaf interface {
         description "Name of adaptive services interface";
         type string;
       }
     }
   }
   rpc get-service-set-plugin-summary {
     description "Show service set plugins summary";
     input {
       leaf interface {
         description "Name of extension provider interface";
         type string;
       }
     }
     output {
       container service-set-plugin-summary {
         leaf interface-name {
           type string;
           description "Name of the adaptive services interface";
         }
         container service-set-plugin-information {
           description "Service set plugin information";
           leaf service-set-name {
             type string;
             description "Name of the service set";
           }
           leaf service-set-state {
             type string;
             description "Service set state";
           }
           leaf plugins-configured {
             type uint32;
             description "Plugins configured";
           }
           container service-set-plugin-entry {
             description "Service set plugin details";
             leaf plugin-name {
               type string;
               description "Name of the plugin";
             }
             leaf plugin-id {
               type uint32;
               description "Plugin ID";
             }
           }
         }
       }
     }
   }
   rpc get-services-match-policies {
     description "Show match-policy information";
     input {
       leaf service-set {
         description "Name of service set";
         type string;
       }
       leaf source-ip {
         description "Source address";
         type ipprefix;
       }
       leaf source-port {
         description "Source port to use as match";
         type uint16;
       }
       leaf destination-ip {
         description "Destination address";
         type ipprefix;
       }
       leaf destination-port {
         description "Destination port to use as match";
         type uint16;
       }
       leaf protocol {
         description "IP protocol name or number";
         type string;
       }
       leaf result-count {
         description "The number of policy matches to display";
         type uint16;
       }
       leaf match-direction {
         description "Match direction";
         type enumeration {
           enum "input" {
             description "Direction input";
           }
           enum "output" {
             description "Direction output";
           }
         }
       }
     }
     output {
       container services-match-policies-information {
         container services-match-policies {
           description "Rule match result";
           leaf policy-match {
             type string;
             description "Policy match";
           }
           leaf policy-direction {
             type string;
             description "Policy direction";
           }
           leaf policy-action {
             type string;
             description "Policy action";
           }
           leaf policy-state {
             type string;
             description "Policy state";
           }
           leaf source-address-title {
             type string;
             description "Source address title";
           }
           leaf source-address {
             type string;
             description "Source address";
           }
           leaf destination-address-title {
             type string;
             description "Destination address tite";
           }
           leaf destination-address {
             type string;
             description "Destination address";
           }
           leaf application-type {
             type string;
             description "Application type";
           }
           leaf ip-protocol {
             type uint32;
             description "Ip protocol";
           }
           leaf policy-timeout {
             type string;
             description "Policy timeout";
           }
           leaf destination-port {
             type string;
             description "Destination port";
           }
         }
       }
     }
   }
   rpc get-service-nat-pool-information {
     description "Show NAT pools information";
     input {
       leaf pool-name {
         description "Name of pool";
         type string;
       }
       leaf display {
         default "brief";
         type enumeration {
           enum "brief" {
             description "Display brief output (default)";
           }
           enum "detail" {
             description "Display detailed output";
           }
         }
       }
     }
     output {
       container service-nat-pool-information {
         container sfw-per-service-set-nat-pool {
           description "NAT pool information for one service set";
           container brief {
             description "NAT pool information for one service set";
             leaf interface-name {
               type string;
               description "Name of the adaptive services interface";
             }
             leaf service-set-name {
               type string;
               description "Name of the service set";
             }
             container service-nat-pool {
               description "NAT pool information";
               leaf pool-name {
                 type string;
                 description "Name of the NAT pool";
               }
               leaf translation-type {
                 type string;
                 description "Type of Network Address Translation";
               }
               leaf pool-address-range {
                 type string;
                 description "Range of port addresses";
               }
               leaf pool-port-range {
                 type string;
                 description "Range of port numbers";
               }
               leaf pool-ports-in-use {
                 type int32;
                 description "Number of ports in use";
               }
               leaf port-block-type {
                 type string;
                 description "Type of port block";
               }
               leaf port-block-size {
                 type uint32;
                 description "Number of ports in a port block";
               }
               leaf max-blocks-per-address {
                 type uint32;
                 description "Max number of port blocks per private address";
               }
               leaf active-block-timeout {
                 type uint32;
                 description "Activity timeout of port block";
               }
               leaf effective-pba-port-range {
                 type string;
                 description "Effective range of port numbers";
               }
               leaf effective-port-blocks {
                 type uint32;
                 description "Effective number of port blocks";
               }
               leaf effective-ports {
                 type uint32;
                 description "Effective number of ports";
               }
               leaf port-block-efficiency {
                 type string;
                 description "Port block efficiency";
               }
               leaf pool-address-start {
                 type string;
                 description "Start of address range";
               }
               leaf pool-address-end {
                 type string;
                 description "End of address range";
               }
               leaf pool-port-low {
                 type int32;
                 description "Start of port range";
               }
               leaf pool-port-high {
                 type int32;
                 description "End of port range";
               }
             }
           }
           container detail {
             description "NAT pool information for one service set";
             leaf interface-name {
               type string;
               description "Name of the adaptive services interface";
             }
             leaf service-set-name {
               type string;
               description "Name of the service set";
             }
             container service-nat-pool {
               description "NAT pool information";
               leaf pool-name {
                 type string;
                 description "Name of the NAT pool";
               }
               leaf translation-type {
                 type string;
                 description "Type of Network Address Translation";
               }
               leaf pool-address-range {
                 type string;
                 description "Range of port addresses";
               }
               leaf pool-avail-addresses {
                 type uint32;
                 description "Total number of free addresses in the nat pool";
               }
               leaf pool-configured-port-range {
                 type string;
                 description "Range of port numbers configured";
               }
               leaf pool-preserve-range-enabled {
                 type string;
                 description "Preserve well known ports has been enabled";
               }
               leaf pool-port-range {
                 type string;
                 description "Range of port numbers";
               }
               leaf pool-ports-in-use {
                 type int32;
                 description "Number of ports in use";
               }
               leaf pool-out-of-port-errors {
                 type int32;
                 description "Number of port allocation failures";
               }
               leaf pool-out-of-address-errors {
                 type int32;
                 description "Number of address allocation failures";
               }
               leaf pool-max-ports-in-use {
                 type int32;
                 description "Maximum number of ports ever used in this pool so far";
               }
               leaf pool-addresses-in-use {
                 type int32;
                 description "Number of Addresses in use";
               }
               leaf pool-parity-port-errors {
                 type int32;
                 description "Number of port allocation failures due to parity";
               }
               leaf pool-preserve-range-errors {
                 type int32;
                 description "Number of port allocation failures due to preserve range";
               }
               leaf pool-app-port-errors {
                 type int32;
                 description "Number of APP port allocation failures";
               }
               leaf pool-app-exceed-port-limit-errors {
                 type int32;
                 description "Number of APP port allocation failures due to port limit";
               }
               leaf pool-mem-alloc-errors {
                 type int32;
                 description "Number of memory allocation failures";
               }
               leaf eif-inbound-session-count {
                 type int32;
                 description "Current number of eif inbound session ";
               }
               leaf eif-inbound-session-limit-exceed-drop {
                 type int32;
                 description "Current number of session drop due to exceeded eif limit ";
               }
               leaf pool-eif-current-inbound-flows-count {
                 type uint32;
                 description "Current eif inbound flows count";
               }
               leaf pool-eif-flow-limit-exceeded-drops {
                 type uint32;
                 description "Total eif flow limit exceeded drops";
               }
               leaf max-port-blocks-used {
                 type uint32;
                 description "Max number of port blocks used";
               }
               leaf port-blocks-in-use {
                 type uint32;
                 description "Current number of port blocks in use";
               }
               leaf port-block-allocation-errors {
                 type uint32;
                 description "Total port block allocation errors";
               }
               leaf port-block-mem-alloc-failure-errors {
                 type uint32;
                 description "Total port block memory allocation errors";
               }
               leaf pool-users {
                 type int32;
                 description "Number of subscribers using this pool";
               }
               leaf port-blocks-limit-exceeded-errors {
                 type uint32;
                 description "Total port blocks allocation limit exceeded errors";
               }
               leaf detnat-subscriber-exceeded-port-limits {
                 type uint32;
                 description "Subscriber port limit exceeded errors";
               }
               leaf pool-address-start {
                 type string;
                 description "Start of address range";
               }
               leaf pool-address-end {
                 type string;
                 description "End of address range";
               }
               leaf pool-port-low {
                 type int32;
                 description "Start of port range";
               }
               leaf pool-port-high {
                 type int32;
                 description "End of port range";
               }
             }
           }
         }
       }
     }
   }
   rpc get-service-detnat-information {
     description "Show deterministic NAT internal-host information";
     input {
       leaf nat-address {
         description "NAT address";
         type string;
         mandatory true;
       }
       leaf nat-port {
         description "NAT port";
         type string;
         mandatory true;
       }
     }
     output {
       container service-detnat-information {
         leaf service-set-name {
           type string;
           description "Name of the service set";
         }
         leaf interface-name {
           type string;
           description "Name of the adaptive services interface";
         }
         leaf pool-name {
           type string;
           description "Name of the NAT pool";
         }
         leaf detnat-internal-host {
           type string;
           description "Internal/Subscriber IP address";
         }
         leaf detnat-nat-ip {
           type string;
           description "NAT IP Address";
         }
         leaf detnat-nat-port-low {
           type string;
           description "NAT Port Start";
         }
         leaf detnat-nat-port-high {
           type string;
           description "NAT Port End";
         }
       }
     }
   }
   rpc get-service-detnat-pb-information {
     description "Show deterministic NAT port blocks assigned to internal-host";
     input {
       leaf internal-address {
         description "Subscriber IP address";
         type string;
         mandatory true;
       }
     }
     output {
       container service-detnat-information {
         leaf service-set-name {
           type string;
           description "Name of the service set";
         }
         leaf interface-name {
           type string;
           description "Name of the adaptive services interface";
         }
         leaf pool-name {
           type string;
           description "Name of the NAT pool";
         }
         leaf detnat-internal-host {
           type string;
           description "Internal/Subscriber IP address";
         }
         leaf detnat-nat-ip {
           type string;
           description "NAT IP Address";
         }
         leaf detnat-nat-port-low {
           type string;
           description "NAT Port Start";
         }
         leaf detnat-nat-port-high {
           type string;
           description "NAT Port End";
         }
       }
     }
   }
   rpc get-service-nat-ipv6-multicast-information {
     description "Show interfaces with IPv6 multicast filter";
     output {
       container service-nat-ipv6-multicast-interfaces-information {
         container brief {
           description "IPv6 multicast interfaces information";
           container service-nat-ipv6-multicast-interfaces {
             description "IPv6 multicast interfaces";
             leaf v6-multicast-interface-name {
               type string;
               description "Name of interface for IPv6 multicast";
             }
             leaf v6-multicast-configured-status {
               type string;
               description "IPv6 multicast configuration";
             }
             leaf v6-multicast-operation-status {
               type string;
               description "IPv6 multicast status";
             }
           }
         }
         container detail {
           description "IPv6 multicast interfaces information";
           container service-nat-ipv6-multicast-interfaces {
             description "IPv6 multicast interfaces";
             leaf v6-multicast-interface-name {
               type string;
               description "Name of interface for IPv6 multicast";
             }
             leaf v6-multicast-configured-status {
               type string;
               description "IPv6 multicast configuration";
             }
             leaf v6-multicast-operation-status {
               type string;
               description "IPv6 multicast status";
             }
             leaf v6-multicast-by-all {
               type string;
               description "IPv6 multicast configured by all keyword";
             }
           }
         }
       }
     }
   }
   rpc get-service-nat-mapping-address-pooling-paired {
     description "Show NAT Address Pooling Paired mapping";
     input {
       leaf private {
         description "Private IP/IPv6 prefix to use as filter";
         type string;
       }
       leaf public {
         description "Public IP/IPv6 prefix to use as filter";
         type string;
       }
     }
   }
   rpc get-service-nat-mapping-endpoint-independent {
     description "Show NAT Endpoint Independent mapping";
     input {
       leaf private {
         description "Private IP/IPv6 prefix to use as filter";
         type string;
       }
       leaf public {
         description "Public IP prefix to use as filter";
         type string;
       }
     }
   }
   rpc get-service-nat-mapping-pcp {
     description "Show NAT PCP mapping";
   }
   rpc get-service-nat-mapping-summary {
     description "Show NAT mapping entries count";
   }
   rpc get-service-nat-mapping-brief {
     description "Show NAT mapping brief";
     input {
       leaf pool-name {
         description "Name of pool";
         type string;
       }
     }
   }
   rpc get-service-nat-mapping-detail {
     description "Show NAT mapping detail";
     input {
       leaf pool-name {
         description "Name of pool";
         type string;
       }
     }
   }
   rpc get-service-nat-mapping-nptv6 {
     description "Show nptv6 translated address";
     input {
       leaf address {
         description "IPV6 Address";
         type ipv6addr;
         mandatory true;
       }
       leaf direction {
         type enumeration {
           enum "internal" {
             description "Internal-address";
           }
           enum "external" {
             description "External-address";
           }
         }
         mandatory true;
       }
     }
   }
   rpc get-service-nat-statistics-information {
     description "Show NAT statistics";
     input {
       leaf interface {
         description "Name of extension provider interface";
         type string;
       }
     }
     output {
       container service-nat-statistics-information {
         leaf interface-name {
           type string;
           description "Name of the adaptive services interface";
         }
         leaf query-unsupported-msg {
           type string;
           description "Query not supported on interface";
         }
         leaf nat-total-session-interest {
           type int32;
           description "Total Session Interest events";
         }
         leaf nat-total-session-create {
           type int32;
           description "Total Session Create events";
         }
         leaf nat-total-session-destroy {
           type int32;
           description "Total Session Destroy events";
         }
         leaf nat-total-session-pub-req {
           type int32;
           description "Total Session Pub Req events";
         }
         leaf nat-total-session-accepts {
           type int32;
           description "Total sessions accepted";
         }
         leaf nat-total-session-discards {
           type int32;
           description "Total sessions discarded";
         }
         leaf nat-total-session-ignores {
           type int32;
           description "Total sessions ignored";
         }
         leaf nat-total-session-time-event {
           type int32;
           description "Total Session Time events";
         }
         leaf nat-session-interest-pub-req {
           type int32;
           description "Session interest thru pub event";
         }
         leaf nat-alg-data-session-interest {
           type int32;
           description "ALG Session interest";
         }
         leaf nat-alg-data-session-created {
           type int32;
           description "ALG Session Create";
         }
         leaf total-session-close {
           type int32;
           description "Total Session Close";
         }
         leaf nat-pkt-dst-in-nat-route {
           type int32;
           description "Sessions discarded due to packet destination in NAT route";
         }
         leaf nat-pkt-drop-in-backup-state {
           type int32;
           description "Sessions discarded due to NAT in backup state";
         }
         leaf nat-session-ext-alloc-failures {
           type int32;
           description "Session extension allocation failures";
         }
         leaf nat-session-ext-set-failures {
           type int32;
           description "Session extension set failures";
         }
         leaf nat-filtering-session {
           type int32;
           description "Session Created for EIF";
         }
         leaf nat-mapping-session {
           type int32;
           description "Session Created for EIM";
         }
         leaf nat-rule-lookup-failures {
           type int32;
           description "NAT rule lookup failures";
         }
         leaf no-sext-in-xlate-pkt {
           type int32;
           description "No NAT Session Ext in Xlate Packet";
         }
         leaf pool-session-cnt-update-fail-on-create {
           type int32;
           description "Pool session count update on create";
         }
         leaf pool-session-cnt-update-fail-on-close {
           type int32;
           description "Pool session count update on close";
         }
         leaf nat-map-allocation-successes {
           type int32;
           description "NAT map allocation success count";
         }
         leaf nat-map-allocation-failures {
           type int32;
           description "NAT map allocation failure count";
         }
         leaf nat-map-free-success {
           type int32;
           description "NAT Free Successes";
         }
         leaf nat-map-free-failures {
           type int32;
           description "NAT Free Failures";
         }
         leaf nat_free_fail_on_inactive_sset {
           type uint32;
           description "NAT Free failures while service set is not active";
         }
         leaf nat-eim-mapping-reused {
           type int32;
           description "NAT EIM mapping reused";
         }
         leaf nat-eim-mapping-alloc-failures {
           type int32;
           description "NAT EIM mapping allocation failures";
         }
         leaf nat-eim-mismatched-mapping {
           type int32;
           description "NAT EIM mapping mismatched entry";
         }
         leaf nat-eim-duplicate-mapping {
           type int32;
           description "NAT EIM mapping duplicate entry";
         }
         leaf nat-eim-mapping-create-failed {
           type int32;
           description "NAT EIM mapping create failed";
         }
         leaf nat-eim-mapping-created {
           type int32;
           description "NAT EIM mapping Created";
         }
         leaf nat-eim-mapping-updated {
           type int32;
           description "NAT EIM mapping Updated";
         }
         leaf nat-eif-mapping-free {
           type int32;
           description "NAT EIF mapping Free";
         }
         leaf nat-eim-mapping-free {
           type int32;
           description "NAT EIM mapping Free";
         }
         leaf nat-eim-waiting-for-init {
           type int32;
           description "NAT EIM waiting for init";
         }
         leaf nat-eim-waiting-for-init-failed {
           type int32;
           description "NAT EIM waiting for init failed";
         }
         leaf nat-eim-lookup-hold-success {
           type int32;
           description "NAT EIM lookup and hold success";
         }
         leaf nat-eim-lookup-timeout {
           type int32;
           description "NAT EIM lookup entry in timeout";
         }
         leaf nat-eim-lookup-clear-timer {
           type int32;
           description "NAT EIM lookup timer cleared for timeout entry";
         }
         leaf nat-eim-lookup-entry-without-timer {
           type int32;
           description "NAT EIM lookup timeout entry without timer";
         }
         leaf nat-eim-release-without-entry {
           type int32;
           description "NAT EIM release without entry";
         }
         leaf nat-eim-release-in-timeout {
           type int32;
           description "NAT EIM release entry in timeout";
         }
         leaf nat-eim-release-race {
           type int32;
           description "NAT EIM release race";
         }
         leaf nat-eim-release-set-timeout {
           type int32;
           description "NAT EIM release set entry for timeout";
         }
         leaf nat-eim-timer-entry-refreshed {
           type int32;
           description "NAT EIM timer entry refreshed";
         }
         leaf nat-eim-timer-start-invalid {
           type int32;
           description "NAT EIM timer invalid timer started";
         }
         leaf nat-eim-timer-start-invalid-fail {
           type int32;
           description "NAT EIM timer invalid timer start failed";
         }
         leaf nat-eim-timer-free-mapping {
           type int32;
           description "NAT EIM timer entry freed";
         }
         leaf nat-eim-timer-update-timeout {
           type int32;
           description "NAT EIM timer entry updated";
         }
         leaf nat-eim-entry-drained {
           type int32;
           description "NAT EIM entry drained";
         }
         leaf nat_eim_mapping_eif_curr_sess_update_invalid {
           type uint32;
           description "NAT EIM - mapping eif curr sess update invalid";
         }
         leaf nat_eim_mapping_created_without_eif_sess_limit {
           type uint32;
           description "NAT EIM - mapping created without eif sess_limit set";
         }
         leaf nat-total-pkts-processed {
           type int32;
           description "Total packets processed";
         }
         leaf nat-total-bytes-processed {
           type int32;
           description "Total bytes processed";
         }
         leaf nat-total-pkts-forwarded {
           type int32;
           description "Total packets forwarded";
         }
         leaf nat-total-pkts-discarded {
           type int32;
           description "Total packets discarded";
         }
         leaf nat-total-pkts-translated {
           type int32;
           description "Total packets translated";
         }
         leaf nat-total-pkts-restored {
           type int32;
           description "Total packets restored";
         }
         leaf nat-cm-sess-lnode-created {
           type int32;
           description "Total session list nodes created";
         }
         leaf nat-cm-sess-lnode-deleted {
           type int32;
           description "Total session list nodes deleted";
         }
         leaf nat-cm-eim-lnode-created {
           type int32;
           description "Total mapping list nodes created";
         }
         leaf nat-cm-eim-lnode-deleted {
           type int32;
           description "Total mapping list nodes deleted";
         }
         leaf nat-src-ipv4-translations {
           type int32;
           description "Source ipv4 translation count";
         }
         leaf nat-src-ipv4-restorations {
           type int32;
           description "Source ipv4 restoration count";
         }
         leaf nat-dst-ipv4-translations {
           type int32;
           description "Destination ipv4 translation count";
         }
         leaf nat-dst-ipv4-restorations {
           type int32;
           description "Destination ipv4 restoration count";
         }
         leaf nat-src-ipv6-translations {
           type uint32;
           description "Source ipv6 translation count";
         }
         leaf nat-src-ipv6-restorations {
           type uint32;
           description "Source ipv6 restoration count";
         }
         leaf nat-dst-ipv6-translations {
           type uint32;
           description "Destination ipv6 translation count";
         }
         leaf nat-dst-ipv6-restorations {
           type uint32;
           description "Destination ipv6 restoration count";
         }
         leaf nat-src-port-translations {
           type int32;
           description "Source port translation count";
         }
         leaf nat-src-port-restorations {
           type int32;
           description "Source port restoration count";
         }
         leaf nat-dst-port-translations {
           type int32;
           description "Destination port translation count";
         }
         leaf nat-dst-port-restorations {
           type int32;
           description "Destination port restoration count";
         }
         leaf nat-icmp-id-translations {
           type int32;
           description "ICMP ID translation count";
         }
         leaf nat-icmp-id-restorations {
           type int32;
           description "ICMP ID restoration count";
         }
         leaf nat-icmp-error-translations {
           type int32;
           description "ICMP error packets after translation";
         }
         leaf nat-icmp-drop {
           type int32;
           description "ICMP drops";
         }
         leaf nat-icmp-allocation-failure {
           type int32;
           description "ICMP allocation failure";
         }
         leaf nat-rule-lookup-for-icmp-err-fail {
           type int32;
           description "ICMP error NAT rule lookup failed";
         }
         leaf nat-tcp-port-translations {
           type int32;
           description "Tcp port translations count";
         }
         leaf nat-tcp-port-restorations {
           type int32;
           description "Tcp port restorations count";
         }
         leaf nat-udp-port-translations {
           type int32;
           description "Udp port translation count";
         }
         leaf nat-udp-port-restorations {
           type int32;
           description "Udp port restoration count";
         }
         leaf nat-unexpected-proto-with-port-xlation {
           type int32;
           description "Unexpected Protocol With Port Translation";
         }
         leaf nat-gre-call-id-translations {
           type int32;
           description "GRE call id translation count";
         }
         leaf nat-gre-call-id-restorations {
           type int32;
           description "GRE call id restoration count";
         }
         leaf nat-unsupported-gre-proto {
           type int32;
           description "GRE unsupported protocol value";
         }
         leaf nat-icmp-error-src-restored {
           type int32;
           description "SRC IP restored in ICMP Error";
         }
         leaf nat-icmp-error-dst-restored {
           type int32;
           description "DST IP restored in ICMP Error";
         }
         leaf nat-icmp-error-src-xlated {
           type int32;
           description "SRC IP translated in ICMP Error";
         }
         leaf nat-icmp-error-dst-xlated {
           type int32;
           description "DST IP translated in ICMP Error";
         }
         leaf nat-icmp-error-new-src-xlated {
           type int32;
           description "New SRC IP translated in ICMP Error";
         }
         leaf nat-icmp-error-org-ip-src-restored {
           type int32;
           description "Inner SRC IP restored in ICMP Error";
         }
         leaf nat-icmp-error-org-ip-src-port-restored {
           type int32;
           description "Inner SRC port restored in ICMP Error";
         }
         leaf nat-icmp-error-org-ip-dst-port-restored {
           type uint32;
           description "Inner DST port restored in ICMP Error";
         }
         leaf nat-icmp-error-org-ip-dst-restored {
           type int32;
           description "Inner DST IP restored in ICMP Error";
         }
         leaf nat-icmp-error-org-ip-src-xlated {
           type int32;
           description "Inner SRC IP Translated in ICMP Error";
         }
         leaf nat-icmp-error-org-ip-src-port-xlated {
           type int32;
           description "Inner SRC port Translated in ICMP Error";
         }
         leaf nat-icmp-error-org-ip-dst-port-xlated {
           type uint32;
           description "Inner DST port Translated in ICMP Error";
         }
         leaf nat-icmp-error-org-ip-dst-xlated {
           type int32;
           description "Inner DST IP Translated in ICMP Error";
         }
         leaf nat-error-no-policy {
           type int32;
           description "NAT error - no policy";
         }
         leaf nat-error-ip-version {
           type uint32;
           description "NAT error - IP version";
         }
         leaf nat-xlate-free-null-ext {
           type int32;
           description "NAT error - xlate free called with null ext";
         }
         leaf nat-session-ext-free-failed {
           type int32;
           description "NAT error - ext free failed";
         }
         leaf nat-policy-add-failed {
           type int32;
           description "NAT error - policy add failed";
         }
         leaf nat-policy-delete-failed {
           type int32;
           description "NAT error - policy delete failed";
         }
         leaf nat-prefix-filter-alloc-failed {
           type uint32;
           description "NAT error - prefix filter allocation failed";
         }
         leaf nat-prefix-filter-name-failed {
           type uint32;
           description "NAT error - prefix filter name failed";
         }
         leaf nat-prefix-list-create-failed {
           type uint32;
           description "NAT error - prefix list create failed";
         }
         leaf nat-prefix-filter-tree-add-failed {
           type uint32;
           description "NAT error - prefix filter tree add failed";
         }
         leaf nat-prefix-filter-created {
           type uint32;
           description "NAT - prefix filter created";
         }
         leaf nat-prefix-filter-changed {
           type uint32;
           description "NAT - prefix filter changed";
         }
         leaf nat-prefix-filter-ctrl-free {
           type uint32;
           description "NAT - prefix filter control free";
         }
         leaf nat-prefix-filter-match {
           type uint32;
           description "NAT - prefix filter match";
         }
         leaf nat-prefix-filter-no-match {
           type uint32;
           description "NAT - prefix filter No match";
         }
         leaf nat-prefix-filter-mapping-add {
           type uint32;
           description "NAT - prefix filter mapping add";
         }
         leaf nat-prefix-filter-mapping-remove {
           type uint32;
           description "NAT - prefix filter mapping remove";
         }
         leaf nat-prefix-filter-mapping-free {
           type uint32;
           description "NAT - prefix filter mapping free";
         }
         leaf nat-prefix-filter-unsupp-ip-version {
           type uint32;
           description "NAT - prefix filter Unsupported IP version";
         }
         leaf nat-unsupported-layer-4-napt {
           type uint32;
           description "NAT - Unsupported layer 4 protocol";
         }
         leaf nat-unsupported-icmp-type-napt {
           type uint32;
           description "NAT - Unsupported ICMP type";
         }
         leaf nat64-ipoptions-drop {
           type uint32;
           description "NAT64 - IP options drop";
         }
         leaf nat64-udp-cksum-zero-drop {
           type uint32;
           description "NAT64 - UDP checksum zero drop";
         }
         leaf nat64-unsupp-icmp-type-drop {
           type uint32;
           description "NAT64 - Unsupported ICMP type drop";
         }
         leaf nat64-unsupp-icmp-code-drop {
           type uint32;
           description "NAT64 - Unsupported ICMP code drop";
         }
         leaf nat64-unsupp-hdr-drop {
           type uint32;
           description "NAT64 - Unsupported Header drop";
         }
         leaf nat64-unsupp-l4-drop {
           type uint32;
           description "NAT64 - Unsupported L4 drop";
         }
         leaf nat64-mtu-exceed {
           type uint32;
           description "NAT64 - MTU exceeded";
         }
         leaf nat64-ttl-exceed {
           type uint32;
           description "NAT64 - TTL exceeded";
         }
         leaf nat64-dfbit-set {
           type uint32;
           description "NAT64 - dfbit set";
         }
         leaf nat64-unsupp-icmp-error {
           type uint32;
           description "NAT64 - Unsupported ICMP error";
         }
         leaf nat64-err-map-src {
           type uint32;
           description "NAT64 error - mapping ipv4 source";
         }
         leaf nat64-err-map-dst {
           type uint32;
           description "NAT64 error - mapping ipv6 destination";
         }
         leaf nat64-err-mtu-exceed-build {
           type uint32;
           description "NAT64 error - MTU exceed build";
         }
         leaf nat64-err-ttl-exceed-build {
           type uint32;
           description "NAT64 error - TTL exceed build";
         }
         leaf nat64-err-mtu-exceed-send {
           type uint32;
           description "NAT64 error - MTU exceed send";
         }
         leaf nat64-err-ttl-exceed-send {
           type uint32;
           description "NAT64 error - TTL exceed send";
         }
         leaf nat-subs-ext-alloc {
           type uint32;
           description "NAT subscriber extension - allocated";
         }
         leaf nat-subs-ext-invalid-param {
           type uint32;
           description "NAT subscriber extension - invalid parameters";
         }
         leaf nat-subs-ext-no-mem {
           type uint32;
           description "NAT subscriber extension - no memory";
         }
         leaf nat-subs-ext-free {
           type uint32;
           description "NAT subscriber extension - freed";
         }
         leaf nat-subs-ext-is-null {
           type uint32;
           description "NAT subscriber extension - is NULL";
         }
         leaf nat-subs-ext-is-invalid {
           type uint32;
           description "NAT subscriber extension - is invalid";
         }
         leaf nat-subs-ext-link-success {
           type uint32;
           description "NAT subscriber extension - link is successful";
         }
         leaf nat-subs-ext-link-exist {
           type uint32;
           description "NAT subscriber extension - link already exists";
         }
         leaf nat-subs-ext-link-fail {
           type uint32;
           description "NAT subscriber extension - link failed";
         }
         leaf nat-subs-ext-link-unknown-ret {
           type uint32;
           description "NAT subscriber extension - unknown return value";
         }
         leaf nat-subs-ext-unlink-success {
           type uint32;
           description "NAT subscriber extension - unlink is successful";
         }
         leaf nat-subs-ext-unlink-fail {
           type uint32;
           description "NAT subscriber extension - unlink failed";
         }
         leaf nat-subs-ext-unlink-busy {
           type uint32;
           description "NAT subscriber extension - unlink on busy";
         }
         leaf nat-subs-ext-resource-in-use {
           type uint32;
           description "NAT subscriber extension - resource in use";
         }
         leaf nat-subs-ext-svc-set-not-active {
           type uint32;
           description "NAT subscriber extension - svc set is not active";
         }
         leaf nat-subs-ext-svc-set-is-null {
           type uint32;
           description "NAT subscriber extension - svc set is null";
         }
         leaf nat-subs-ext-timer-start-success {
           type uint32;
           description "NAT subscriber extension - timer start successful";
         }
         leaf nat-subs-ext-timer-start-fail {
           type uint32;
           description "NAT subscriber extension - timer start failed";
         }
         leaf nat-subs-ext-delay-timer-success {
           type uint32;
           description "NAT subscriber extension - delay timer start success";
         }
         leaf nat-subs-ext-delay-timer-fail {
           type uint32;
           description "NAT subscriber extension - delay timer start failed";
         }
         leaf nat-subs-ext-reuse-from-timer {
           type uint32;
           description "NAT subscriber extension - reuse from timer";
         }
         leaf nat-subs-ext-timer-cb {
           type uint32;
           description "NAT subscriber extension - timer callback called";
         }
         leaf nat-subs-ext-refcount-dec-fail {
           type uint32;
           description "NAT subscriber extension - plugin refcount decrement failed";
         }
         leaf nat-subs-ext-subs-reset-fail {
           type uint32;
           description "NAT subscriber extension - subscriber reset failed";
         }
         leaf nat-subs-ext-subs-session-count-update-ignore {
           type uint32;
           description "NAT subscriber extension - session count update ignored";
         }
         leaf nat-subs-ext-incorrect-state {
           type uint32;
           description "NAT subscriber extension - Incorrect state";
         }
         leaf nat-subs-ext-unlink-unk-err {
           type uint32;
           description "NAT subscriber extension - Unlink unknown error";
         }
         leaf nat-subs-ext-queue-inconsistent {
           type uint32;
           description "NAT subscriber extension - Queue inconsistent state";
         }
         leaf nat-subs-ext-return-to-prealloc-err {
           type uint32;
           description "NAT subscriber extension - Return to prealloc queue err";
         }
         leaf nat-subs-ext-dec-inval-sess-cnt {
           type uint32;
           description "NAT subscriber extension - Decrement invalid session count";
         }
         leaf nat-subs-ext-dec-inval-eim-cnt {
           type uint32;
           description "NAT subscriber extension - Decrement invalid EIM count";
         }
         leaf nat-subs-ext-ports-in-use-err {
           type uint32;
           description "NAT subscriber extension - Ports in use error";
         }
         leaf nat-subs-ext-err-set-state {
           type uint32;
           description "NAT subscriber extension - Set state error";
         }
         leaf nat-subs-ext-missing-ext {
           type uint32;
           description "NAT subscriber extension - Nat subscriber extension is missing";
         }
         leaf nat-subs-ext-invalid-eimrefcnt {
           type uint32;
           description "NAT subscriber extension - unexpected eim refcnt";
         }
         leaf nat-subs-ext-is-invalid-subs-in-tw {
           type uint32;
           description "NAT subscriber extension - invalid subs in timer wheel";
         }
         leaf nat-subs-ext-in-tw-during-free {
           type uint32;
           description "NAT subscriber extension - subs in timer wheel during free";
         }
         leaf nat_jflow_log_nat_sext_null {
           type uint32;
           description "NAT jflow-log error - session extension get fail";
         }
         leaf nat_jflow_log_alloc_fail {
           type uint32;
           description "NAT jflow-log error - memory allocation fail";
         }
         leaf nat_jflow_log_alloc_success {
           type uint32;
           description "NAT jflow-log - memory allocation success";
         }
         leaf nat_jflow_log_free_success {
           type uint32;
           description "NAT jflow-log - memory free success";
         }
         leaf nat_jflow_log_free_fail_record {
           type uint32;
           description "NAT jflow-log error - memory free fail null record";
         }
         leaf nat_jflow_log_free_fail_data {
           type uint32;
           description "NAT jflow-log error - memory free fail null data";
         }
         leaf nat_jflow_log_invalid_trans_type {
           type uint32;
           description "NAT jflow-log error - invalid nat translation type";
         }
         leaf nat_jflow_log_free_success_fail_queuing {
           type uint32;
           description "NAT jflow-log - memory free success";
         }
         leaf nat_jflow_log_invalid_input_args {
           type uint32;
           description "NAT jflow-log - invalid input arguments";
         }
         leaf nat_jflow_log_invalid_alloc_err {
           type uint32;
           description "NAT jflow-log - invalid allocation error type";
         }
         leaf nat_jflow_log_rate_limit_fail_get_pool_name {
           type uint32;
           description "NAT jflow-log - rate limit fail get pool name";
         }
         leaf nat_jflow_log_rate_limit_fail_get_natpool {
           type uint32;
           description "NAT jflow-log - rate limit fail get natpool";
         }
         leaf nat_jflow_log_rate_limit_fail_get_natpool_given_id {
           type uint32;
           description "NAT jflow-log - rate limit fail get natpool for given id";
         }
         leaf nat_jflow_log_rate_limit_fail_get_service_set {
           type uint32;
           description "NAT jflow-log - rate limit fail get service set";
         }
         leaf nat_jflow_log_rate_limit_fail_invalid_current_time {
           type uint32;
           description "NAT jflow-log - rate limit fail invalid current time";
         }
         leaf nat_ha_recv_no_nat_policy_found {
           type uint32;
           description "NAT HA RECV STATES - No nat policy found";
         }
         leaf nat_ha_recv_no_matching_policy_nat_rule_found {
           type uint32;
           description "NAT HA RECV STATES - No nat rule found for the policy";
         }
         leaf nat_ha_recv_mapping_found_without_eif_sess_limit {
           type uint32;
           description "NAT HA RECV STATES - mapping found without eif sess limit";
         }
         leaf nat_ha_recv_mapping_create_without_eif_sess_limit {
           type uint32;
           description "NAT HA RECV STATES - mapping creation without eif sess limit";
         }
         leaf nat-eim-drain-in-lookup {
           type int32;
           description "NAT EIM entry found in drain state in lookup";
         }
       }
     }
   }
   rpc get-service-cos-statistics-information {
     description "Show statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
       leaf service-set {
         description "Name of service set";
         type string;
       }
       leaf interface {
         description "Name of adaptive services interface";
         type string;
       }
     }
     output {
       container service-cos-statistics-information {
         container brief {
           description "Class of service statistics information";
           container service-cos-statistics-entry {
             description "Class of service statistics entry";
             leaf interface-name {
               type string;
               description "Name of the adaptive services interface";
             }
             leaf service-set-name {
               type string;
               description "Name of the service set";
             }
             container cos-stats-service-set-dscp-information {
               container cos-stats-service-set-dscp-entry {
                 description "Class-of-service service set statistics entry";
               }
             }
             container cos-stats-service-set-forwarding-class-information {
               container cos-stats-service-set-forwarding-class-entry {
                 description "Class-of-service service set statistics entry";
               }
             }
           }
         }
         container summary {
           description "Class of service statistics information";
           container service-cos-statistics-entry {
             description "Class of service statistics entry";
             leaf interface-name {
               type string;
               description "Name of the adaptive services interface";
             }
             container cos-stats-service-set-dscp-information {
               container cos-stats-service-set-dscp-entry {
                 description "Class-of-service service set statistics entry";
               }
             }
             container cos-stats-service-set-forwarding-class-information {
               container cos-stats-service-set-forwarding-class-entry {
                 description "Class-of-service service set statistics entry";
               }
             }
           }
         }
       }
     }
   }
   rpc get-service-cos-diffserv-statistics {
     description "Show Diffserv marking statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
     }
   }
   rpc get-service-cos-forwarding-class-statistics {
     description "Show forwarding Class statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
     }
   }
   rpc get-service-mss-sessions-information {
     description "Show mobile subscriber data sessions";
     input {
       leaf imsi {
         description "IMSI of subscriber";
         type string {
           length "5 .. 15";
         }
       }
     }
   }
   rpc get-service-hcm-sessions-stats {
     description "Show hcm session statistics";
     input {
       leaf imsi {
         description "IMSI of subscriber";
         type string {
           length "5 .. 15";
         }
         mandatory true;
       }
     }
   }
   rpc get-service-tdf-sessions-information {
     description "Show traffic-detection-function subscriber data sessions";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
   }
   rpc get-service-tdf-hcm-sessions-stats {
     description "Show hcm session statistics";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
   }
   rpc get-service-pgcp-flow-table-information {
     description "Show PGCP flow table entries";
     output {
       container service-pgcp-flow-table-information {
         container pgcp-per-service-set-flow-table {
           description "Flows sorted by service set";
           leaf interface-name {
             type string;
             description "Name of the adaptive services interface";
           }
           leaf service-set-name {
             type string;
             description "Name of the service set";
           }
           container service-pgcp-flow-table {
             description "Stateful firewall flows";
             leaf service-pgcp-flow-table.heading {
               type string;
               description "Stateful firewall flows";
             }
             container pgcp-flow-entry {
               description "Flow brief information";
               leaf pgcp-flow-protocol {
                 type string;
                 description "PGCP Flow protocol description";
               }
               leaf pgcp-flow-source-ip {
                 type string;
                 description "PGCP Source IP address";
               }
               leaf pgcp-flow-source-port {
                 type int32;
                 description "PGCP Source port address";
               }
               leaf pgcp-flow-destination-ip {
                 type string;
                 description "Flow destination IP address";
               }
               leaf pgcp-flow-destination-port {
                 type string;
                 description "PGCP Flow destination port";
               }
               leaf pgcp-flow-state {
                 type string;
                 description "Flow state";
               }
               leaf pgcp-flow-direction {
                 type string;
                 description "PGCP Flow direction";
               }
               leaf pgcp-flow-frame-counter {
                 type uint64;
                 description "Number of frames transmitted";
               }
               leaf pgcp-flow-gate-id {
                 type uint64;
                 description "PGCP gate-id";
               }
               leaf pgcp-flow-table-byte-count {
                 type uint64;
                 description "PGCP Flow byte count";
               }
               leaf pgcp-flow-table-role {
                 type string;
                 description "Role of flow in conversation";
               }
               leaf pgcp-flow-table-timeout {
                 type uint64;
                 description "Timeout value of PGCP flow (seconds)";
               }
               leaf pgcp-flow-table-protocol-detail {
                 type string;
                 description "PGCP Flow protocol detail information";
               }
               leaf flow-gate-tman-policing {
                 type string;
                 description "Install/uninstall a traffic management policing for this gate";
               }
               leaf flow-gate-sdr {
                 type uint32;
                 description "Sustainable data rate threshold for a gate";
               }
               leaf flow-gate-sdr-mbs {
                 type uint32;
                 description "Maximum sdr burst size limit for a gate";
               }
               leaf flow-gate-pdr {
                 type uint32;
                 description "Peak data rate threshold for a gate";
               }
               leaf flow-gate-pdr-mbs {
                 type uint32;
                 description "Maximum pdr burst size limit for a gate";
               }
               leaf source-routing-instance {
                 type string;
                 description "Source routing-instance";
               }
               leaf destination-routing-instance {
                 type string;
                 description "Destination routing-instance";
               }
               leaf flow-replication-status {
                 type string;
                 description "Flow replication status with backup Data-Pic, values: In-Progress/Disabled/Completed";
               }
               leaf pgcp-flow-table-tcp-window-size {
                 type uint64;
                 description "PGCP TCP protocol window size";
               }
               leaf pgcp-flow-table-tcp-acknowledge {
                 type uint64;
                 description "PGCP TCP protocol acknowledge";
               }
               leaf pgcp-flow-table-tcp-tickle {
                 type uint64;
                 description "PGCP Time between TCP tickles (seconds)";
               }
               container pgcp-flow-nat {
                 description "NAT translation";
                 leaf pgcp-flow-nat.nat-type {
                   type string;
                   description "NAT translation";
                 }
                 leaf pgcp-flow-nat-ip {
                   type string;
                   description "PGCP NAT IP address";
                 }
                 leaf pgcp-flow-nat-port {
                   type string;
                   description "PGCP NAT port";
                 }
                 leaf pgcp-flow-translated-ip {
                   type string;
                   description "Translated PGCP IP address";
                 }
                 leaf pgcp-flow-translated-port {
                   type string;
                   description "Translated PGCP port";
                 }
               }
             }
           }
         }
       }
     }
   }
   rpc get-service-pgcp-flow-table-information-gateway {
     description "Show packet-gateway-control-protocol information for gateway";
     input {
       leaf gateway-name {
         description "Gateway name";
         type string;
         mandatory true;
       }
       leaf gate-id {
         description "Gate id";
         type uint64;
       }
       leaf service-set {
         description "Name of service set";
         type string;
       }
       leaf source-prefix {
         description "Source prefix to use as filter";
         type string;
       }
       leaf destination-prefix {
         description "Destination prefix to use as filter";
         type string;
       }
       leaf source-port {
         description "Source port to use as filter";
         type uint16;
       }
       leaf destination-port {
         description "Destination port to use as filter";
         type uint16;
       }
       leaf source-routing-instance {
         description "Source routing-instance";
         type string;
       }
       leaf destination-routing-instance {
         description "Destination routing-instance";
         type string;
       }
       leaf protocol {
         description "IP protocol type to use as filter";
         type string;
       }
       leaf get-service-pgcp-flow-count-information {
         description "Show count of matching entries";
         type empty;
       }
       leaf level {
         default "brief";
         type enumeration {
           enum "brief" {
             description "Display brief output";
           }
           enum "extensive" {
             description "Display extensive output";
           }
         }
       }
       leaf backup-data-pic {
         description "Show flows table by querying the backup Data-PIC";
         type empty;
       }
       leaf redundancy-option {
         default "master";
         type enumeration {
           enum "master" {
             description "Query the master RE or ms-pic (default)";
           }
           enum "backup" {
             description "Query the backup ms-pic";
           }
         }
       }
     }
   }
   rpc get-service-pgcp-conversation-information {
     description "Show PGCP conversations";
     output {
       container service-pgcp-conversation-information {
         container pgcp-per-service-set-conversation {
           description "Show conversations";
           leaf interface-name {
             type string;
             description "Name of the adaptive services interface";
           }
           leaf service-set-name {
             type string;
             description "Name of the service set";
           }
           container pgcp-conversation {
             description "Stateful firewall conversations";
             leaf pgcp-flow-table-conv-initiator {
               type int32;
               description "Number of initiator flows";
             }
             leaf pgcp-flow-table-conv-responder {
               type int32;
               description "Number of responder flows";
             }
             container service-pgcp-flow-table {
               description "Stateful firewall flows";
               leaf service-pgcp-flow-table.heading {
                 type string;
                 description "Stateful firewall flows";
               }
               container pgcp-flow-entry {
                 description "Flow brief information";
                 leaf pgcp-flow-protocol {
                   type string;
                   description "PGCP Flow protocol description";
                 }
                 leaf pgcp-flow-source-ip {
                   type string;
                   description "PGCP Source IP address";
                 }
                 leaf pgcp-flow-source-port {
                   type int32;
                   description "PGCP Source port address";
                 }
                 leaf pgcp-flow-destination-ip {
                   type string;
                   description "Flow destination IP address";
                 }
                 leaf pgcp-flow-destination-port {
                   type string;
                   description "PGCP Flow destination port";
                 }
                 leaf pgcp-flow-state {
                   type string;
                   description "Flow state";
                 }
                 leaf pgcp-flow-direction {
                   type string;
                   description "PGCP Flow direction";
                 }
                 leaf pgcp-flow-frame-counter {
                   type uint64;
                   description "Number of frames transmitted";
                 }
                 leaf pgcp-flow-gate-id {
                   type uint64;
                   description "PGCP gate-id";
                 }
                 leaf pgcp-flow-table-byte-count {
                   type uint64;
                   description "PGCP Flow byte count";
                 }
                 leaf pgcp-flow-table-role {
                   type string;
                   description "Role of flow in conversation";
                 }
                 leaf pgcp-flow-table-timeout {
                   type uint64;
                   description "Timeout value of PGCP flow (seconds)";
                 }
                 leaf pgcp-flow-table-protocol-detail {
                   type string;
                   description "PGCP Flow protocol detail information";
                 }
                 leaf flow-gate-tman-policing {
                   type string;
                   description "Install/uninstall a traffic management policing for this gate";
                 }
                 leaf flow-gate-sdr {
                   type uint32;
                   description "Sustainable data rate threshold for a gate";
                 }
                 leaf flow-gate-sdr-mbs {
                   type uint32;
                   description "Maximum sdr burst size limit for a gate";
                 }
                 leaf flow-gate-pdr {
                   type uint32;
                   description "Peak data rate threshold for a gate";
                 }
                 leaf flow-gate-pdr-mbs {
                   type uint32;
                   description "Maximum pdr burst size limit for a gate";
                 }
                 leaf source-routing-instance {
                   type string;
                   description "Source routing-instance";
                 }
                 leaf destination-routing-instance {
                   type string;
                   description "Destination routing-instance";
                 }
                 leaf flow-replication-status {
                   type string;
                   description "Flow replication status with backup Data-Pic, values: In-Progress/Disabled/Completed";
                 }
                 leaf pgcp-flow-table-tcp-window-size {
                   type uint64;
                   description "PGCP TCP protocol window size";
                 }
                 leaf pgcp-flow-table-tcp-acknowledge {
                   type uint64;
                   description "PGCP TCP protocol acknowledge";
                 }
                 leaf pgcp-flow-table-tcp-tickle {
                   type uint64;
                   description "PGCP Time between TCP tickles (seconds)";
                 }
                 container pgcp-flow-nat {
                   description "NAT translation";
                   leaf pgcp-flow-nat.nat-type {
                     type string;
                     description "NAT translation";
                   }
                   leaf pgcp-flow-nat-ip {
                     type string;
                     description "PGCP NAT IP address";
                   }
                   leaf pgcp-flow-nat-port {
                     type string;
                     description "PGCP NAT port";
                   }
                   leaf pgcp-flow-translated-ip {
                     type string;
                     description "Translated PGCP IP address";
                   }
                   leaf pgcp-flow-translated-port {
                     type string;
                     description "Translated PGCP port";
                   }
                 }
               }
             }
           }
         }
       }
     }
   }
   rpc get-service-pgcp-conversation-information-gateway {
     description "Show PGCP conversations for gateway";
     input {
       leaf gateway-name {
         description "Gateway name";
         type string;
         mandatory true;
       }
       leaf service-set {
         description "Name of service set";
         type string;
       }
       leaf source-prefix {
         description "Source prefix to use as filter";
         type string;
       }
       leaf destination-prefix {
         description "Destination prefix to use as filter";
         type string;
       }
       leaf source-port {
         description "Source port to use as filter";
         type uint16;
       }
       leaf destination-port {
         description "Destination port to use as filter";
         type uint16;
       }
       leaf source-routing-instance {
         description "Source routing-instance";
         type string;
       }
       leaf destination-routing-instance {
         description "Destination routing-instance";
         type string;
       }
       leaf protocol {
         description "IP protocol type to use as filter";
         type string;
       }
       leaf level {
         default "brief";
         type enumeration {
           enum "brief" {
             description "Display brief output";
           }
           enum "extensive" {
             description "Display extensive output";
           }
         }
       }
       leaf backup-data-pic {
         description "Show conversations information by querying the backup Data-PIC";
         type empty;
       }
       leaf redundancy-option {
         default "master";
         type enumeration {
           enum "master" {
             description "Query the master RE or ms-pic (default)";
           }
           enum "backup" {
             description "Query the backup ms-pic";
           }
         }
       }
     }
   }
   rpc get-pgcpd-active-configuration {
     description "Show pgcpd active-configuration";
     output {
       container pgcpd-active-configuration {
         container virtual-interface-entry {
           leaf virtual-interface-name {
             type string;
           }
           leaf routing-instance {
             type string;
           }
           leaf interface-name {
             type string;
             description "Name of the adaptive services interface";
           }
           leaf vif-service-state {
             type string;
           }
         }
         container controller-entry {
           leaf controller-name {
             type string;
           }
           leaf remote-ip-address {
             type string;
           }
           leaf remote-port {
             type uint32;
           }
         }
         container h248-timers-entry {
           leaf maximum-waiting-delay {
             type uint32;
           }
           leaf tmax-retransmission-delay {
             type uint32;
           }
           leaf initial-average-ack-delay {
             type uint32;
           }
           leaf maximum-net-propagation-delay {
             type uint32;
           }
         }
         container h248-options-entry {
           leaf wildcard-response-service-change {
             type string;
           }
           leaf audit-observed-events-returns-history {
             type string;
             description "Activation of event history";
           }
           leaf h248-profile {
             type string;
           }
         }
         container base-root-entry {
           description "Array of h248 base root properties";
           leaf brp_name {
             type string;
             description "Property's name";
           }
           leaf brp_minimum {
             type uint32;
             description "Property's minimum range value";
           }
           leaf brp_maximum {
             type uint32;
             description "Property's maximum range value";
           }
           leaf brp_default {
             type uint32;
             description "Property's default value";
           }
         }
         container h248-segmentation-properties-entry {
           description "Array of h248 segmentation properties";
           leaf sgp_name {
             type string;
             description "Property's name";
           }
           leaf sgp_minimum {
             type uint32;
             description "Property's minimum range value";
           }
           leaf sgp_maximum {
             type uint32;
             description "Property's maximum range value";
           }
           leaf sgp_default {
             type uint32;
             description "Property's default value";
           }
         }
         container h248-diffserv-entry {
           leaf dscp {
             type string;
           }
         }
         container h248-notification-behavior-entry {
           leaf notification-regulation {
             type string;
             description "Notify regulation";
           }
         }
         container h248-application-data-inactivity-detection-entry {
           leaf ip-flow-stop-detection {
             type string;
             description "Notify behavior to media inactivity event";
           }
         }
         container h248-event-timestamp-notification-entry {
           leaf requested-timestamp {
             type string;
             description "Notification timestamp";
           }
         }
         container inactivity-timer-entry {
           leaf detect {
             type string;
             description "Detect inactivity timeout";
           }
           container maximum-inactivity-time {
             leaf minimum {
               type uint32;
               description "Minimum valid value of maximum inactivity timeout";
             }
             leaf maximum {
               type uint32;
               description "Maximum valid value of maximum inactivity timeout";
             }
             leaf default {
               type uint32;
               description "Default valid value of maximum inactivity timeout";
             }
           }
         }
         container fast-update-filters-entry {
           description "Firewall filters limitation";
           leaf max-terms {
             type uint64;
             description "Maximum number of filter terms";
           }
           leaf max-term-percentage {
             type uint32;
             description "Maximum percentage of gates with filter terms";
           }
         }
         container overload-control-entry {
           leaf queue-limit-percentage {
             type uint32;
           }
           leaf reject-new-calls-threshold {
             type uint32;
           }
           leaf reject-all-commands-threshold {
             type uint32;
           }
         }
         container gateway-entry {
           leaf gateway-name {
             type string;
           }
           leaf local-ip-address {
             type string;
           }
           leaf gateway-vrf {
             type string;
           }
           leaf local-port {
             type uint32;
           }
           leaf platform {
             type string;
           }
           leaf service-state {
             type string;
           }
           leaf active-controller {
             type string;
           }
           leaf replication-socket {
             type string;
           }
           leaf synchronization-state {
             type string;
           }
           leaf up-time {
             type string;
             description "Gateway uptime";
           }
           leaf load-status {
             type string;
             description "Gateway load status";
           }
           leaf cleanup-timeout {
             type uint32;
           }
           leaf maximum-concurrent-calls {
             type uint32;
             description "Maximum concurrent calls";
           }
           leaf inactivity-timeout-delay {
             type uint32;
           }
           leaf inactivity-timeout-duration {
             type uint32;
           }
           leaf latch-deadlock-duration {
             type uint32;
           }
           container h248-timers-entry {
             leaf maximum-waiting-delay {
               type uint32;
             }
             leaf tmax-retransmission-delay {
               type uint32;
             }
             leaf initial-average-ack-delay {
               type uint32;
             }
             leaf maximum-net-propagation-delay {
               type uint32;
             }
           }
           container base-root-entry {
             description "Array of h248 base root properties";
             leaf brp_name {
               type string;
               description "Property's name";
             }
             leaf brp_minimum {
               type uint32;
               description "Property's minimum range value";
             }
             leaf brp_maximum {
               type uint32;
               description "Property's maximum range value";
             }
             leaf brp_default {
               type uint32;
               description "Property's default value";
             }
           }
           container h248-options-entry {
             leaf wildcard-response-service-change {
               type string;
             }
             leaf audit-observed-events-returns-history {
               type string;
               description "Activation of event history";
             }
             leaf h248-profile {
               type string;
             }
           }
           container h248-segmentation-properties-entry {
             description "Array of h248 segmentation properties";
             leaf sgp_name {
               type string;
               description "Property's name";
             }
             leaf sgp_minimum {
               type uint32;
               description "Property's minimum range value";
             }
             leaf sgp_maximum {
               type uint32;
               description "Property's maximum range value";
             }
             leaf sgp_default {
               type uint32;
               description "Property's default value";
             }
           }
           container h248-diffserv-entry {
             leaf dscp {
               type string;
             }
           }
           container h248-notification-behavior-entry {
             leaf notification-regulation {
               type string;
               description "Notify regulation";
             }
           }
           container h248-application-data-inactivity-detection-entry {
             leaf ip-flow-stop-detection {
               type string;
               description "Notify behavior to media inactivity event";
             }
           }
           container h248-event-timestamp-notification-entry {
             leaf requested-timestamp {
               type string;
               description "Notification timestamp";
             }
           }
           container inactivity-timer-entry {
             leaf detect {
               type string;
               description "Detect inactivity timeout";
             }
             container maximum-inactivity-time {
               leaf minimum {
                 type uint32;
                 description "Minimum valid value of maximum inactivity timeout";
               }
               leaf maximum {
                 type uint32;
                 description "Maximum valid value of maximum inactivity timeout";
               }
               leaf default {
                 type uint32;
                 description "Default valid value of maximum inactivity timeout";
               }
             }
           }
           container fast-update-filters-entry {
             description "Firewall filters limitation";
             leaf max-terms {
               type uint64;
               description "Maximum number of filter terms";
             }
             leaf max-term-percentage {
               type uint32;
               description "Maximum percentage of gates with filter terms";
             }
           }
           container controller-entry {
             leaf controller-name {
               type string;
             }
             leaf remote-ip-address {
               type string;
             }
             leaf remote-port {
               type uint32;
             }
           }
           container overload-control-entry {
             leaf queue-limit-percentage {
               type uint32;
             }
             leaf reject-new-calls-threshold {
               type uint32;
             }
             leaf reject-all-commands-threshold {
               type uint32;
             }
           }
         }
         container rule-ref-entry {
           leaf rule-ref-name {
             type string;
           }
         }
         container rule-entry {
           leaf rule-name {
             type string;
             description "Rule name";
           }
           leaf rule-gateway-name {
             type string;
           }
         }
         container service-pic-entry {
           leaf pic-name {
             type string;
             description "Services PIC Name";
           }
           leaf pic-status {
             type string;
           }
           leaf pic-redundancy-state {
             type string;
           }
           leaf primary-pic {
             type string;
           }
           leaf secondary-pic {
             type string;
           }
           leaf pic-ha-state {
             type string;
           }
           leaf last-change {
             type string;
           }
         }
         container service-set-entry {
           leaf service-set-name {
             type string;
             description "Name of the service set";
           }
           leaf id {
             type uint32;
           }
         }
         container firewall-entry {
           leaf connection-status {
             type string;
           }
           leaf number-of-terms {
             type uint64;
           }
           leaf number-of-filters {
             type uint64;
           }
         }
         container pgcpd-config {
           container media-service-entry {
             leaf media-service-name {
               type string;
             }
             leaf media-service-nat-pool {
               type string;
             }
           }
           container virtual-interface-entry {
             leaf virtual-interface-name {
               type string;
             }
             leaf routing-instance {
               type string;
             }
             leaf interface-name {
               type string;
               description "Name of the adaptive services interface";
             }
             leaf vif-service-state {
               type string;
             }
             container media-service-ref-entry {
             }
           }
           container gateway-entry {
             leaf gateway-name {
               type string;
             }
             leaf local-ip-address {
               type string;
             }
             leaf gateway-vrf {
               type string;
             }
             leaf local-port {
               type uint32;
             }
             leaf platform {
               type string;
             }
             leaf service-state {
               type string;
             }
             leaf active-controller {
               type string;
             }
             leaf replication-socket {
               type string;
             }
             leaf synchronization-state {
               type string;
             }
             leaf up-time {
               type string;
               description "Gateway uptime";
             }
             leaf load-status {
               type string;
               description "Gateway load status";
             }
             leaf cleanup-timeout {
               type uint32;
             }
             leaf maximum-concurrent-calls {
               type uint32;
               description "Maximum concurrent calls";
             }
             leaf inactivity-timeout-delay {
               type uint32;
             }
             leaf inactivity-timeout-duration {
               type uint32;
             }
             leaf latch-deadlock-duration {
               type uint32;
             }
             container h248-timers-entry {
             }
             container base-root-entry {
               description "Array of h248 base root properties";
             }
             container h248-options-entry {
             }
             container h248-segmentation-properties-entry {
               description "Array of h248 segmentation properties";
             }
             container h248-diffserv-entry {
             }
             container h248-notification-behavior-entry {
             }
             container h248-application-data-inactivity-detection-entry {
             }
             container h248-event-timestamp-notification-entry {
             }
             container inactivity-timer-entry {
               container maximum-inactivity-time {
                 leaf minimum {
                   type uint32;
                   description "Minimum valid value of maximum inactivity timeout";
                 }
                 leaf maximum {
                   type uint32;
                   description "Maximum valid value of maximum inactivity timeout";
                 }
                 leaf default {
                   type uint32;
                   description "Default valid value of maximum inactivity timeout";
                 }
               }
             }
             container fast-update-filters-entry {
               description "Firewall filters limitation";
             }
             container controller-entry {
             }
             container overload-control-entry {
             }
           }
           container rule-entry {
             leaf rule-name {
               type string;
               description "Rule name";
             }
             leaf rule-gateway-name {
               type string;
             }
           }
           container service-set-entry {
             leaf service-set-name {
               type string;
               description "Name of the service set";
             }
             leaf id {
               type uint32;
             }
             container rule-ref-entry {
             }
           }
           container service-pic-entry {
             leaf pic-name {
               type string;
               description "Services PIC Name";
             }
             leaf pic-status {
               type string;
             }
             leaf pic-redundancy-state {
               type string;
             }
             leaf primary-pic {
               type string;
             }
             leaf secondary-pic {
               type string;
             }
             leaf pic-ha-state {
               type string;
             }
             leaf last-change {
               type string;
             }
           }
           container firewall-entry {
             leaf connection-status {
               type string;
             }
             leaf number-of-terms {
               type uint64;
             }
             leaf number-of-filters {
               type uint64;
             }
           }
         }
       }
     }
   }
   rpc get-service-pgcp-active-configuration-gateway {
     description "Show gateway active configuration";
     input {
       leaf gateway-name {
         description "Gateway name";
         type string;
         mandatory true;
       }
       leaf redundancy-option {
         default "master";
         type enumeration {
           enum "master" {
             description "Query the master RE or ms-pic (default)";
           }
           enum "backup" {
             description "Query the backup ms-pic";
           }
         }
       }
     }
   }
   rpc get-service-pgcp-statistics {
     description "Show pgcpd statistics";
   }
   rpc get-service-pgcp-statistics-gateway {
     description "Show gateway statistics";
     input {
       leaf gateway-name {
         description "Gateway name";
         type string;
         mandatory true;
       }
       leaf display {
         default "brief";
         type enumeration {
           enum "brief" {
             description "Display brief output (default)";
           }
           enum "extensive" {
             description "Display extensive output";
           }
         }
       }
       leaf redundancy-option {
         default "master";
         type enumeration {
           enum "master" {
             description "Query the master RE or ms-pic (default)";
           }
           enum "backup" {
             description "Query the backup ms-pic";
           }
         }
       }
     }
     output {
       container service-pgcp-statistics-gateway {
         leaf pgcp-statistics-since {
           type string;
           description "Since when statistics were collected";
         }
         container gateway-entry {
           leaf gateway-name {
             type string;
           }
           leaf local-ip-address {
             type string;
           }
           leaf gateway-vrf {
             type string;
           }
           leaf local-port {
             type uint32;
           }
           leaf platform {
             type string;
           }
           leaf service-state {
             type string;
           }
           leaf active-controller {
             type string;
           }
           leaf replication-socket {
             type string;
           }
           leaf synchronization-state {
             type string;
           }
           leaf up-time {
             type string;
             description "Gateway uptime";
           }
           leaf load-status {
             type string;
             description "Gateway load status";
           }
           leaf cleanup-timeout {
             type uint32;
           }
           leaf maximum-concurrent-calls {
             type uint32;
             description "Maximum concurrent calls";
           }
           leaf inactivity-timeout-delay {
             type uint32;
           }
           leaf inactivity-timeout-duration {
             type uint32;
           }
           leaf latch-deadlock-duration {
             type uint32;
           }
           container inactivity-timer-entry {
             container maximum-inactivity-time {
               leaf minimum {
                 type uint32;
                 description "Minimum valid value of maximum inactivity timeout";
               }
               leaf maximum {
                 type uint32;
                 description "Maximum valid value of maximum inactivity timeout";
               }
               leaf default {
                 type uint32;
                 description "Default valid value of maximum inactivity timeout";
               }
             }
           }
         }
         container service-pic-entry {
           leaf pic-name {
             type string;
             description "Services PIC Name";
           }
           leaf pic-status {
             type string;
           }
           leaf pic-redundancy-state {
             type string;
           }
           leaf primary-pic {
             type string;
           }
           leaf secondary-pic {
             type string;
           }
           leaf pic-ha-state {
             type string;
           }
           leaf last-change {
             type string;
           }
         }
         container services-pgcp-traffic-entry {
           leaf traffic-bytes-recv {
             type uint64;
             description "Number of bytes received";
           }
           leaf traffic-bytes-sent {
             type uint64;
             description "Number of bytes sent";
           }
           leaf traffic-packets-recv {
             type uint64;
             description "Number of packets received";
           }
           leaf traffic-packets-sent {
             type uint64;
             description "Number of packets sent";
           }
         }
         container services-pgcp-dropped-traffic-entry {
           leaf drop-packets-flow-drop-state {
             type uint64;
             description "Number of packets dropped as result of flow in state drop";
           }
           leaf drop-bytes-flow-drop-state {
             type uint64;
             description "Number of bytes dropped as result of flow in state drop";
           }
           leaf drop-packets-flow-rate-limit {
             type uint64;
             description "Number of packets dropped as result of rate limit";
           }
           leaf drop-bytes-flow-rate-limit {
             type uint64;
             description "Number of bytes dropped as result of rate limit";
           }
           leaf drop-packets-algs {
             type uint64;
             description "Number of packets dropped as result of ALG varification";
           }
           leaf drop-bytes-algs {
             type uint64;
             description "Number of bytes dropped as result of ALG varification";
           }
           leaf drop-packets-other {
             type uint64;
             description "Number of packets dropped as result of other reason";
           }
           leaf drop-bytes-other {
             type uint64;
             description "Number of bytes dropped as result of other reason";
           }
         }
         container usage-counters-entry {
           leaf contexts-number {
             type uint32;
             description "Number of contexts";
           }
           leaf emergency-contexts-number {
             type uint32;
             description "Number of emergency contexts";
           }
         }
         container service-pgcp-statistics-h248 {
           leaf messages-received {
             type uint32;
             description "Number of H.248 messages received";
           }
           leaf octets-received {
             type uint32;
             description "Number of H.248 octets received";
           }
           leaf messages-sent {
             type uint32;
             description "Number of H.248 messages sent";
           }
           leaf octets-sent {
             type uint32;
             description "Number of H.248 octest sent";
           }
           leaf protocol-errors {
             type uint32;
             description "Number of H.248 protocol erros";
           }
           leaf transport-losses {
             type uint32;
             description "Number of H.248 transport losses";
           }
           leaf last-detected-event {
             type string;
             description "Last detected H.248 event";
           }
           leaf last-detected-event-time {
             type uint32;
             description "Last detected H.248 event time";
           }
           leaf last-reset-time {
             type uint32;
             description "Last H.248 reset time";
           }
         }
         container service-pgcp-stat-h248-per-command-header {
           leaf per-command-header-name {
             type string;
             description "Statistics header";
           }
         }
         container service-pgcp-stat-h248-per-command {
           leaf command-name {
             type string;
             description "H.248 command requests";
           }
           leaf commands-total {
             type uint32;
             description "Total number of h.248 command requests";
           }
           leaf commands-wildcard {
             type uint32;
             description "The number of command request that had wildcard termination ID or termination list";
           }
           leaf commands-success {
             type uint32;
             description "Number of H.248 successful replies";
           }
           leaf commands-error {
             type uint32;
             description "Number of H.248 failed replies";
           }
         }
       }
     }
   }
   rpc get-service-pgcp-terminations {
     description "Show list of terminations";
     output {
       container service-pgcp-terminations {
         container brief {
           container gateway-entry {
             container inactivity-timer-entry {
               container maximum-inactivity-time {
                 leaf minimum {
                   type uint32;
                   description "Minimum valid value of maximum inactivity timeout";
                 }
                 leaf maximum {
                   type uint32;
                   description "Maximum valid value of maximum inactivity timeout";
                 }
                 leaf default {
                   type uint32;
                   description "Default valid value of maximum inactivity timeout";
                 }
               }
             }
           }
           container service-pgcp-termination-entry-information {
             leaf termination-id-string {
               type string;
               description "Termination id as string";
             }
             leaf termination-state {
               type string;
               description "Termination state (in/out of service)";
             }
             leaf termination-duration {
               type uint32;
               description "Termination duration (in milliseconds)";
             }
           }
           container service-pgcp-termination-gates-information {
             leaf gate-id {
               type uint64;
               description "Gate id";
             }
             leaf gate-direction {
               type string;
               description "Gate direction (A->B/B->A)";
             }
             leaf gate-state {
               type string;
               description "Gate state (active/disabled)";
             }
             leaf gate-action {
               type string;
               description "Gate action (forward/drop)";
             }
           }
           container service-pgcp-terminations-count {
             description "Count of termination entries per gateway";
             leaf gateway-name {
               type string;
             }
             leaf termination-count {
               type uint32;
               description "Number of terminations in the gateway";
             }
           }
         }
         container h248 {
           container gateway-entry {
             container inactivity-timer-entry {
               container maximum-inactivity-time {
                 leaf minimum {
                   type uint32;
                   description "Minimum valid value of maximum inactivity timeout";
                 }
                 leaf maximum {
                   type uint32;
                   description "Maximum valid value of maximum inactivity timeout";
                 }
                 leaf default {
                   type uint32;
                   description "Default valid value of maximum inactivity timeout";
                 }
               }
             }
           }
           container service-pgcp-termination-entry-information {
             leaf termination-h248-dump {
               type string;
               description "Termination information";
             }
           }
           container service-pgcp-terminations-count {
             description "Count of termination entries per gateway";
             leaf gateway-name {
               type string;
             }
             leaf termination-count {
               type uint32;
               description "Number of terminations in the gateway";
             }
           }
         }
         container count {
           container gateway-entry {
             leaf gateway-name {
               type string;
             }
             leaf termination-count {
               type uint32;
               description "Number of terminations in the gateway";
             }
           }
           container service-pgcp-terminations-count {
             description "Count of termination entries per gateway";
             leaf gateway-name {
               type string;
             }
             leaf termination-count {
               type uint32;
               description "Number of terminations in the gateway";
             }
           }
         }
       }
     }
   }
   rpc get-service-pgcp-terminations-gateway {
     description "Show list of terminations for gateway";
     input {
       leaf gateway-name {
         description "Gateway name";
         type string;
         mandatory true;
       }
       leaf termination-prefix {
         description "Termination-prefix to use as filter, default * (all)";
         type string;
       }
       leaf display {
         default "brief";
         type enumeration {
           enum "h248" {
             description "Display H248 output format";
           }
           enum "brief" {
             description "Display brief output (default)";
           }
           enum "count" {
             description "Show count of matching entries";
           }
         }
       }
       leaf redundancy-option {
         default "master";
         type enumeration {
           enum "master" {
             description "Query the master RE or ms-pic (default)";
           }
           enum "backup" {
             description "Query the backup ms-pic";
           }
         }
       }
     }
   }
   rpc get-service-pgcp-gates {
     description "Show list of gates";
     output {
       container service-pgcp-gates {
         container brief {
           container gateway-entry {
             leaf gateway-name {
               type string;
             }
             leaf local-ip-address {
               type string;
             }
             leaf gateway-vrf {
               type string;
             }
             leaf local-port {
               type uint32;
             }
             leaf platform {
               type string;
             }
             leaf service-state {
               type string;
             }
             leaf active-controller {
               type string;
             }
             leaf replication-socket {
               type string;
             }
             leaf synchronization-state {
               type string;
             }
             leaf up-time {
               type string;
               description "Gateway uptime";
             }
             leaf load-status {
               type string;
               description "Gateway load status";
             }
             leaf cleanup-timeout {
               type uint32;
             }
             leaf maximum-concurrent-calls {
               type uint32;
               description "Maximum concurrent calls";
             }
             leaf inactivity-timeout-delay {
               type uint32;
             }
             leaf inactivity-timeout-duration {
               type uint32;
             }
             leaf latch-deadlock-duration {
               type uint32;
             }
             container inactivity-timer-entry {
               container maximum-inactivity-time {
                 leaf minimum {
                   type uint32;
                   description "Minimum valid value of maximum inactivity timeout";
                 }
                 leaf maximum {
                   type uint32;
                   description "Maximum valid value of maximum inactivity timeout";
                 }
                 leaf default {
                   type uint32;
                   description "Default valid value of maximum inactivity timeout";
                 }
               }
             }
           }
           container service-pgcp-gate-entry-information {
             leaf gate-id {
               type uint64;
               description "Gate id";
             }
             leaf gate-state {
               type string;
               description "Gate state (active/disabled)";
             }
             leaf gate-action {
               type string;
               description "Gate action (forward/drop)";
             }
             leaf gate-service-set-id {
               type uint32;
               description "Service set id";
             }
             leaf media-card-name {
               type string;
               description "Media card name";
             }
             leaf media-handler-name {
               type string;
               description "Media handler name";
             }
             leaf termination-id-string {
               type string;
               description "Termination id as string";
             }
             container gate-rtcp-information {
               container gate-rtcp-receiver-information {
                 description "RTCP receiver reports";
               }
               container gate-rtcp-extended-information {
                 description "RTCP extended report";
                 container gate-rtcp-extended-report {
                   leaf rtcp-xr-ssrc {
                     type uint32;
                     description "RTCP XR Synchronization source";
                   }
                   leaf packet-loss-concealment-type {
                     type string;
                     description "The type of packet loss concealment algorithm in use";
                   }
                   leaf network-packet-loss-rate {
                     type uint32;
                     description "The proportion of packets lost since the start of transmission";
                   }
                   leaf jitter-buffer-discard-rate {
                     type uint32;
                     description "The proportion of packets discarded by the receiving jitter buffer";
                   }
                   leaf rtcp-round-trip-delay {
                     type uint32;
                     description "The round-trip delay between the RTP endpoints";
                   }
                   leaf end-system-delay {
                     type uint32;
                     description "End system delay";
                   }
                   leaf signal-level {
                     type uint32;
                     description "The ratio of the signal level to a 0 dBm0 reference";
                   }
                   leaf noise-level {
                     type uint32;
                     description "The ratio of the silent period background noise level";
                   }
                   leaf residual-echo-return-loss {
                     type uint32;
                     description "The echo return loss after the effects of echo cancellation";
                   }
                   leaf r-factor {
                     type uint32;
                     description "A value representing the receiving end call quality of the RTP stream";
                   }
                   leaf external-r-factor {
                     type uint32;
                     description "External r factor";
                   }
                   leaf estimated-moslq {
                     type uint32;
                     description "An estimated receiving end Listening Quality MOS";
                   }
                   leaf estimated-moscq {
                     type uint32;
                     description "An estimated receiving end Conversational Quality MOS";
                   }
                 }
                 container gate-rtcp-extended-burst-metrics-report {
                   leaf minimum-gap-threshold {
                     type uint32;
                     description "A parameter used to define bursts";
                   }
                   leaf burst-loss-density {
                     type uint32;
                     description "The average proportion of packets both lost and discarded during burst periods";
                   }
                   leaf burst-duration {
                     type uint32;
                     description "The average length of burst periods";
                   }
                   leaf gap-loss-density {
                     type uint32;
                     description "The average proportion of packets lost and discarded during gap periods";
                   }
                   leaf gap-duration {
                     type uint32;
                     description "The average length of gap periods";
                   }
                 }
               }
             }
             container service-rate-limit-information {
               description "Rate limiting statistics";
             }
           }
           container service-pgcp-gates-count {
             description "Count of gate entries per gateway";
             leaf gateway-name {
               type string;
             }
             leaf gate-count {
               type uint32;
               description "Number of gates in the gateway";
             }
           }
         }
         container extensive {
           container gateway-entry {
             leaf gateway-name {
               type string;
             }
             leaf local-ip-address {
               type string;
             }
             leaf gateway-vrf {
               type string;
             }
             leaf local-port {
               type uint32;
             }
             leaf platform {
               type string;
             }
             leaf service-state {
               type string;
             }
             leaf active-controller {
               type string;
             }
             leaf replication-socket {
               type string;
             }
             leaf synchronization-state {
               type string;
             }
             leaf up-time {
               type string;
               description "Gateway uptime";
             }
             leaf load-status {
               type string;
               description "Gateway load status";
             }
             leaf cleanup-timeout {
               type uint32;
             }
             leaf maximum-concurrent-calls {
               type uint32;
               description "Maximum concurrent calls";
             }
             leaf inactivity-timeout-delay {
               type uint32;
             }
             leaf inactivity-timeout-duration {
               type uint32;
             }
             leaf latch-deadlock-duration {
               type uint32;
             }
             container inactivity-timer-entry {
               container maximum-inactivity-time {
                 leaf minimum {
                   type uint32;
                   description "Minimum valid value of maximum inactivity timeout";
                 }
                 leaf maximum {
                   type uint32;
                   description "Maximum valid value of maximum inactivity timeout";
                 }
                 leaf default {
                   type uint32;
                   description "Default valid value of maximum inactivity timeout";
                 }
               }
             }
           }
           container service-pgcp-gate-entry-information {
             leaf gate-id {
               type uint64;
               description "Gate id";
             }
             leaf gate-direction {
               type string;
               description "Gate direction (A->B/B->A)";
             }
             leaf gate-state {
               type string;
               description "Gate state (active/disabled)";
             }
             leaf gate-action {
               type string;
               description "Gate action (forward/drop)";
             }
             leaf source-routing-instance {
               type string;
               description "Source routing-instance";
             }
             leaf destination-routing-instance {
               type string;
               description "Destination routing-instance";
             }
             leaf gate-remote-source-address {
               type string;
               description "Gate remote source address";
             }
             leaf gate-remote-source-port {
               type string;
               description "Gate remote source port";
             }
             leaf gate-remote-destination-address {
               type string;
               description "Gate remote destination address";
             }
             leaf gate-remote-destination-port {
               type string;
               description "Gate remote destination port";
             }
             leaf gate-local-source-address {
               type string;
               description "Gate local source address";
             }
             leaf gate-local-source-port {
               type string;
               description "Gate local source port";
             }
             leaf gate-local-destination-address {
               type string;
               description "Gate local destination address";
             }
             leaf gate-local-destination-port {
               type string;
               description "Gate local destination port";
             }
             leaf gate-transport {
               type string;
               description "Gate transport protocols";
             }
             leaf gate-rtcp-shadow {
               type string;
               description "Is there a shadowed RTCP gate associated";
             }
             leaf gate-latch {
               type string;
               description "Install/uninstall a latch for this gate";
             }
             leaf gate-dscp {
               type string;
               description "DSCP for outgoing packets on this gate";
             }
             leaf gate-tman-policing {
               type string;
               description "Install/uninstall a traffic management policing for this gate";
             }
             leaf gate-sdr {
               type uint32;
               description "Sustainable data rate threshold for a gate";
             }
             leaf gate-pdr {
               type uint32;
               description "Peak data rate threshold for a gate";
             }
             leaf gate-mbs {
               type uint32;
               description "Maximum pdr burst size limit for a gate";
             }
             leaf rtcp-sdr {
               type uint32;
               description "SDR Sustainable data rate threshold of the RTCP stream";
             }
             leaf rtcp-pdr {
               type uint32;
               description "Peak data rate threshold of the RTCP stream";
             }
             leaf rtcp-mbs {
               type uint32;
               description "Maximum burst size limit of the RTCP stream";
             }
             leaf gate-fuf-policing {
               type string;
               description "Install/uninstall a fuf policer for this gate";
             }
             leaf gate-green-action {
               type string;
               description "Action to be application over green packets";
             }
             leaf gate-yellow-action {
               type string;
               description "Action to be application over yellow packets";
             }
             leaf gate-red-action {
               type string;
               description "Action to be application over red packets";
             }
             container gate-rtcp-information {
               container gate-rtcp-receiver-information {
                 description "RTCP receiver reports";
               }
               container gate-rtcp-extended-information {
                 description "RTCP extended report";
                 container gate-rtcp-extended-report {
                   leaf rtcp-xr-ssrc {
                     type uint32;
                     description "RTCP XR Synchronization source";
                   }
                   leaf packet-loss-concealment-type {
                     type string;
                     description "The type of packet loss concealment algorithm in use";
                   }
                   leaf network-packet-loss-rate {
                     type uint32;
                     description "The proportion of packets lost since the start of transmission";
                   }
                   leaf jitter-buffer-discard-rate {
                     type uint32;
                     description "The proportion of packets discarded by the receiving jitter buffer";
                   }
                   leaf rtcp-round-trip-delay {
                     type uint32;
                     description "The round-trip delay between the RTP endpoints";
                   }
                   leaf end-system-delay {
                     type uint32;
                     description "End system delay";
                   }
                   leaf signal-level {
                     type uint32;
                     description "The ratio of the signal level to a 0 dBm0 reference";
                   }
                   leaf noise-level {
                     type uint32;
                     description "The ratio of the silent period background noise level";
                   }
                   leaf residual-echo-return-loss {
                     type uint32;
                     description "The echo return loss after the effects of echo cancellation";
                   }
                   leaf r-factor {
                     type uint32;
                     description "A value representing the receiving end call quality of the RTP stream";
                   }
                   leaf external-r-factor {
                     type uint32;
                     description "External r factor";
                   }
                   leaf estimated-moslq {
                     type uint32;
                     description "An estimated receiving end Listening Quality MOS";
                   }
                   leaf estimated-moscq {
                     type uint32;
                     description "An estimated receiving end Conversational Quality MOS";
                   }
                 }
                 container gate-rtcp-extended-burst-metrics-report {
                   leaf minimum-gap-threshold {
                     type uint32;
                     description "A parameter used to define bursts";
                   }
                   leaf burst-loss-density {
                     type uint32;
                     description "The average proportion of packets both lost and discarded during burst periods";
                   }
                   leaf burst-duration {
                     type uint32;
                     description "The average length of burst periods";
                   }
                   leaf gap-loss-density {
                     type uint32;
                     description "The average proportion of packets lost and discarded during gap periods";
                   }
                   leaf gap-duration {
                     type uint32;
                     description "The average length of gap periods";
                   }
                 }
               }
             }
             container service-rate-limit-information {
               description "Rate limiting statistics";
             }
           }
           container service-pgcp-gates-count {
             description "Count of gate entries per gateway";
             leaf gateway-name {
               type string;
             }
             leaf gate-count {
               type uint32;
               description "Number of gates in the gateway";
             }
           }
         }
         container statistics {
           container gateway-entry {
             container inactivity-timer-entry {
               container maximum-inactivity-time {
                 leaf minimum {
                   type uint32;
                   description "Minimum valid value of maximum inactivity timeout";
                 }
                 leaf maximum {
                   type uint32;
                   description "Maximum valid value of maximum inactivity timeout";
                 }
                 leaf default {
                   type uint32;
                   description "Default valid value of maximum inactivity timeout";
                 }
               }
             }
           }
           container service-pgcp-gate-entry-information {
             leaf gate-output-packets {
               type uint64;
               description "Packet-sent by gate statistics";
             }
             leaf gate-input-packets {
               type uint64;
               description "Packet-received by gate statistics";
             }
             leaf gate-dropped-packets {
               type uint64;
               description "Packet-dropped by gate statistics";
             }
             leaf gate-lost-rtp-packets {
               type uint64;
               description "Number of lost RTP packets lost";
             }
             leaf gate-fractional-lost-rtp-packets {
               type uint64;
               description "Calculated fractional lost RTP packets";
             }
             leaf gate-measured-rate {
               type uint32;
               description "Measured rate of traffic for gate in bytes/second";
             }
             container gate-rtcp-information {
               container gate-rtcp-sender-information {
                 description "RTCP statistcs";
               }
               container gate-rtcp-receiver-information {
                 description "RTCP receiver reports";
                 container gate-rtcp-receiver-entry {
                 }
               }
               container gate-rtcp-extended-information {
                 description "RTCP extended report";
                 container gate-rtcp-extended-report {
                   leaf rtcp-xr-ssrc {
                     type uint32;
                     description "RTCP XR Synchronization source";
                   }
                   leaf packet-loss-concealment-type {
                     type string;
                     description "The type of packet loss concealment algorithm in use";
                   }
                   leaf network-packet-loss-rate {
                     type uint32;
                     description "The proportion of packets lost since the start of transmission";
                   }
                   leaf jitter-buffer-discard-rate {
                     type uint32;
                     description "The proportion of packets discarded by the receiving jitter buffer";
                   }
                   leaf rtcp-round-trip-delay {
                     type uint32;
                     description "The round-trip delay between the RTP endpoints";
                   }
                   leaf end-system-delay {
                     type uint32;
                     description "End system delay";
                   }
                   leaf signal-level {
                     type uint32;
                     description "The ratio of the signal level to a 0 dBm0 reference";
                   }
                   leaf noise-level {
                     type uint32;
                     description "The ratio of the silent period background noise level";
                   }
                   leaf residual-echo-return-loss {
                     type uint32;
                     description "The echo return loss after the effects of echo cancellation";
                   }
                   leaf r-factor {
                     type uint32;
                     description "A value representing the receiving end call quality of the RTP stream";
                   }
                   leaf external-r-factor {
                     type uint32;
                     description "External r factor";
                   }
                   leaf estimated-moslq {
                     type uint32;
                     description "An estimated receiving end Listening Quality MOS";
                   }
                   leaf estimated-moscq {
                     type uint32;
                     description "An estimated receiving end Conversational Quality MOS";
                   }
                 }
                 container gate-rtcp-extended-burst-metrics-report {
                   leaf minimum-gap-threshold {
                     type uint32;
                     description "A parameter used to define bursts";
                   }
                   leaf burst-loss-density {
                     type uint32;
                     description "The average proportion of packets both lost and discarded during burst periods";
                   }
                   leaf burst-duration {
                     type uint32;
                     description "The average length of burst periods";
                   }
                   leaf gap-loss-density {
                     type uint32;
                     description "The average proportion of packets lost and discarded during gap periods";
                   }
                   leaf gap-duration {
                     type uint32;
                     description "The average length of gap periods";
                   }
                 }
               }
             }
             container service-rate-limit-information {
               description "Rate limiting statistics";
               container service-rate-limit-entry {
               }
             }
             container gate-fuf-statistics-information {
               description "FUF statistics";
             }
             container gate-srtp-stats-information {
               description "Srtp encrypt and decrypt statistics";
             }
             container gate-srtcp-stats-information {
               description "Srtcp encrypt and decrypt statistics";
             }
           }
           container service-pgcp-gates-count {
             description "Count of gate entries per gateway";
             leaf gateway-name {
               type string;
             }
             leaf gate-count {
               type uint32;
               description "Number of gates in the gateway";
             }
           }
         }
         container count {
           container gateway-entry {
             leaf gateway-name {
               type string;
             }
             leaf gate-count {
               type uint32;
               description "Number of gates in the gateway";
             }
           }
           container service-pgcp-gate-entry-information {
             container gate-rtcp-information {
               container gate-rtcp-receiver-information {
                 description "RTCP receiver reports";
               }
               container gate-rtcp-extended-information {
                 description "RTCP extended report";
                 container gate-rtcp-extended-report {
                   leaf rtcp-xr-ssrc {
                     type uint32;
                     description "RTCP XR Synchronization source";
                   }
                   leaf packet-loss-concealment-type {
                     type string;
                     description "The type of packet loss concealment algorithm in use";
                   }
                   leaf network-packet-loss-rate {
                     type uint32;
                     description "The proportion of packets lost since the start of transmission";
                   }
                   leaf jitter-buffer-discard-rate {
                     type uint32;
                     description "The proportion of packets discarded by the receiving jitter buffer";
                   }
                   leaf rtcp-round-trip-delay {
                     type uint32;
                     description "The round-trip delay between the RTP endpoints";
                   }
                   leaf end-system-delay {
                     type uint32;
                     description "End system delay";
                   }
                   leaf signal-level {
                     type uint32;
                     description "The ratio of the signal level to a 0 dBm0 reference";
                   }
                   leaf noise-level {
                     type uint32;
                     description "The ratio of the silent period background noise level";
                   }
                   leaf residual-echo-return-loss {
                     type uint32;
                     description "The echo return loss after the effects of echo cancellation";
                   }
                   leaf r-factor {
                     type uint32;
                     description "A value representing the receiving end call quality of the RTP stream";
                   }
                   leaf external-r-factor {
                     type uint32;
                     description "External r factor";
                   }
                   leaf estimated-moslq {
                     type uint32;
                     description "An estimated receiving end Listening Quality MOS";
                   }
                   leaf estimated-moscq {
                     type uint32;
                     description "An estimated receiving end Conversational Quality MOS";
                   }
                 }
                 container gate-rtcp-extended-burst-metrics-report {
                   leaf minimum-gap-threshold {
                     type uint32;
                     description "A parameter used to define bursts";
                   }
                   leaf burst-loss-density {
                     type uint32;
                     description "The average proportion of packets both lost and discarded during burst periods";
                   }
                   leaf burst-duration {
                     type uint32;
                     description "The average length of burst periods";
                   }
                   leaf gap-loss-density {
                     type uint32;
                     description "The average proportion of packets lost and discarded during gap periods";
                   }
                   leaf gap-duration {
                     type uint32;
                     description "The average length of gap periods";
                   }
                 }
               }
             }
             container service-rate-limit-information {
               description "Rate limiting statistics";
             }
           }
           container service-pgcp-gates-count {
             description "Count of gate entries per gateway";
             leaf gateway-name {
               type string;
             }
             leaf gate-count {
               type uint32;
               description "Number of gates in the gateway";
             }
           }
         }
         container session-mirroring {
           container gateway-entry {
             leaf gateway-name {
               type string;
             }
             leaf local-ip-address {
               type string;
             }
             leaf gateway-vrf {
               type string;
             }
             leaf local-port {
               type uint32;
             }
             leaf platform {
               type string;
             }
             leaf service-state {
               type string;
             }
             leaf active-controller {
               type string;
             }
             leaf replication-socket {
               type string;
             }
             leaf synchronization-state {
               type string;
             }
             leaf up-time {
               type string;
               description "Gateway uptime";
             }
             leaf load-status {
               type string;
               description "Gateway load status";
             }
             leaf cleanup-timeout {
               type uint32;
             }
             leaf maximum-concurrent-calls {
               type uint32;
               description "Maximum concurrent calls";
             }
             leaf inactivity-timeout-delay {
               type uint32;
             }
             leaf inactivity-timeout-duration {
               type uint32;
             }
             leaf latch-deadlock-duration {
               type uint32;
             }
             container inactivity-timer-entry {
               container maximum-inactivity-time {
                 leaf minimum {
                   type uint32;
                   description "Minimum valid value of maximum inactivity timeout";
                 }
                 leaf maximum {
                   type uint32;
                   description "Maximum valid value of maximum inactivity timeout";
                 }
                 leaf default {
                   type uint32;
                   description "Default valid value of maximum inactivity timeout";
                 }
               }
             }
           }
           container service-pgcp-gate-entry-information {
             leaf gate-id {
               type uint64;
               description "Gate id";
             }
             leaf gate-state {
               type string;
               description "Gate state (active/disabled)";
             }
             leaf gate-action {
               type string;
               description "Gate action (forward/drop)";
             }
             leaf gate-mirroring-state {
               type string;
               description "Whether session mirroring is active for this gate";
             }
             leaf gate-mirroring-correlation-number {
               type string;
               description "Session mirroring correlation number";
             }
             leaf gate-mirroring-target-id {
               type string;
               description "List of session mirroring destinations";
             }
             leaf gate-mirroring-direction {
               type string;
               description "Whether session mirroring is done before or after NAT";
             }
             container gate-rtcp-information {
               container gate-rtcp-receiver-information {
                 description "RTCP receiver reports";
               }
               container gate-rtcp-extended-information {
                 description "RTCP extended report";
                 container gate-rtcp-extended-report {
                   leaf rtcp-xr-ssrc {
                     type uint32;
                     description "RTCP XR Synchronization source";
                   }
                   leaf packet-loss-concealment-type {
                     type string;
                     description "The type of packet loss concealment algorithm in use";
                   }
                   leaf network-packet-loss-rate {
                     type uint32;
                     description "The proportion of packets lost since the start of transmission";
                   }
                   leaf jitter-buffer-discard-rate {
                     type uint32;
                     description "The proportion of packets discarded by the receiving jitter buffer";
                   }
                   leaf rtcp-round-trip-delay {
                     type uint32;
                     description "The round-trip delay between the RTP endpoints";
                   }
                   leaf end-system-delay {
                     type uint32;
                     description "End system delay";
                   }
                   leaf signal-level {
                     type uint32;
                     description "The ratio of the signal level to a 0 dBm0 reference";
                   }
                   leaf noise-level {
                     type uint32;
                     description "The ratio of the silent period background noise level";
                   }
                   leaf residual-echo-return-loss {
                     type uint32;
                     description "The echo return loss after the effects of echo cancellation";
                   }
                   leaf r-factor {
                     type uint32;
                     description "A value representing the receiving end call quality of the RTP stream";
                   }
                   leaf external-r-factor {
                     type uint32;
                     description "External r factor";
                   }
                   leaf estimated-moslq {
                     type uint32;
                     description "An estimated receiving end Listening Quality MOS";
                   }
                   leaf estimated-moscq {
                     type uint32;
                     description "An estimated receiving end Conversational Quality MOS";
                   }
                 }
                 container gate-rtcp-extended-burst-metrics-report {
                   leaf minimum-gap-threshold {
                     type uint32;
                     description "A parameter used to define bursts";
                   }
                   leaf burst-loss-density {
                     type uint32;
                     description "The average proportion of packets both lost and discarded during burst periods";
                   }
                   leaf burst-duration {
                     type uint32;
                     description "The average length of burst periods";
                   }
                   leaf gap-loss-density {
                     type uint32;
                     description "The average proportion of packets lost and discarded during gap periods";
                   }
                   leaf gap-duration {
                     type uint32;
                     description "The average length of gap periods";
                   }
                 }
               }
             }
             container service-rate-limit-information {
               description "Rate limiting statistics";
             }
           }
           container service-pgcp-gates-count {
             description "Count of gate entries per gateway";
             leaf gateway-name {
               type string;
             }
             leaf gate-count {
               type uint32;
               description "Number of gates in the gateway";
             }
           }
         }
       }
     }
   }
   rpc get-service-pgcp-gates-gateway {
     description "Show all gates for gateway";
     input {
       leaf gateway-name {
         description "Gateway name";
         type string;
         mandatory true;
       }
       leaf display {
         default "brief";
         type enumeration {
           enum "extensive" {
             description "Display extensive output";
           }
           enum "brief" {
             description "Display brief output (default)";
           }
           enum "count" {
             description "Show count of matching entries";
           }
         }
       }
       leaf source-routing-instance {
         description "Source routing-instance";
         type string;
       }
       leaf destination-routing-instance {
         description "Destination routing-instance";
         type string;
       }
       leaf redundancy-option {
         default "master";
         type enumeration {
           enum "master" {
             description "Query the master RE or ms-pic (default)";
           }
           enum "backup" {
             description "Query the backup ms-pic";
           }
         }
       }
     }
   }
   rpc get-service-pgcp-gate {
     description "Show gate according to gate-id";
   }
   rpc get-service-pgcp-gate-gateway {
     description "Show gate for gateway";
     input {
       leaf gateway-name {
         description "Gateway name";
         type string;
         mandatory true;
       }
       leaf gate-id {
         description "Gate id";
         type uint64;
         mandatory true;
       }
       leaf display {
         default "brief";
         type enumeration {
           enum "extensive" {
             description "Display extensive output";
           }
           enum "brief" {
             description "Display brief output (default)";
           }
           enum "statistics" {
             description "Display statistics for gate";
           }
           enum "session-mirroring" {
             description "Display session mirroring for gate";
           }
         }
       }
       leaf redundancy-option {
         default "master";
         type enumeration {
           enum "master" {
             description "Query the master RE or ms-pic (default)";
           }
           enum "backup" {
             description "Query the backup ms-pic";
           }
         }
       }
     }
   }
   rpc get-services-pgcpd-root-termination {
     description "Show root termination h248 information";
     output {
       container services-pgcpd-root-termination {
         leaf root-termination-information {
           type string;
           description "H248 root termination information";
         }
       }
     }
   }
   rpc get-services-pgcpd-root-termination-gateway {
     description "Show root termination h248 information for gateway";
     input {
       leaf gateway-name {
         description "Gateway name";
         type string;
         mandatory true;
       }
       leaf redundancy-option {
         default "master";
         type enumeration {
           enum "master" {
             description "Query the master RE or ms-pic (default)";
           }
           enum "backup" {
             description "Query the backup ms-pic";
           }
         }
       }
     }
   }
   rpc get-service-border-signaling-gateway-statistics-calls {
     description "Show border signaling gateway calls statistics";
     output {
       container bsg-statistics-calls-details {
         container bsg-statistics-calls {
           leaf bsg-start-time {
             type string;
           }
           container bsg-service-point-calls-details {
             leaf bsg-sp-name {
               type string;
               description "The service point name";
             }
             leaf service-interface {
               type string;
               description "The service interface hexadecimal representation";
             }
             leaf bsg-server-name {
               type string;
               description "The server name";
             }
             leaf bsg-sp-direction {
               type string;
               description "The service point direction";
             }
             leaf bsg-sp-failed-calls {
               type uint32;
               description "Counts all the failed calls";
             }
             leaf bsg-sp-completed-calls {
               type uint32;
               description "Counts all the completed calls";
             }
             leaf bsg-sp-active-calls {
               type uint32;
               description "Counts all the active calls";
             }
           }
         }
       }
     }
   }
   rpc get-service-border-signaling-gateway-statistics-calls-by-sp {
     description "Show border signaling gateway calls statistics grouped by service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-calls-by-server {
     description "Show border signaling gateway calls statistics grouped by server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-calls-duration-by-sp {
     description "Show border signaling gateway calls duration statistics grouped by service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-calls-duration-by-server {
     description "Show border signaling gateway calls duration statistics grouped by server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-failed-calls-by-sp {
     description "Show border signaling gateway failed calls statistics grouped by service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-statistics-calls-failed-details {
         container bsg-statistics-calls-failed {
           leaf bsg-start-time {
             type string;
           }
           container bsg-service-point-calls-failed-details {
             leaf bsg-sp-name {
               type string;
               description "The service point name";
             }
             leaf service-interface {
               type string;
               description "The service interface hexadecimal representation";
             }
             leaf bsg-server-name {
               type string;
               description "The server name";
             }
             leaf bsg-sp-direction {
               type string;
               description "The service point direction";
             }
             leaf bsg-sp-error-response-code {
               type uint32;
               description "Error response codes received during call setup that terminated the call";
             }
             leaf bsg-sp-internal-error {
               type uint32;
               description "BSG Internal errors during the call setup that terminated the call";
             }
             leaf bsg-sp-inactive-timeout {
               type uint32;
               description "Inactive timeout timer has expired and caused active call termination";
             }
             leaf bsg-sp-setup-media-failure {
               type uint32;
               description "Some media failure during call setup terminated the call";
             }
             leaf bsg-sp-established-call-media-inactivity {
               type uint32;
               description "A media inactivity was detected, causing the call to terminate";
             }
             leaf bsg-sp-cac-policy-rejection {
               type uint32;
               description "The call was terminated during setup due to CAC restrictions";
             }
             leaf bsg-sp-default-behavior-policy-rejection {
               type uint32;
               description "No matching accepting policy was match on the incoming call";
             }
             leaf bsg-sp-configured-behavior-policy-rejection {
               type uint32;
               description "The call was actively rejected by the policy";
             }
             leaf bsg-sp-transport-conflict-policy-rejection {
               type uint32;
               description "No matching egress service point was found";
             }
             leaf bsg-sp-protocol-error {
               type uint32;
               description "Some protocol error during call setup terminated the call";
             }
             leaf bsg-sp-setup-timeout {
               type uint32;
               description "Some timeout during call setup terminated the call";
             }
             leaf bsg-sp-transport-error {
               type uint32;
               description "Some transport error during call setup terminated the call";
             }
             leaf bsg-sp-canceled-calls {
               type uint32;
               description "Call was canceled";
             }
             leaf bsg-sp-media-abort {
               type uint32;
               description "A session abort notification received, causing the call to terminate";
             }
           }
         }
       }
     }
   }
   rpc get-service-border-signaling-gateway-statistics-failed-calls-by-server {
     description "Show border signaling gateway failed calls statistics grouped by server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-statistics-calls-failed-details {
         container bsg-statistics-calls-failed {
           leaf bsg-start-time {
             type string;
           }
           container bsg-service-point-calls-failed-details {
             leaf bsg-sp-name {
               type string;
               description "The service point name";
             }
             leaf service-interface {
               type string;
               description "The service interface hexadecimal representation";
             }
             leaf bsg-server-name {
               type string;
               description "The server name";
             }
             leaf bsg-sp-direction {
               type string;
               description "The service point direction";
             }
             leaf bsg-sp-error-response-code {
               type uint32;
               description "Error response codes received during call setup that terminated the call";
             }
             leaf bsg-sp-internal-error {
               type uint32;
               description "BSG Internal errors during the call setup that terminated the call";
             }
             leaf bsg-sp-inactive-timeout {
               type uint32;
               description "Inactive timeout timer has expired and caused active call termination";
             }
             leaf bsg-sp-setup-media-failure {
               type uint32;
               description "Some media failure during call setup terminated the call";
             }
             leaf bsg-sp-established-call-media-inactivity {
               type uint32;
               description "A media inactivity was detected, causing the call to terminate";
             }
             leaf bsg-sp-cac-policy-rejection {
               type uint32;
               description "The call was terminated during setup due to CAC restrictions";
             }
             leaf bsg-sp-default-behavior-policy-rejection {
               type uint32;
               description "No matching accepting policy was match on the incoming call";
             }
             leaf bsg-sp-configured-behavior-policy-rejection {
               type uint32;
               description "The call was actively rejected by the policy";
             }
             leaf bsg-sp-transport-conflict-policy-rejection {
               type uint32;
               description "No matching egress service point was found";
             }
             leaf bsg-sp-protocol-error {
               type uint32;
               description "Some protocol error during call setup terminated the call";
             }
             leaf bsg-sp-setup-timeout {
               type uint32;
               description "Some timeout during call setup terminated the call";
             }
             leaf bsg-sp-transport-error {
               type uint32;
               description "Some transport error during call setup terminated the call";
             }
             leaf bsg-sp-canceled-calls {
               type uint32;
               description "Call was canceled";
             }
             leaf bsg-sp-media-abort {
               type uint32;
               description "A session abort notification received, causing the call to terminate";
             }
           }
         }
       }
     }
   }
   rpc get-service-bsg-denied-messages {
     description "Show information about dropped messages";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-statistics-denied-messages-details {
         container bsg-statistics-denied-messages {
           leaf overload-last-reset-time {
             type string;
             description "Last overload reset time";
           }
           container bsg-denied-messages-details {
             leaf bsg-denied-message {
               type string;
               description "Displays the time a message was denied";
             }
           }
         }
       }
     }
   }
   rpc get-service-border-signaling-gateway-statistics-admission-control {
     description "Show border signaling gateway admission control profile statistics statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-information-by-request-uri {
     description "Show border signaling gateway information by request uri";
     input {
       leaf gateway {
         description "Name of border signaling gateway";
         type string;
         mandatory true;
       }
       leaf uri {
         description "URI";
         type string;
       }
       leaf display {
         default "brief";
         type enumeration {
           enum "brief" {
             description "Display brief output (default)";
           }
           enum "summary" {
             description "Display summary output";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
   }
   rpc get-service-border-signaling-gateway-information-by-contact {
     description "Show border signaling gateway information by contact";
     input {
       leaf gateway {
         description "Name of border signaling gateway";
         type string;
         mandatory true;
       }
       leaf contact {
         description "Contact";
         type string;
       }
       leaf display {
         default "brief";
         type enumeration {
           enum "brief" {
             description "Display brief output (default)";
           }
           enum "summary" {
             description "Display summary output";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
   }
   rpc get-service-bsg-information-by-call-context-id {
     description "Show border signaling gateway information by call context ID";
     input {
       leaf gateway {
         description "Name of border signaling gateway";
         type string;
         mandatory true;
       }
       leaf context-id {
         description "Call context ID";
         type uint32;
       }
       leaf display {
         default "brief";
         type enumeration {
           enum "brief" {
             description "Display brief output (default)";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
   }
   rpc get-service-bsg-status-information {
     description "Show border signaling gateway status information";
     input {
       leaf gateway {
         description "Name of border signaling gateway";
         type string;
         mandatory true;
       }
       leaf display {
         default "brief";
         type enumeration {
           enum "brief" {
             description "Display brief output (default)";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
     output {
       container bsg-status-information {
         leaf bsg-redundancy-state {
           type string;
           description "Shows bsg redundancy state";
         }
         container bsg-redundancy-pic-info {
           description "Shows PIC information";
           leaf bsg-redundancy-local-or-remote {
             type string;
             description "Local or remote pic";
           }
           leaf bsg-redundancy-pic-if-name {
             type string;
             description "Shows PIC interface name";
           }
           leaf bsg-redundancy-pic-ip {
             type string;
             description "Shows PIC IP address";
           }
           leaf bsg-redundancy-pic-rms-role {
             type string;
             description "Shows PIC RMS role";
           }
         }
         container bsg-redundancy-connection-info {
           description "Shows the connection information";
           leaf bsg-redundancy-conn-type {
             type string;
             description "Shows the connection type";
           }
           leaf bsg-redundancy-conn-status {
             type string;
             description "Shows the connection status";
           }
           leaf bsg-redundancy-conn-details {
             type string;
             description "Shows the connection details";
           }
           leaf bsg-redundancy-conn-messages {
             type string;
             description "Shows the number of Rx/Tx messages";
           }
         }
       }
     }
   }
   rpc get-border-signaling-gateway-name-resolution-cache-by-fqdn {
     description "Show records for the Fully Qualified Domain Name";
     input {
       leaf fqdn {
         description "Fully Qualified Domain Name";
         type string;
         mandatory true;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-name-resolution-cache-information {
         container bsg-nr-cache {
           container bsg-name-resolution-entry {
             leaf bsg-nr-entry-fqdn {
               type string;
               description "Domain name";
             }
             leaf bsg-nr-entry-type {
               type string;
               description "Record type";
             }
             leaf bsg-nr-entry-rdata {
               type string;
               description "Raw data";
             }
             leaf bsg-nr-entry-ttl-expiry {
               type uint32;
               description "Seconds to TTL expiry";
             }
             leaf bsg-nr-entry-blacklist-expiry {
               type uint32;
               description "Seconds to TTL expiry";
             }
           }
         }
       }
     }
   }
   rpc get-service-border-signaling-gateway-name-resolution-cache-all {
     description "Show contents of the cache";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-name-resolution-cache-information {
         container bsg-nr-cache {
           container bsg-name-resolution-entry {
             leaf bsg-nr-entry-fqdn {
               type string;
               description "Domain name";
             }
             leaf bsg-nr-entry-type {
               type string;
               description "Record type";
             }
             leaf bsg-nr-entry-rdata {
               type string;
               description "Raw data";
             }
             leaf bsg-nr-entry-ttl-expiry {
               type uint32;
               description "Seconds to TTL expiry";
             }
             leaf bsg-nr-entry-blacklist-expiry {
               type uint32;
               description "Seconds to TTL expiry";
             }
           }
         }
       }
     }
   }
   rpc get-service-border-signaling-gateway-routing-blacklist {
     description "Show border signaling gateway servers blacklist content";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-bsg-registrations {
     description "Show border signaling gateway registrations statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-registrations {
         leaf bsg-registrations-start-time {
           type string;
           description "Statistics start time";
         }
         leaf bsg-registrations-active-registrations {
           type string;
           description "Number of active registrations";
         }
       }
     }
   }
   rpc get-service-bsg-registrations-statistics {
     description "Show registration statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-registrations {
         leaf bsg-registrations-start-time {
           type string;
           description "Statistics start time";
         }
         leaf bsg-registrations-active-registrations {
           type string;
           description "Number of active registrations";
         }
       }
     }
   }
   rpc get-service-bsg-registrations-realm-statistics {
     description "Realm statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
       leaf realm-name {
         type string;
       }
     }
     output {
       container bsg-registrations-realm {
         leaf bsg-registrations-realm-start-time {
           type string;
           description "Statistics start time";
         }
         leaf bsg-registrations-realm-name {
           type string;
           description "Name of realm";
         }
         leaf bsg-registrations-realm-active-registrations {
           type string;
           description "Number of active registrations";
         }
       }
     }
   }
   rpc get-service-border-signaling-gateway-address-of-record {
     description "Show border signaling gateway address of record";
     output {
       container bsg-address-of-records {
         container bsg-address-of-record {
           description "Address of record";
           leaf bsg-aor-name {
             type string;
             description "The address-of-record";
           }
           leaf bsg-aor-bindings-num-of-lu {
             type string;
             description "Number of binded contacts";
           }
           container bsg-address-of-record-bindings {
             description "Binding URI's";
             container bsg-address-of-record-binding {
               description "Binding URI's";
               leaf bsg-aor-bindings-uri {
                 type string;
                 description "The URI";
               }
               leaf bsg-aor-bindings-reg-realm {
                 type string;
                 description "The realm where the user registered from";
               }
               leaf bsg-aor-bindings-service-point {
                 type string;
                 description "The service-point where the user registered from";
               }
               leaf bsg-aor-bindings-first-reg-time {
                 type string;
                 description "The first registration time";
               }
               leaf bsg-aor-bindings-last-reg-time {
                 type string;
                 description "The last registration time";
               }
               leaf bsg-aor-bindings-expiration-time {
                 type string;
                 description "The expiration time";
               }
               leaf bsg-aor-bindings-lu {
                 type string;
                 description "The translated URI";
               }
               leaf bsg-aor-bindings-fe-nat-used {
                 type string;
                 description "Whether FE-NAT traversal logic is applied to this UE";
               }
               leaf bsg-aor-bindings-fe-nat-method {
                 type string;
                 description "Far End NAT traversal method";
               }
               leaf bsg-aor-bindings-fe-nat-ka-interval {
                 type uint32;
                 description "Far End NAT traversal keepalive interval";
               }
             }
           }
         }
       }
     }
   }
   rpc get-service-border-signaling-gateway-address-of-record-bindings {
     description "Show address of record bindings";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
       leaf address-of-record {
         description "Address of record name";
         type string;
       }
       leaf detail {
         description "Detail mode";
         type empty;
       }
     }
   }
   rpc get-service-border-signaling-gateway-charging-status {
     description "Show border signaling gateway accounting status";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-charging-status {
         leaf bsg-charging-name {
           type string;
           description "Charging Trigger Function - name";
         }
         leaf bsg-charging-release-number {
           type string;
           description "Charging Trigger Function - 3GPP release number";
         }
         leaf bsg-charging-operational-mode {
           type string;
           description "Charging Trigger Function - operational mode (session or event)";
         }
         container bsg-charging-status-cdf {
           description "Charging Trigger Function - CDF servers list";
           leaf bsg-charging-cdf-name {
             type string;
             description "Charging Data Function Server - name";
           }
           leaf bsg-charging-cdf-realm {
             type string;
             description "Charging Data Function Server - server's realm";
           }
           leaf bsg-charging-cdf-host {
             type string;
             description "Charging Data Function Server - server's host name";
           }
           leaf bsg-charging-cdf-priority {
             type uint32;
             description "Charging Data Function Server - server's priority";
           }
         }
       }
     }
   }
   rpc get-service-border-signaling-gateway-charging-statistics {
     description "Show border signaling gateway accounting statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-charging-statistics {
         leaf number-of-ctf-messages {
           type uint32;
           description "Number of charging-trigger messages";
         }
         leaf number-of-ctf-retries-messages {
           type uint32;
           description "Number of charging-trigger retries messages";
         }
         leaf number-of-ctf-replied-messages {
           type uint32;
           description "Number of charging-trigger replied messages";
         }
         leaf number-of-ctf-error-replied-messages {
           type uint32;
           description "Number of charging-trigger error reply messages";
         }
       }
     }
   }
   rpc get-service-msp-flow-table-information {
     description "Show flow table entries";
     input {
       leaf all {
         description "Display all the entries";
         type empty;
       }
       leaf limit {
         description "Maximum number of entries to display";
         type uint32 {
           range "1 .. 4294967295";
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type uint16;
       }
       leaf destination-port {
         description "Destination port to use as filter";
         type uint16;
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
         }
       }
       leaf get-service-sfw-flow-count-information {
         description "Show count of matching entries";
         type empty;
       }
     }
     output {
       container service-sfw-flow-table-information {
         container sfw-per-service-set-flow-table {
           description "Flows sorted by service set";
           leaf interface-name {
             type string;
             description "Name of the adaptive services interface";
           }
           leaf service-set-name {
             type string;
             description "Name of the service set";
           }
           container service-sfw-flow-table {
             description "Stateful firewall flows";
             leaf service-sfw-flow-table.heading {
               type string;
               description "Stateful firewall flows";
             }
             container sfw-flow-entry {
               description "Flow brief information";
               leaf sfw-flow-protocol {
                 type string;
                 description "Flow protocol description";
               }
               leaf sfw-flow-source-ip {
                 type string;
                 description "Source IP address";
               }
               leaf sfw-flow-source-port {
                 type int32;
                 description "Source port address";
               }
               leaf sfw-flow-destination-ip {
                 type string;
                 description "Flow destination IP address";
               }
               leaf sfw-flow-destination-port {
                 type string;
                 description "Flow destination port";
               }
               leaf sfw-flow-state {
                 type string;
                 description "Flow state";
               }
               leaf sfw-flow-direction {
                 type string;
                 description "Flow direction";
               }
               leaf sfw-flow-frame-counter {
                 type uint64;
                 description "Number of frames transmitted";
               }
               leaf sfw-flow-gate-id {
                 type uint64;
                 description "PGCP gate-id";
               }
               leaf sfw-flow-table-byte-count {
                 type uint64;
                 description "Flow byte count";
               }
               leaf sfw-flow-table-tcp-window-size {
                 type uint64;
                 description "TCP protocol window size";
               }
               leaf sfw-flow-table-tcp-acknowledge {
                 type uint64;
                 description "TCP protocol acknowledge";
               }
               leaf sfw-flow-table-tcp-tickle {
                 type uint64;
                 description "Time between TCP tickles (seconds)";
               }
               leaf sfw-flow-table-role {
                 type string;
                 description "Role of flow in conversation";
               }
               leaf sfw-flow-table-timeout {
                 type uint64;
                 description "Timeout value of flow (seconds)";
               }
               leaf sfw-flow-table-protocol-detail {
                 type string;
                 description "Flow protocol detail information";
               }
               container sfw-flow-nat {
                 description "NAT translation";
                 leaf sfw-flow-nat-type {
                   type string;
                   description "Type of NAT translation";
                 }
                 leaf sfw-flow-nat-ip {
                   type string;
                   description "Original IP address";
                 }
                 leaf sfw-flow-nat-port {
                   type string;
                   description "Original port";
                 }
                 leaf sfw-flow-translated-ip {
                   type string;
                   description "Translated IP address";
                 }
                 leaf sfw-flow-translated-port {
                   type string;
                   description "Translated port";
                 }
               }
             }
           }
         }
       }
     }
   }
   rpc get-msp-session-table {
     description "Show session table entries";
     input {
       leaf limit {
         description "Maximum number of entries to display";
         type uint32;
       }
       leaf display {
         default "brief";
         type enumeration {
           enum "extensive" {
             description "Display extensive output";
           }
           enum "brief" {
             description "Display brief output (default)";
           }
         }
       }
       leaf source-prefix {
         description "Source prefix to use as filter";
         type string;
       }
       leaf destination-prefix {
         description "Destination prefix to use as filter";
         type string;
       }
       leaf source-port {
         description "Source port to use as filter";
         type uint16;
       }
       leaf destination-port {
         description "Destination port to use as filter";
         type uint16;
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
         }
       }
     }
   }
   rpc get-service-msp-sess-count-information {
     description "Show count of matching entries";
     input {
       leaf source-prefix {
         description "Source prefix to use as filter";
         type string;
       }
       leaf destination-prefix {
         description "Destination prefix to use as filter";
         type string;
       }
       leaf source-port {
         description "Source port to use as filter";
         type uint16;
       }
       leaf destination-port {
         description "Destination port to use as filter";
         type uint16;
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
         }
       }
       leaf service-set {
         description "Name of service set";
         type string;
       }
       leaf interface {
         description "Name of extension provider interface";
         type string;
       }
     }
     output {
       container service-msp-sess-count-information {
         container service-msp-sess-count {
           description "Stateful firewall sessions count";
           leaf interface-name {
             type string;
             description "Name of the adaptive services interface";
           }
           leaf service-set-name {
             type string;
             description "Name of the service set";
           }
           leaf sess-count {
             type uint32;
             description "Number of sessions in the service set";
           }
         }
       }
     }
   }
   rpc show-service-msp-session-analysis-information {
     description "Show service sessions statistics";
     input {
       leaf interface {
         description "Name of extension provider interface";
         type string;
       }
     }
   }
   rpc get-services-sessions-utilization {
     description "Show session utilization statistics";
     input {
       leaf interface {
         description "Name of extension provider interface";
         type string;
       }
     }
     output {
       container services-sessions-utilization-information {
         container services-sessions-utilization {
           description "Sessions utilization statistics";
           leaf interface-name {
             type string;
             description "Name of the adaptive services interface";
           }
           leaf session-count {
             type uint32;
             description "Session count";
           }
           leaf memory-percent {
             type uint32;
             description "Memory usage (percent)";
           }
           leaf session-setup-rate {
             type uint32;
             description "Session setup rate";
           }
           leaf session-setup-percent {
             type uint32;
             description "Setup load (percent)";
           }
           leaf session-drop-rate {
             type uint32;
             description "Session drop rate";
           }
           leaf session-teardown-rate {
             type uint32;
             description "Session teardown rate";
           }
           leaf cpu-load {
             type string;
             description "CPU load";
           }
         }
       }
     }
   }
   rpc get-service-msp-alg-conversation-information {
     description "Show alg conversations";
     input {
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
         }
       }
       leaf display {
         default "brief";
         type enumeration {
           enum "extensive" {
             description "Display extensive output";
           }
           enum "brief" {
             description "Display brief output (default)";
           }
         }
       }
     }
     output {
       container service-msp-alg-conversation-information {
         leaf interface-name {
           type string;
           description "Name of the adaptive services interface";
         }
         container msp-alg-conv-all-entry {
           description "ALG conversations";
           leaf client-name {
             type string;
           }
           leaf client-state {
             type string;
           }
           leaf num-groups {
             type uint32;
           }
           leaf parent-sess-state {
             type string;
           }
           leaf parent-sess-id {
             type uint64;
           }
           leaf parent-flow-protocol {
             type string;
           }
           leaf parent-fflow-src-ip {
             type string;
           }
           leaf parent-fflow-src-port {
             type uint32;
           }
           leaf parent-fflow-dst-ip {
             type string;
           }
           leaf parent-fflow-dst-port {
             type uint32;
           }
           leaf parent-rflow-src-ip {
             type string;
           }
           leaf parent-rflow-src-port {
             type uint32;
           }
           leaf parent-rflow-dst-ip {
             type string;
           }
           leaf parent-rflow-dst-port {
             type uint32;
           }
           leaf child-sess-id {
             type uint64;
           }
           leaf child-flow-protocol {
             type string;
           }
           leaf child-fflow-src-ip {
             type string;
           }
           leaf child-fflow-src-port {
             type uint32;
           }
           leaf child-fflow-dst-ip {
             type string;
           }
           leaf child-fflow-dst-port {
             type uint32;
           }
           leaf child-rflow-src-ip {
             type string;
           }
           leaf child-rflow-src-port {
             type uint32;
           }
           leaf child-rflow-dst-ip {
             type string;
           }
           leaf child-rflow-dst-port {
             type uint32;
           }
           leaf group-id {
             type uint32;
           }
           leaf group-state {
             type string;
           }
           leaf num-resources {
             type uint32;
           }
           leaf resource-id {
             type uint32;
           }
           leaf resource-state {
             type string;
           }
           leaf num-sessions {
             type uint32;
           }
           leaf group-is-active {
             type string;
           }
           leaf parent-session-id {
             type uint64;
           }
           leaf group-timeout {
             type uint32;
           }
           leaf resource {
             type uint32;
           }
         }
         container msp-alg-conv-all-extensive-entry {
           description "ALG conversations extensive";
           leaf client-name {
             type string;
           }
           leaf client-state {
             type string;
           }
           leaf num-groups {
             type uint32;
           }
           leaf group-id {
             type uint32;
           }
           leaf group-state {
             type string;
           }
           leaf parent-sess-state {
             type string;
           }
           leaf parent-sess-id {
             type uint64;
           }
           leaf parent-flow-protocol {
             type string;
           }
           leaf parent-fflow-src-ip {
             type string;
           }
           leaf parent-fflow-src-port {
             type uint32;
           }
           leaf parent-fflow-dst-ip {
             type string;
           }
           leaf parent-fflow-dst-port {
             type uint32;
           }
           leaf parent-rflow-src-ip {
             type string;
           }
           leaf parent-rflow-src-port {
             type uint32;
           }
           leaf parent-rflow-dst-ip {
             type string;
           }
           leaf parent-rflow-dst-port {
             type uint32;
           }
           leaf num-resources {
             type uint32;
           }
           leaf resource-id {
             type uint32;
           }
           leaf resource-state {
             type string;
           }
           leaf num-sessions {
             type uint32;
           }
           leaf child-sess-id {
             type uint64;
           }
           leaf child-flow-protocol {
             type string;
           }
           leaf child-fflow-src-ip {
             type string;
           }
           leaf child-fflow-src-port {
             type uint32;
           }
           leaf child-fflow-dst-ip {
             type string;
           }
           leaf child-fflow-dst-port {
             type uint32;
           }
           leaf child-rflow-src-ip {
             type string;
           }
           leaf child-rflow-src-port {
             type uint32;
           }
           leaf child-rflow-dst-ip {
             type string;
           }
           leaf child-rflow-dst-port {
             type uint32;
           }
           leaf group-is-active {
             type string;
           }
           leaf parent-session-id {
             type uint64;
           }
           leaf group-timeout {
             type uint32;
           }
           leaf resource {
             type uint32;
           }
         }
         container msp-alg-conv-summary-entry {
           description "ALG conversation summary";
           leaf clients-active {
             type uint32;
           }
           leaf groups-active {
             type uint32;
           }
           leaf resources-active {
             type uint32;
           }
           leaf sessions-active {
             type uint32;
           }
         }
         container msp-alg-conv-groups-entry {
           description "ALG groups";
           leaf group-id {
             type uint32;
           }
           leaf group-is-active {
             type string;
           }
           leaf client-name {
             type string;
           }
           leaf num-resources {
             type uint32;
           }
           leaf resource-id {
             type uint32;
           }
           leaf parent-session-id {
             type uint64;
           }
           leaf group-timeout {
             type uint32;
           }
           leaf resource {
             type uint32;
           }
         }
         container msp-alg-conv-group-num-entry {
           description "ALG group information";
           leaf group-id {
             type uint32;
           }
           leaf group-is-active {
             type string;
           }
           leaf client-name {
             type string;
           }
           leaf parent-session-id {
             type uint64;
           }
           leaf group-timeout {
             type uint32;
           }
           leaf num-resources {
             type uint32;
           }
           leaf resource {
             type uint32;
           }
         }
         container msp-alg-conv-resources-entry {
           description "ALG resources";
           leaf resource-id {
             type uint32;
           }
           leaf resource-is-active {
             type string;
           }
           leaf group-id {
             type uint32;
           }
           leaf client-name {
             type string;
           }
           leaf num-sessions {
             type uint32;
           }
           leaf session-id {
             type uint64;
           }
           leaf session-ids {
             type uint64;
           }
           leaf num-holes {
             type uint32;
           }
           leaf src-ip-low {
             type string;
           }
           leaf src-ip-high {
             type string;
           }
           leaf src-port-low {
             type uint32;
           }
           leaf src-port-high {
             type uint32;
           }
           leaf dst-ip-low {
             type string;
           }
           leaf dst-ip-high {
             type string;
           }
           leaf dst-port-low {
             type uint32;
           }
           leaf dst-port-high {
             type uint32;
           }
           leaf translated-src-ip {
             type string;
           }
           leaf translated-src-port {
             type uint32;
           }
           leaf translated-dst-ip {
             type string;
           }
           leaf translated-dst-port {
             type uint32;
           }
           leaf proto {
             type uint32;
           }
           leaf ref-count {
             type uint32;
           }
         }
         container msp-alg-conv-resource-num-entry {
           description "ALG resource information";
           leaf resource-id {
             type uint32;
           }
           leaf resource-is-active {
             type string;
           }
           leaf num-sessions {
             type uint32;
           }
           leaf session-ids {
             type uint64;
           }
           leaf num-holes {
             type uint32;
           }
           leaf src-ip-low {
             type string;
           }
           leaf src-ip-high {
             type string;
           }
           leaf src-port-low {
             type uint32;
           }
           leaf src-port-high {
             type uint32;
           }
           leaf dst-ip-low {
             type string;
           }
           leaf dst-ip-high {
             type string;
           }
           leaf dst-port-low {
             type uint32;
           }
           leaf dst-port-high {
             type uint32;
           }
           leaf translated-src-ip {
             type string;
           }
           leaf translated-src-port {
             type uint32;
           }
           leaf translated-dst-ip {
             type string;
           }
           leaf translated-dst-port {
             type uint32;
           }
           leaf proto {
             type uint32;
           }
           leaf ref-count {
             type uint32;
           }
         }
       }
     }
   }
   rpc get-service-msp-alg-stats-information {
     description "Show ALG Statistics";
     input {
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
         }
       }
     }
     output {
       container service-msp-alg-stats-information {
         leaf interface-name {
           type string;
           description "Name of the adaptive services interface";
         }
         container msp-alg-rsh-entry {
           description "RSH ALG stats";
           leaf rsh-invalid-pkts {
             type uint32;
           }
           leaf rsh-drop-pkts {
             type uint32;
           }
           leaf rsh-parse-fail-pkts {
             type uint32;
           }
           leaf rsh-freed-pkts {
             type uint32;
           }
         }
         container msp-alg-dns-entry {
           description "DNS ALG statistics";
           leaf dns-invalid-pkts {
             type uint32;
           }
           leaf dns-reply-pkts {
             type uint32;
           }
           leaf dns-oversize-pkts {
             type uint32;
           }
         }
         container msp-alg-pptp-entry {
           description "PPTP ALG statistics";
           leaf pptp-objects-active {
             type uint32;
           }
           leaf pptp-objects-total {
             type uint32;
           }
           leaf pptp-objects-error {
             type uint32;
           }
           leaf pptp-group-active {
             type uint32;
           }
           leaf pptp-group-total {
             type uint32;
           }
           leaf pptp-group-error {
             type uint32;
           }
           leaf pptp-packets-received {
             type uint32;
           }
           leaf pptp-packets-discarded {
             type uint32;
           }
           leaf pptp-packets-free {
             type uint32;
           }
           leaf pptp-ocrq-rcvd {
             type uint32;
           }
           leaf pptp-ocrq-discarded {
             type uint32;
           }
           leaf pptp-ocrp-rcvd {
             type uint32;
           }
           leaf pptp-ocrp-discarded {
             type uint32;
           }
           leaf pptp-wen-rcvd {
             type uint32;
           }
           leaf pptp-wen-discarded {
             type uint32;
           }
           leaf pptp-ccrq-rcvd {
             type uint32;
           }
           leaf pptp-cdsn-rcvd {
             type uint32;
           }
           leaf pptp-ccrq-discarded {
             type uint32;
           }
           leaf pptp-session-create {
             type uint32;
           }
           leaf pptp-session-destroy {
             type uint32;
           }
           leaf pptp-gate-create {
             type uint32;
           }
           leaf pptp-gate-hit {
             type uint32;
           }
           leaf pptp-gate-timeout {
             type uint32;
           }
           leaf pptp-nat-event {
             type uint32;
           }
           leaf pptp-nat-total {
             type uint32;
           }
           leaf pptp-nat-ok {
             type uint32;
           }
           leaf pptp-nat-pending {
             type uint32;
           }
           leaf pptp-nat-fail {
             type uint32;
           }
           leaf pptp-rm-total {
             type uint32;
           }
           leaf pptp-rm-ok {
             type uint32;
           }
           leaf pptp-rm-pending {
             type uint32;
           }
           leaf pptp-rm-fail {
             type uint32;
           }
           leaf pptp-nat-async-total {
             type uint32;
           }
           leaf pptp-nat-async-invalid {
             type uint32;
           }
           leaf pptp-nat-async-error1 {
             type uint32;
           }
           leaf pptp-nat-async-error2 {
             type uint32;
           }
           leaf pptp-asl-hole-ok {
             type uint32;
           }
           leaf pptp-asl-hole-error {
             type uint32;
           }
           leaf pptp-asl-first-hit {
             type uint32;
           }
           leaf pptp-asl-hole-timeout {
             type uint32;
           }
           leaf pptp-asl-invalid {
             type uint32;
           }
           leaf pptp-nat-ctx-free {
             type uint32;
           }
           leaf pptp-create-resource-error {
             type uint32;
           }
           leaf pptp-s2c-hole-error {
             type uint32;
           }
           leaf pptp-c2s-hole-error {
             type uint32;
           }
           leaf pptp-lnbrk-error {
             type uint32;
           }
           leaf pptp-mpool-error {
             type uint32;
           }
           leaf pptp-rm-client-error {
             type uint32;
           }
         }
         container msp-alg-rtsp-entry {
           description "RTSP ALG statistics";
           leaf rtsp-exceed-max-data-len {
             type uint32;
           }
           leaf rtsp-drop-packets {
             type uint32;
           }
           leaf rtsp-describe-msg-cnt {
             type uint32;
           }
           leaf rtsp-setup-msg-cnt {
             type uint32;
           }
           leaf rtsp-teardown-msg-cnt {
             type uint32;
           }
         }
         container msp-alg-ftp-entry {
           description "FTP ALG stats";
           leaf ftp-drop-pkts {
             type uint32;
           }
           leaf ftp-parse-fail-pkts {
             type uint32;
           }
           leaf ftp-bad-ip-pkts {
             type uint32;
           }
           leaf ftp-bad-port-pkts {
             type uint32;
           }
           leaf ftp-bad-cmd-pkts {
             type uint32;
           }
         }
         container msp-alg-talk-entry {
           description "TALK ALG stats";
           leaf talk-lookup-pkts {
             type uint32;
           }
           leaf talk-announce-pkts {
             type uint32;
           }
           leaf talk-delete-pkts {
             type uint32;
           }
         }
         container msp-alg-sql-entry {
           description "SQLNET ALG statistics";
           leaf sql-rcvd-pkts {
             type uint32;
           }
           leaf sql-parse-fail-pkts {
             type uint32;
           }
           leaf sql-freed-pkts {
             type uint32;
           }
           leaf sql-gate-fail-errs {
             type uint32;
           }
         }
         container msp-alg-dce-rpc-portmap-entry {
           description "DCE-RPC-PORTMAP ALG stats";
           leaf dce-rpc-lookup-request {
             type uint32;
           }
           leaf dce-rpc-map-request {
             type uint32;
           }
           leaf dce-rpc-lookup-reply {
             type uint32;
           }
           leaf dce-rpc-map-reply {
             type uint32;
           }
           leaf dce-rpc-fail-reply {
             type uint32;
           }
         }
         container msp-alg-dce-rpc-entry {
           description "DCE-RPC ALG stats";
           leaf dce-rpc-wrong-header {
             type uint32;
           }
           leaf dce-rpc-non-epm3 {
             type uint32;
           }
           leaf dce-rpc-type-mismatch {
             type uint32;
           }
           leaf dce-rpc-id-mismatch {
             type uint32;
           }
           leaf dce-rpc-call-mismatch {
             type uint32;
           }
           leaf dce-rpc-fragment-pkts {
             type uint32;
           }
           leaf dce-rpc-queue-pkts {
             type uint32;
           }
           leaf dce-rpc-drop-pkts {
             type uint32;
           }
           leaf dce-rpc-released-pkts {
             type uint32;
           }
         }
         container msp-alg-rpc-portmap-entry {
           description "RPC-PORTMAP ALG stats";
           leaf rpc-process-fail {
             type uint32;
           }
           leaf rpc-request {
             type uint32;
           }
           leaf rpc-call-dump {
             type uint32;
           }
           leaf rpc-call-callit {
             type uint32;
           }
           leaf rpc-reply-ok {
             type uint32;
           }
           leaf rpc-reply-dump {
             type uint32;
           }
           leaf rpc-reply-callit {
             type uint32;
           }
           leaf rpc-process-reply-deny {
             type uint32;
           }
           leaf rpc-process-reply-xid-mismatch {
             type uint32;
           }
           leaf rpc-pkt-ver-error {
             type uint32;
           }
           leaf rpc-pkt-not-rpcbind {
             type uint32;
           }
         }
         container msp-alg-rpc-entry {
           description "RPC ALG stats";
           leaf rpc-call-bind-version-2 {
             type uint32;
           }
           leaf rpc-call-bind-version-3 {
             type uint32;
           }
           leaf rpc-call-bind-version-4 {
             type uint32;
           }
           leaf rpc-call-bind-version-error {
             type uint32;
           }
           leaf rpc-reply-bind-version-2 {
             type uint32;
           }
           leaf rpc-reply-bind-version-3 {
             type uint32;
           }
           leaf rpc-reply-bind-version-4 {
             type uint32;
           }
           leaf rpc-reply-bind-version-error {
             type uint32;
           }
           leaf rpc-pkt-fragmented {
             type uint32;
           }
           leaf rpc-pkt-drop {
             type uint32;
           }
           leaf rpc-pkt-release {
             type uint32;
           }
         }
         container msp-alg-sip-entry {
           description "SIP ALG stats";
           leaf active-sip-call-count {
             type uint32;
             description "Total number of active SIP calls";
           }
           leaf sip-invite-count {
             type uint32;
             description "INVITE count";
           }
           leaf sip-invite-retransmit-count {
             type uint32;
             description "INVITE retransmits count";
           }
           leaf sip-register-count {
             type uint32;
             description "REGISTER count";
           }
           leaf sip-bye-count {
             type uint32;
             description "BYE count";
           }
           leaf sip-cancel-count {
             type uint32;
             description "CANCEL count";
           }
           leaf sip-subscribe-count {
             type uint32;
             description "SUBSCRIBE count";
           }
           leaf sip-notify-count {
             type uint32;
             description "NOTIFY count";
           }
           leaf sip-options-count {
             type uint32;
             description "OPTIONS count";
           }
           leaf sip-info-count {
             type uint32;
             description "INFO count";
           }
           leaf sip-update-count {
             type uint32;
             description "UPDATE count";
           }
           leaf sip-refer-count {
             type uint32;
             description "REFER count";
           }
           leaf sip-resp-ok-to-invite-count {
             type uint32;
             description "OK response to INVITE count";
           }
           leaf sip-resp-ok-to-non-invite-count {
             type uint32;
             description "OK response to non-INVITE count";
           }
           leaf sip-resp-1xx-count {
             type uint32;
             description "1xx response count";
           }
           leaf sip-redirection-3xx-resp-count {
             type uint32;
             description "3xx response count";
           }
           leaf sip-req-failure-4xx-resp-count {
             type uint32;
             description "4xx response count";
           }
           leaf sip-server-failure-5xx-resp-count {
             type uint32;
             description "5xx response count";
           }
           leaf sip-global-failure-6xx-resp-count {
             type uint32;
             description "6xx response count";
           }
           leaf sip-resp-all-retransmits-count {
             type uint32;
             description "Response (all) retransmits";
           }
           leaf sip-pkts-drop {
             type uint32;
             description "Total number of packets dropped";
           }
           leaf sip-unexpect-req-drop {
             type uint32;
             description "Number of unexpected requests dropped";
           }
           leaf sip-unexpect-res-drop {
             type uint32;
             description "Number of unexpected responses dropped";
           }
           leaf sip-dscp-marked {
             type uint32;
             description "Number of packets of DSCP marked";
           }
           leaf sip-dscp-marked-err {
             type uint32;
             description "Number of packets of DSCP marked error";
           }
           leaf sip-nat-err {
             type uint32;
             description "Number of NAT errors";
           }
           leaf sip-rr-hdr-exceed-max {
             type uint32;
             description "Number of RR headers exceeded maximum limits";
           }
           leaf sip-contact-hdr-exceed-max {
             type uint32;
             description "Number of contact headers exceeded maximum limits";
           }
           leaf sip-invite-drop-call-limit {
             type uint32;
             description "Number of invite dropped due to call limit";
           }
           leaf sip-msgs-not-processed {
             type uint32;
             description "Number of messages not processed by sip stack";
           }
           leaf sip-unknown-pkts-drop {
             type uint32;
             description "Number of unknown packets dropped";
           }
           leaf sip-decoding-error {
             type uint32;
             description "Number of decoding errors";
           }
           leaf sip-out-of-state {
             type uint32;
             description "Number of packets received in out of state";
           }
         }
         container msp-alg-tftp-entry {
           description "TFTP ALG stats";
           leaf tftp-total-invalid-pkts {
             type uint32;
             description "Number of Invalid packets";
           }
           leaf tftp-total-sessions {
             type uint32;
             description "Total number of sessions";
           }
           leaf tftp-active-sessions {
             type uint32;
             description "Number of active sessions";
           }
         }
         container msp-alg-ike-esp-entry {
           description "IKE ESP ALG stats";
           leaf ike-esp-sess-interest {
             type uint32;
             description "Number of session interests processed";
           }
           leaf ike-esp-sess-create {
             type uint32;
             description "Number of sessions created";
           }
           leaf ike-esp-sess-destroy {
             type uint32;
             description "Number of sessions destroyed";
           }
           leaf ike-esp-ctrl-sess-create {
             type uint32;
             description "Number of control sessions created";
           }
           leaf ike-esp-ctrl-sess-destroy {
             type uint32;
             description "Number of control sessions destroyed";
           }
           leaf ike-esp-data-sess-create {
             type uint32;
             description "Number of data sessions created";
           }
           leaf ike-esp-data-sess-destroy {
             type uint32;
             description "Number of data sessions destroyed";
           }
           leaf ike-esp-gate-create {
             type uint32;
             description "Number of gates created";
           }
           leaf ike-esp-gate-hit {
             type uint32;
             description "Number of gates hit";
           }
           leaf ike-esp-gate-timeout {
             type uint32;
             description "Number of gates timedout";
           }
         }
       }
     }
   }
   rpc get-service-msp-alg-sip-globals-information {
     description "Show SIP ALG global configurations";
     input {
       leaf interface {
         description "Name of extension provider interface";
         type string;
       }
     }
     output {
       container service-msp-alg-sip-globals-information {
         leaf interface-name {
           type string;
           description "Name of the adaptive services interface";
         }
         container msp-alg-sip-globals-entry {
           description "Show SIP ALG Global configurations";
           leaf sip-max-no-calls {
             type uint32;
             description "Maximum number of calls allowed";
           }
           leaf sip-inactive-media-timeout {
             type uint32;
             description "Inactive media timeout";
           }
           leaf sip-max-call-timeout {
             type uint32;
             description "Maximum call timeout";
           }
           leaf sip-t1-interval {
             type uint32;
             description "T1 interval timeout";
           }
           leaf sip-t4-interval {
             type uint32;
             description "T4 interval timeout";
           }
           leaf sip-c-interval {
             type uint32;
             description "C interval timeout";
           }
         }
       }
     }
   }
   rpc get-service-ha-info {
     description "Show HA info and current status";
     input {
       leaf interface {
         description "Name of adaptive services interface";
         type string;
       }
       leaf level {
         default "brief";
         type enumeration {
           enum "brief" {
             description "Display brief output";
           }
           enum "detail" {
             description "Display detailed output";
           }
           enum "statistics" {
             description "Display statistics output";
           }
         }
       }
     }
     output {
       container service-ha-info {
         container brief {
           description "Show ha information";
           leaf interface-name {
             type string;
             description "Name of the adaptive services interface";
           }
           leaf ha-type {
             type string;
             description "Type of HA - Intra Chassis / Inter Chassis";
           }
           leaf ha-role {
             type string;
             description "Role of PIC in HA pair";
           }
           leaf ha-conn-status {
             type string;
             description "Connection status - Up/Down";
           }
           leaf ha-sync-type {
             type string;
             description "Sync Type";
           }
           leaf ha-local-ip {
             type string;
             description "Local IP address";
           }
           leaf ha-local-port {
             type int32;
             description "Local Port being used";
           }
           leaf ha-remote-ip {
             type string;
             description "Peer's IP address";
           }
           leaf ha-remote-port {
             type int32;
             description "Remote Port being used";
           }
         }
       }
     }
   }
   rpc get-service-flow-analysis-information {
     description "Show flow table entries";
     input {
       leaf interface {
         description "Name of adaptive services interface";
         type string;
       }
     }
     output {
       container service-flow-analysis-information {
         container service-flow-analysis-entry {
           container flow-analysis-statistics-pic-info {
             leaf pic-name {
               type string;
               description "Services PIC Name";
             }
           }
           container flow-analysis-statistics-entry {
             description "Flow Analysis Statistics";
             leaf num-total-flows-active {
               type uint32;
               description "Number of Total Flows Active";
             }
             leaf num-total-tcp-flows-active {
               type uint32;
               description "Number of Total TCP Flows Active";
             }
             leaf num-total-udp-flows-active {
               type uint32;
               description "Number of Total UDP Flows Active";
             }
             leaf num-total-other-flows-active {
               type uint32;
               description "Number of Total Other Flows Active";
             }
             leaf num-total-predicted-flows-active {
               type uint32;
               description "Number of Total Predicted Flows Active";
             }
             leaf num-total-pred-discard-flows-active {
               type uint32;
               description "Number of Total Predicted Discard Flows Active";
             }
             leaf num-created-flows-per-sec {
               type uint32;
               description "Number of Created Flows per Second";
             }
             leaf num-deleted-flows-per-sec {
               type uint32;
               description "Number of Deleted Flows per Second";
             }
             leaf peak-total-flows-active {
               type uint32;
               description "Peak Total Flows Active";
             }
             leaf peak-total-tcp-flows-active {
               type uint32;
               description "Peak Total TCP Flows Active";
             }
             leaf peak-total-udp-flows-active {
               type uint32;
               description "Peak Total UDP Flows Active";
             }
             leaf peak-total-other-flows-active {
               type uint32;
               description "Peak Total Other Flows Active";
             }
             leaf peak-created-flows-per-second {
               type uint32;
               description "Peak Created Flows per Second";
             }
             leaf peak-deleted-flows-per-second {
               type uint32;
               description "Peak Deleted Flows per Second";
             }
             leaf pkts-received {
               type uint64;
               description "Packets received";
             }
             leaf pkts-transmitted {
               type uint64;
               description "Packets transmitted";
             }
             leaf slow-path-forward {
               type uint64;
               description "Slow Path Forward";
             }
             leaf slow-path-discard {
               type uint64;
               description "Slow Path Discard";
             }
             leaf slow-path-predicted-discard {
               type uint64;
               description "Slow Path Predicted Discard";
             }
           }
           container flow-analysis-num-flows-sec-samples-entry {
             leaf num-flows-sec-samples {
               type uint32;
             }
           }
           container flow-analysis-num-flows-sec-entry {
             description "Flow Rate Statistics";
             leaf flow-operation {
               type string;
             }
             leaf num-flows-sec-300000-plus {
               type uint32;
               description "Flow setup rate is 300k or above";
             }
             leaf num-flows-sec-250000-plus {
               type uint32;
               description "Flow setup rate is 250k or above";
             }
             leaf num-flows-sec-200000-plus {
               type uint32;
               description "Flow setup rate is 200k or above";
             }
             leaf num-flows-sec-160000-plus {
               type uint32;
               description "Flow setup rate is 160k or above";
             }
             leaf num-flows-sec-150000-plus {
               type uint32;
               description "Flow setup rate is 150k or above";
             }
             leaf num-flows-sec-50000-plus {
               type uint32;
             }
             leaf num-flows-sec-40000-50000 {
               type uint32;
             }
             leaf num-flows-sec-30000-40000 {
               type uint32;
             }
             leaf num-flows-sec-20000-30000 {
               type uint32;
             }
             leaf num-flows-sec-10000-20000 {
               type uint32;
             }
             leaf num-flows-sec-1000-10000 {
               type uint32;
             }
             leaf num-flows-sec-1000-minus {
               type uint32;
             }
           }
           container flow-analysis-protocol-lifetime-entry {
             description "Flow Analysis Protocol Lifetime Statistics";
             leaf flow-lifetime-240s-plus {
               type uint64;
             }
             leaf udp-flow-lifetime-240s-plus {
               type uint64;
             }
             leaf http-flow-lifetime-240s-plus {
               type uint64;
             }
             leaf flow-lifetime-120s-240s {
               type uint64;
             }
             leaf udp-flow-lifetime-120s-240s {
               type uint64;
             }
             leaf flow-lifetime-60s-120s {
               type uint64;
             }
             leaf udp-flow-lifetime-60s-120s {
               type uint64;
             }
             leaf flow-lifetime-30s-60s {
               type uint64;
             }
             leaf udp-flow-lifetime-30s-60s {
               type uint64;
             }
             leaf flow-lifetime-15s-30s {
               type uint64;
             }
             leaf udp-flow-lifetime-15s-30s {
               type uint64;
             }
             leaf flow-lifetime-5s-15s {
               type uint64;
             }
             leaf udp-flow-lifetime-5s-15s {
               type uint64;
             }
             leaf flow-lifetime-1s-5s {
               type uint64;
             }
             leaf udp-flow-lifetime-1s-5s {
               type uint64;
             }
             leaf flow-lifetime-1s-minus {
               type uint64;
             }
             leaf udp-flow-lifetime-1s-minus {
               type uint64;
             }
           }
         }
       }
     }
   }
   rpc get-service-subs-analysis-information {
     description "Show subscriber table entries";
     input {
       leaf interface {
         description "Name of adaptive services interface";
         type string;
       }
     }
     output {
       container service-subs-analysis-information {
         container subs-analysis-statistics-pic-info {
           leaf pic-name {
             type string;
             description "Services PIC Name";
           }
         }
         container subs-analysis-statistics-entry {
           description "Subscriber Analysis Statistics";
           leaf num-total-subs-active {
             type uint32;
             description "Number of Total Subscribers Active";
           }
           leaf num-created-subs-per-sec {
             type uint32;
             description "Number of Created Subscribers per Second";
           }
           leaf num-deleted-subs-per-sec {
             type uint32;
             description "Number of Deleted Subscribers per Second";
           }
           leaf peak-total-subs-active {
             type uint32;
             description "Peak Total Subscribers Active";
           }
           leaf peak-created-subs-per-second {
             type uint32;
             description "Peak Created Subscribers per Second";
           }
           leaf peak-deleted-subs-per-second {
             type uint32;
             description "Peak Deleted Subscribers per Second";
           }
         }
         container subs-analysis-num-subs-sec-samples-entry {
           leaf num-subs-sec-samples {
             type uint32;
           }
         }
         container subs-analysis-num-subs-sec-entry {
           description "Subscriber Rate Statistics";
           leaf subs-operation {
             type string;
           }
           leaf num-subs-sec-300000-plus {
             type uint32;
             description "Subscriber setup rate is 300k or above";
           }
           leaf num-subs-sec-250000-plus {
             type uint32;
             description "Subscriber setup rate is 250k or above";
           }
           leaf num-subs-sec-200000-plus {
             type uint32;
             description "Subscriber setup rate is 200k or above";
           }
           leaf num-subs-sec-150000-plus {
             type uint32;
             description "Subscriber setup rate is 150k or above";
           }
           leaf num-subs-sec-100000-plus {
             type uint32;
             description "Subscriber setup rate is 100k or above";
           }
           leaf num-subs-sec-50000-plus {
             type uint32;
             description "Subscriber setup rate is 50k or above";
           }
           leaf num-subs-sec-40000-plus {
             type uint32;
             description "Subscriber setup rate is > 40k or above";
           }
           leaf num-subs-sec-30000-plus {
             type uint32;
             description "Subscriber setup rate is > 30k or above";
           }
           leaf num-subs-sec-20000-plus {
             type uint32;
             description "Subscriber setup rate is > 20k or above";
           }
           leaf num-subs-sec-10000-plus {
             type uint32;
             description "Subscriber setup rate is > 10k or above";
           }
           leaf num-subs-sec-1000-plus {
             type uint32;
             description "Subscriber setup rate is > 1k or above";
           }
           leaf num-subs-sec-1000-minus {
             type uint32;
             description "Subscriber setup rate is < 1k";
           }
         }
       }
     }
   }
   rpc get-service-sfw-flow-table-information {
     description "Show flow table entries";
     input {
       leaf all {
         description "Display all the entries";
         type empty;
       }
       leaf limit {
         description "Maximum number of entries to display";
         type uint32 {
           range "1 .. 4294967295";
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type uint16;
       }
       leaf destination-port {
         description "Destination port to use as filter";
         type uint16;
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
         }
       }
       leaf service-set {
         description "Name of service set";
         type string;
       }
       leaf interface {
         description "Name of adaptive services interface";
         type string;
       }
       leaf pgcp {
         description "Use pgcp flow type as filter";
         type empty;
       }
       leaf get-service-sfw-flow-count-information {
         description "Show count of matching entries";
         type empty;
       }
     }
     output {
       container service-sfw-flow-table-information {
         container sfw-per-service-set-flow-table {
           description "Flows sorted by service set";
           leaf interface-name {
             type string;
             description "Name of the adaptive services interface";
           }
           leaf service-set-name {
             type string;
             description "Name of the service set";
           }
           container service-sfw-flow-table {
             description "Stateful firewall flows";
             leaf service-sfw-flow-table.heading {
               type string;
               description "Stateful firewall flows";
             }
             container sfw-flow-entry {
               description "Flow brief information";
               leaf sfw-flow-protocol {
                 type string;
                 description "Flow protocol description";
               }
               leaf sfw-flow-source-ip {
                 type string;
                 description "Source IP address";
               }
               leaf sfw-flow-source-port {
                 type int32;
                 description "Source port address";
               }
               leaf sfw-flow-destination-ip {
                 type string;
                 description "Flow destination IP address";
               }
               leaf sfw-flow-destination-port {
                 type string;
                 description "Flow destination port";
               }
               leaf sfw-flow-state {
                 type string;
                 description "Flow state";
               }
               leaf sfw-flow-direction {
                 type string;
                 description "Flow direction";
               }
               leaf sfw-flow-frame-counter {
                 type uint64;
                 description "Number of frames transmitted";
               }
               leaf sfw-flow-gate-id {
                 type uint64;
                 description "PGCP gate-id";
               }
               leaf sfw-flow-table-byte-count {
                 type uint64;
                 description "Flow byte count";
               }
               leaf sfw-flow-table-tcp-window-size {
                 type uint64;
                 description "TCP protocol window size";
               }
               leaf sfw-flow-table-tcp-acknowledge {
                 type uint64;
                 description "TCP protocol acknowledge";
               }
               leaf sfw-flow-table-tcp-tickle {
                 type uint64;
                 description "Time between TCP tickles (seconds)";
               }
               leaf sfw-flow-table-role {
                 type string;
                 description "Role of flow in conversation";
               }
               leaf sfw-flow-table-timeout {
                 type uint64;
                 description "Timeout value of flow (seconds)";
               }
               leaf sfw-flow-table-protocol-detail {
                 type string;
                 description "Flow protocol detail information";
               }
               container sfw-flow-nat {
                 description "NAT translation";
                 leaf sfw-flow-nat-type {
                   type string;
                   description "Type of NAT translation";
                 }
                 leaf sfw-flow-nat-ip {
                   type string;
                   description "Original IP address";
                 }
                 leaf sfw-flow-nat-port {
                   type string;
                   description "Original port";
                 }
                 leaf sfw-flow-translated-ip {
                   type string;
                   description "Translated IP address";
                 }
                 leaf sfw-flow-translated-port {
                   type string;
                   description "Translated port";
                 }
               }
             }
           }
         }
       }
     }
   }
   rpc get-service-sfw-conversation-information {
     description "Show conversations";
     input {
       leaf all {
         description "Display all the entries";
         type empty;
       }
       leaf limit {
         description "Maximum number of entries to display";
         type uint32 {
           range "1 .. 4294967295";
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type uint16;
       }
       leaf destination-port {
         description "Destination port to use as filter";
         type uint16;
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
         }
       }
       leaf service-set {
         description "Name of service set";
         type string;
       }
       leaf interface {
         description "Name of adaptive services interface";
         type string;
       }
       leaf pgcp {
         description "Use pgcp flow type as filter";
         type empty;
       }
     }
     output {
       container service-sfw-conversation-information {
         container sfw-per-service-set-conversation {
           description "Show conversations";
           leaf interface-name {
             type string;
             description "Name of the adaptive services interface";
           }
           leaf service-set-name {
             type string;
             description "Name of the service set";
           }
           container sfw-conversation {
             description "Stateful firewall conversations";
             leaf sfw-flow-table-conv-alg {
               type string;
               description "Application Protocol Gateway protocol";
             }
             leaf sfw-flow-table-conv-initiator {
               type int32;
               description "Number of initiator flows";
             }
             leaf sfw-flow-table-conv-responder {
               type int32;
               description "Number of responder flows";
             }
             container service-sfw-flow-table {
               description "Stateful firewall flows";
               leaf service-sfw-flow-table.heading {
                 type string;
                 description "Stateful firewall flows";
               }
               container sfw-flow-entry {
                 description "Flow brief information";
                 leaf sfw-flow-protocol {
                   type string;
                   description "Flow protocol description";
                 }
                 leaf sfw-flow-source-ip {
                   type string;
                   description "Source IP address";
                 }
                 leaf sfw-flow-source-port {
                   type int32;
                   description "Source port address";
                 }
                 leaf sfw-flow-destination-ip {
                   type string;
                   description "Flow destination IP address";
                 }
                 leaf sfw-flow-destination-port {
                   type string;
                   description "Flow destination port";
                 }
                 leaf sfw-flow-state {
                   type string;
                   description "Flow state";
                 }
                 leaf sfw-flow-direction {
                   type string;
                   description "Flow direction";
                 }
                 leaf sfw-flow-frame-counter {
                   type uint64;
                   description "Number of frames transmitted";
                 }
                 leaf sfw-flow-gate-id {
                   type uint64;
                   description "PGCP gate-id";
                 }
                 leaf sfw-flow-table-byte-count {
                   type uint64;
                   description "Flow byte count";
                 }
                 leaf sfw-flow-table-tcp-window-size {
                   type uint64;
                   description "TCP protocol window size";
                 }
                 leaf sfw-flow-table-tcp-acknowledge {
                   type uint64;
                   description "TCP protocol acknowledge";
                 }
                 leaf sfw-flow-table-tcp-tickle {
                   type uint64;
                   description "Time between TCP tickles (seconds)";
                 }
                 leaf sfw-flow-table-role {
                   type string;
                   description "Role of flow in conversation";
                 }
                 leaf sfw-flow-table-timeout {
                   type uint64;
                   description "Timeout value of flow (seconds)";
                 }
                 leaf sfw-flow-table-protocol-detail {
                   type string;
                   description "Flow protocol detail information";
                 }
                 container sfw-flow-nat {
                   description "NAT translation";
                   leaf sfw-flow-nat-type {
                     type string;
                     description "Type of NAT translation";
                   }
                   leaf sfw-flow-nat-ip {
                     type string;
                     description "Original IP address";
                   }
                   leaf sfw-flow-nat-port {
                     type string;
                     description "Original port";
                   }
                   leaf sfw-flow-translated-ip {
                     type string;
                     description "Translated IP address";
                   }
                   leaf sfw-flow-translated-port {
                     type string;
                     description "Translated port";
                   }
                 }
               }
             }
           }
         }
       }
     }
   }
   rpc get-service-sfw-sip-call-information {
     description "Show SIP call information";
     input {
       leaf all {
         description "Display all the entries";
         type empty;
       }
       leaf limit {
         description "Maximum number of entries to display";
         type uint32 {
           range "1 .. 4294967295";
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type uint16;
       }
       leaf destination-port {
         description "Destination port to use as filter";
         type uint16;
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
         }
       }
       leaf service-set {
         description "Name of service set";
         type string;
       }
       leaf interface {
         description "Name of adaptive services interface";
         type string;
       }
       leaf get-service-sfw-sip-call-count-information {
         description "Show count of matching entries";
         type empty;
       }
     }
     output {
       container service-sfw-sip-call-information {
         container sfw-per-service-set-sip-calls {
           description "Stateful firewall SIP calls sorted by service set";
           leaf interface-name {
             type string;
             description "Name of the adaptive services interface";
           }
           leaf service-set-name {
             type string;
             description "Name of the service set";
           }
           container sfw-sip-calls {
             container sfw-sip-call-entry {
               description "Session Initiation Protocol call";
               leaf sfw-sip-from {
                 type string;
                 description "SIP invite from";
               }
               leaf sfw-sip-to {
                 type string;
                 description "SIP invite to";
               }
               leaf sfw-sip-callid {
                 type string;
                 description "SIP call ID";
               }
               leaf sfw-sip-number-control-iflows {
                 type int32;
                 description "Number of SIP Control initiator flows";
               }
               leaf sfw-sip-number-control-rflows {
                 type int32;
                 description "Number of SIP control responder flows";
               }
               leaf sfw-sip-number-contact-iflows {
                 type int32;
                 description "Number of SIP contact initiator flows";
               }
               leaf sfw-sip-number-contact-rflows {
                 type int32;
                 description "Number of SIP contact responder flows";
               }
               leaf sfw-sip-number-media-iflows {
                 type int32;
                 description "Number of SIP media initiator flows";
               }
               leaf sfw-sip-number-media-rflows {
                 type int32;
                 description "Number of SIP media responder flows";
               }
             }
           }
         }
       }
     }
   }
   rpc get-service-sfw-sip-register-information {
     description "Show SIP register information";
     input {
       leaf all {
         description "Display all the entries";
         type empty;
       }
       leaf limit {
         description "Maximum number of entries to display";
         type uint32 {
           range "1 .. 4294967295";
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type uint16;
       }
       leaf destination-port {
         description "Destination port to use as filter";
         type uint16;
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
         }
       }
       leaf service-set {
         description "Name of service set";
         type string;
       }
       leaf interface {
         description "Name of adaptive services interface";
         type string;
       }
       leaf get-service-sfw-sip-register-count-information {
         description "Show count of matching entries";
         type empty;
       }
     }
   }
   rpc get-service-sfw-statistics-information {
     description "Show statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
       leaf service-set {
         description "Name of service set";
         type string;
       }
       leaf interface {
         description "Name of adaptive services interface";
         type string;
       }
     }
     output {
       container service-sfw-statistics-information {
         container summary {
           description "Stateful firewall statistics information";
           container service-sfw-statistics-entry {
             description "Stateful firewall statistics entry";
             leaf interface-name {
               type string;
               description "Name of the adaptive services interface";
             }
             container sfw-stats-service-set-entry {
               description "Stateful firewall service set statistics entry";
               container new-flow-counters {
                 description "New flow counters";
                 leaf new-flow-accepts {
                   type uint32;
                   description "Packets accepted by new flows";
                 }
                 leaf new-flow-discards {
                   type uint32;
                   description "Packets discarded by new flows";
                 }
                 leaf new-flow-rejects {
                   type uint32;
                   description "Packets rejected by new flows";
                 }
               }
               container existing-flow-counters {
                 description "Existing flow counters";
                 leaf existing-flow-accepts {
                   type uint32;
                   description "Packets accepted by existing accept flow";
                 }
                 leaf existing-flow-discards {
                   type uint32;
                   description "Packets discarded by existing drop flow";
                 }
                 leaf existing-flow-rejects {
                   type uint32;
                   description "Packets rejected by existing reject flow";
                 }
               }
               container hairpinning-counters {
                 description "Hairpinned packets count";
                 leaf slow-path-hairpinned-packets {
                   type uint32;
                   description "Initiator packets for Hairpinning";
                 }
                 leaf fast-path-hairpinned-packets {
                   type uint32;
                   description "Packets recieved on existing Hairpinned flows";
                 }
               }
               container drop_counters {
                 description "Drop counters (rules or resource exhaustion)";
                 leaf ip-option {
                   type uint32;
                   description "IP option drops";
                 }
                 leaf syn-defense {
                   type uint32;
                   description "Incomplete TCP handshakes";
                 }
                 leaf nat-ports-exhausted {
                   type uint32;
                   description "NAT ports exhausted";
                 }
                 leaf subs-flow-limit-exceeded {
                   type uint32;
                   description "Subscriber flow limit exceeded";
                 }
               }
               container error-counters {
                 description "Summarized protocol processing errors";
                 leaf ip-errors {
                   type uint32;
                   description "IP processing errors";
                 }
                 leaf tcp-errors {
                   type uint32;
                   description "TCP processing errors";
                 }
                 leaf udp-errors {
                   type uint32;
                   description "UDP processing errors";
                 }
                 leaf icmp-errors {
                   type uint32;
                   description "ICMP processing errors";
                 }
                 leaf non-ip-packets {
                   type uint32;
                   description "Non-IP packets";
                 }
                 leaf alg-errors {
                   type uint32;
                   description "ALG processing errors";
                 }
               }
               container ip-error-counters {
                 description "Extensive output of IP processing errors";
                 leaf ip-length-error {
                   type uint32;
                   description "IP packet length inconsistencies";
                 }
                 leaf ip-header-length-error {
                   type uint32;
                   description "Minimum IP header length check failures";
                 }
                 leaf long-packet {
                   type uint32;
                   description "Reassembled packet exceeds maximum IP length (65,535 bytes)";
                 }
                 leaf illegal-destination-address {
                   type uint32;
                   description "Illegal destination address";
                 }
                 leaf illegal-source-address {
                   type uint32;
                   description "Illegal source address";
                 }
                 leaf ttl-zero {
                   type uint32;
                   description "IP packets received with a TTL value of 0";
                 }
                 leaf illegal-ip-protocol {
                   type uint32;
                   description "Illegal IP protocol number ";
                 }
                 leaf non-ipv6 {
                   type uint32;
                   description "Non-IPv6 packets";
                 }
                 leaf land-attack {
                   type uint32;
                   description "IP source address same as destination address";
                 }
                 leaf not-ip-packet {
                   type uint32;
                   description "Not IP Packet";
                 }
                 leaf non-ipv4 {
                   type uint32;
                   description "Non-IPv4 packets";
                 }
                 leaf bad-checksum {
                   type uint32;
                   description "Bad checksum";
                 }
                 leaf illegal-fragment-length {
                   type uint32;
                   description "Illegal IP fragment length";
                 }
                 leaf fragment-overlap {
                   type uint32;
                   description "IP fragment overlap";
                 }
                 leaf fragment-reassembly-timeout {
                   type uint32;
                   description "IP fragment reassembly timeout";
                 }
                 leaf fragment-limit-exceeded {
                   type uint32;
                   description "IP fragment limit exceeded";
                 }
                 leaf unknown {
                   type uint32;
                   description "Unknown errors";
                 }
               }
               container tcp-error-counters {
                 description "Extensive output of TCP processing errors";
                 leaf tcp-header-length-error {
                   type uint32;
                   description "TCP header length inconsistencies";
                 }
                 leaf tcp-zero-port {
                   type uint32;
                   description "Source or destination port number is zero";
                 }
                 leaf illegal-sequence-number-flags {
                   type uint32;
                   description "Illegal sequence number and flags combinations";
                 }
                 leaf syn-attack {
                   type uint32;
                   description "SYN attack";
                 }
                 leaf non-syn-first-packet {
                   type uint32;
                   description "First packet not a SYN message";
                 }
                 leaf tcp-port-scan {
                   type uint32;
                   description "TCP port scan";
                 }
                 leaf bad-syn-cookie-response {
                   type uint32;
                   description "Bad SYN cookie response";
                 }
                 leaf tcp-recon-sequence-number-error {
                   type uint32;
                   description "TCP reconstructor sequence number error";
                 }
                 leaf tcp-recon-retransmits {
                   type uint32;
                   description "TCP reconstructor retransmissions";
                 }
                 leaf tcp-partially-opened-connection-timeout-syn-rcvd {
                   type uint32;
                   description "TCP partially opened connection timeout";
                 }
                 leaf tcp-partially-opened-connection-timeout-syn-ack-rcvd {
                   type uint32;
                   description "TCP partially opened connection timeout";
                 }
                 leaf tcp-partially-closed-connection-reuse {
                   type uint32;
                   description "TCP partially closed connection reuse";
                 }
                 leaf tcp-3way-error-client-sent-syn-ack {
                   type uint32;
                   description "TCP 3-way error - client sent SYN+ACK";
                 }
                 leaf tcp-3way-error-server-sent-ack {
                   type uint32;
                   description "TCP 3-way error - server sent ACK";
                 }
                 leaf tcp-3way-error-syn-seq-num-retrans-mismatch {
                   type uint32;
                   description "TCP 3-way error - SYN seq number retransmission mismatch";
                 }
                 leaf tcp-3way-error-rst-seq-num-mismatch {
                   type uint32;
                   description "TCP 3-way error - RST seq number mismatch";
                 }
                 leaf tcp-3way-error-fin-received {
                   type uint32;
                   description "TCP 3-way error - FIN received";
                 }
                 leaf tcp-3way-error-invalid-flags {
                   type uint32;
                   description "TCP 3-way error - invalid TCP flag combination";
                 }
                 leaf tcp-3way-error-syn-no-flow-initiator {
                   type uint32;
                   description "TCP 3-way error - SYN recvd but no client flows";
                 }
                 leaf tcp-3way-error-first-packet-syn-ack {
                   type uint32;
                   description "TCP 3-way error - first packet SYN+ACK";
                 }
                 leaf tcp-3way-error-first-packet-fin-ack {
                   type uint32;
                   description "TCP 3-way error - first packet FIN+ACK";
                 }
                 leaf tcp-3way-error-first-packet-fin {
                   type uint32;
                   description "TCP 3-way error - first packet FIN";
                 }
                 leaf tcp-3way-error-first-packet-rst {
                   type uint32;
                   description "TCP 3-way error - first packet RST";
                 }
                 leaf tcp-3way-error-first-packet-ack {
                   type uint32;
                   description "TCP 3-way error - first packet ack";
                 }
                 leaf tcp-3way-error-first-packet-invalid-flags {
                   type uint32;
                   description "TCP 3-way error - first packet ack";
                 }
                 leaf tcp-close-error-no-final-ack {
                   type uint32;
                   description "TCP close error - no final ack";
                 }
                 leaf tcp-resumed-flow {
                   type uint32;
                   description "TCP Resumed Flow";
                 }
               }
               container udp-error-counters {
                 description "Extensive output of UDP processing errors";
                 leaf udp-header-length-error {
                   type uint32;
                   description "IP data length is less than minimum UDP header length (8 bytes)";
                 }
                 leaf udp-zero-port {
                   type uint32;
                   description "Source or destination port number is zero";
                 }
                 leaf udp-port-scan {
                   type uint32;
                   description "UDP port scan (ICMP error seen for UDP flow)";
                 }
               }
               container icmp-error-counters {
                 description "Extensive output of ICMP processing errors";
                 leaf icmp-length-error {
                   type uint32;
                   description "IP data length less than minimum ICMP header length (8 bytes)";
                 }
                 leaf icmp-error-length-error {
                   type uint32;
                   description "ICMP error length inconsistencies";
                 }
                 leaf ping-duplicate-sequence-number {
                   type uint32;
                   description "Duplicate ping sequence number";
                 }
                 leaf ping-mismatched-sequence-number {
                   type uint32;
                   description "Mismatched ping sequence number";
                 }
                 leaf icmp-error-no-matching-flow {
                   type uint32;
                   description "No matching flow for ICMP error packet";
                 }
               }
               container alg-error-counters {
                 description "Extensive output of ALG processing errors";
                 leaf alg-bootp-errors {
                   type uint32;
                   description "ALG BOOTP errors";
                 }
                 leaf alg-dce-rpc-errors {
                   type uint32;
                   description "ALG DCE-RPC errors";
                 }
                 leaf alg-dce-rpc-portmap-errors {
                   type uint32;
                   description "ALG DCE-RPC portmap errors";
                 }
                 leaf alg-dns-errors {
                   type uint32;
                   description "ALG DNS errors";
                 }
                 leaf alg-exec-errors {
                   type uint32;
                   description "ALG exec errors";
                 }
                 leaf alg-ftp-errors {
                   type uint32;
                   description "ALG FTP errors";
                 }
                 leaf alg-h323-errors {
                   type uint32;
                   description "ALG H323 errors";
                 }
                 leaf alg-icmp-errors {
                   type uint32;
                   description "ALG ICMP errors";
                 }
                 leaf alg-iiop-errors {
                   type uint32;
                   description "ALG IIOP errors";
                 }
                 leaf alg-login-errors {
                   type uint32;
                   description "ALG login errors";
                 }
                 leaf alg-netbios-errors {
                   type uint32;
                   description "ALG NetBIOS errors";
                 }
                 leaf alg-netshow-errors {
                   type uint32;
                   description "ALG NetShow errors";
                 }
                 leaf alg-realaudio-errors {
                   type uint32;
                   description "ALG Real Audio errors";
                 }
                 leaf alg-rpc-errors {
                   type uint32;
                   description "ALG RPC errors";
                 }
                 leaf alg-rpc-portmap-errors {
                   type uint32;
                   description "ALG RPC portmap errors";
                 }
                 leaf alg-rtsp-errors {
                   type uint32;
                   description "ALG Real-Time Streaming Protocol errors";
                 }
                 leaf alg-shell-errors {
                   type uint32;
                   description "ALG shell errors";
                 }
                 leaf alg-sip-errors {
                   type uint32;
                   description "ALG Session Initiation Protocol errors";
                 }
                 leaf alg-snmp-errors {
                   type uint32;
                   description "ALG SNMP errors";
                 }
                 leaf alg-sqlnet-errors {
                   type uint32;
                   description "ALG SQLNet errors";
                 }
                 leaf alg-tftp-errors {
                   type uint32;
                   description "ALG TFTP errors";
                 }
                 leaf alg-traceroute-errors {
                   type uint32;
                   description "ALG traceroute errors";
                 }
               }
               container sip-alg-counters {
                 description "SIP statistics";
                 container alg-sip {
                   description "SIP statistics";
                   container total-counters {
                     description "Total statistics";
                     leaf total-messages {
                       type uint32;
                       description "Total SIP messages";
                     }
                     leaf call-segments {
                       type uint32;
                       description "SIP call segments";
                     }
                   }
                   container parser-counters {
                     description "Parser statistics";
                     leaf syntax-errors {
                       type uint32;
                       description "SIP syntax errors";
                     }
                     leaf content-errors {
                       type uint32;
                       description "SIP message content errors";
                     }
                     leaf unknown-methods {
                       type uint32;
                       description "SIP unknown methods";
                     }
                   }
                   container message-counters {
                     description "SIP message counters";
                     leaf response-provisional {
                       type uint32;
                       description "Number of provisional responses";
                     }
                     leaf response-invite-ok {
                       type uint32;
                       description "Number of 'OK' responses to INVITE messages";
                     }
                     leaf response-non-invite-ok {
                       type uint32;
                       description "Number of 'OK' responses to messages other than INVITE";
                     }
                     leaf response-redir {
                       type uint32;
                       description "Number of redirection (3xx) responses";
                     }
                     leaf response-request-failure {
                       type uint32;
                       description "Number of request failure (4xx) responses";
                     }
                     leaf response-server-failure {
                       type uint32;
                       description "Number of server failure (5xx) responses";
                     }
                     leaf response-global-failure {
                       type uint32;
                       description "Number of global failure (6xx) responses";
                     }
                     leaf response-invalid {
                       type uint32;
                       description "Number of invalid responses";
                     }
                     leaf response-retransmits {
                       type uint32;
                       description "Number of response retransmissions";
                     }
                     leaf register-new {
                       type uint32;
                       description "Number of REGISTER messages";
                     }
                     leaf invite-new {
                       type uint32;
                       description "Number of new INVITE messages";
                     }
                     leaf invite-retransmits {
                       type uint32;
                       description "Number of INVITE message retransmissions";
                     }
                     leaf reinvites {
                       type uint32;
                       description "Number of ReINVITE messages";
                     }
                     leaf cancel-valid {
                       type uint32;
                       description "Number of valid CANCEL messages";
                     }
                     leaf cancel-invalid {
                       type uint32;
                       description "Number of invalid CANCEL messages";
                     }
                     leaf ack-valid {
                       type uint32;
                       description "Number of valid ACK messages";
                     }
                     leaf ack-invalid {
                       type uint32;
                       description "Number of invalid ACK messages";
                     }
                     leaf ack-retransmits {
                       type uint32;
                       description "Number of ACK message retransmissions";
                     }
                     leaf bye-valid {
                       type uint32;
                       description "Number of valid BYE messages";
                     }
                     leaf bye-invalid {
                       type uint32;
                       description "Number of invalid BYE messages";
                     }
                     leaf subscribe-valid {
                       type uint32;
                       description "Number of valid SUBSCRIBE messages";
                     }
                     leaf subscribe-invalid {
                       type uint32;
                       description "Number of invalid SUBSCRIBE messages";
                     }
                     leaf notify-valid {
                       type uint32;
                       description "Number of valid NOTIFY messages";
                     }
                     leaf notify-invalid {
                       type uint32;
                       description "Number of invalid NOTIFY messages";
                     }
                     leaf message-valid {
                       type uint32;
                       description "Number of valid MESSAGE messages";
                     }
                     leaf message-invalid {
                       type uint32;
                       description "Number of invalid MESSAGE messages";
                     }
                     leaf options-valid {
                       type uint32;
                       description "Number of valid OPTIONS messages";
                     }
                     leaf options-invalid {
                       type uint32;
                       description "Number of invalid OPTIONS messages";
                     }
                     leaf info-valid {
                       type uint32;
                       description "Number of valid INFO messages";
                     }
                     leaf info-invalid {
                       type uint32;
                       description "Number of invalid INFO messages";
                     }
                     leaf update-valid {
                       type uint32;
                       description "Number of valid UPDATE messages";
                     }
                     leaf update-invalid {
                       type uint32;
                       description "Number of invalid UPDATE messages";
                     }
                     leaf refer-valid {
                       type uint32;
                       description "Number of valid REFER messages";
                     }
                     leaf refer-invalid {
                       type uint32;
                       description "Number of invalid REFER messages";
                     }
                   }
                 }
               }
               container drop-flows {
                 description "Drop flow statistics";
                 leaf max-ingress-drop-flows {
                   type string;
                   description "Maximum ingress drop flows allowed";
                 }
                 leaf max-egress-drop-flows {
                   type string;
                   description "Maximum egress drop flows allowed";
                 }
                 container drop-flows-counters {
                   leaf current-ingress-drop-flows {
                     type int32;
                     description "Current ingress drop flows count";
                   }
                   leaf current-egress-drop-flows {
                     type int32;
                     description "Current egress drop flows count";
                   }
                   leaf ingress-drop-flowlimit-drops {
                     type uint32;
                     description "Drops because ingress drop flow limit is reached";
                   }
                   leaf egress-drop-flowlimit-drops {
                     type uint32;
                     description "Drops because egress drop flow limit is reached";
                   }
                 }
               }
             }
           }
         }
         container brief {
           description "Stateful firewall statistics information";
           container service-sfw-statistics-entry {
             description "Stateful firewall statistics entry";
             leaf interface-name {
               type string;
               description "Name of the adaptive services interface";
             }
             container sfw-stats-service-set-entry {
               description "Stateful firewall service set statistics entry";
               container new-flow-counters {
                 description "New flow counters";
                 leaf new-flow-accepts {
                   type uint32;
                   description "Packets accepted by new flows";
                 }
                 leaf new-flow-discards {
                   type uint32;
                   description "Packets discarded by new flows";
                 }
                 leaf new-flow-rejects {
                   type uint32;
                   description "Packets rejected by new flows";
                 }
               }
               container existing-flow-counters {
                 description "Existing flow counters";
                 leaf existing-flow-accepts {
                   type uint32;
                   description "Packets accepted by existing accept flow";
                 }
                 leaf existing-flow-discards {
                   type uint32;
                   description "Packets discarded by existing drop flow";
                 }
                 leaf existing-flow-rejects {
                   type uint32;
                   description "Packets rejected by existing reject flow";
                 }
               }
               container hairpinning-counters {
                 description "Hairpinned packets count";
                 leaf slow-path-hairpinned-packets {
                   type uint32;
                   description "Initiator packets for Hairpinning";
                 }
                 leaf fast-path-hairpinned-packets {
                   type uint32;
                   description "Packets recieved on existing Hairpinned flows";
                 }
               }
               container drop_counters {
                 description "Drop counters (rules or resource exhaustion)";
                 leaf ip-option {
                   type uint32;
                   description "IP option drops";
                 }
                 leaf syn-defense {
                   type uint32;
                   description "Incomplete TCP handshakes";
                 }
                 leaf nat-ports-exhausted {
                   type uint32;
                   description "NAT ports exhausted";
                 }
                 leaf subs-flow-limit-exceeded {
                   type uint32;
                   description "Subscriber flow limit exceeded";
                 }
               }
               container error-counters {
                 description "Summarized protocol processing errors";
                 leaf ip-errors {
                   type uint32;
                   description "IP processing errors";
                 }
                 leaf tcp-errors {
                   type uint32;
                   description "TCP processing errors";
                 }
                 leaf udp-errors {
                   type uint32;
                   description "UDP processing errors";
                 }
                 leaf icmp-errors {
                   type uint32;
                   description "ICMP processing errors";
                 }
                 leaf non-ip-packets {
                   type uint32;
                   description "Non-IP packets";
                 }
                 leaf alg-errors {
                   type uint32;
                   description "ALG processing errors";
                 }
               }
               container ip-error-counters {
                 description "Extensive output of IP processing errors";
                 leaf ip-length-error {
                   type uint32;
                   description "IP packet length inconsistencies";
                 }
                 leaf ip-header-length-error {
                   type uint32;
                   description "Minimum IP header length check failures";
                 }
                 leaf long-packet {
                   type uint32;
                   description "Reassembled packet exceeds maximum IP length (65,535 bytes)";
                 }
                 leaf illegal-destination-address {
                   type uint32;
                   description "Illegal destination address";
                 }
                 leaf illegal-source-address {
                   type uint32;
                   description "Illegal source address";
                 }
                 leaf ttl-zero {
                   type uint32;
                   description "IP packets received with a TTL value of 0";
                 }
                 leaf illegal-ip-protocol {
                   type uint32;
                   description "Illegal IP protocol number ";
                 }
                 leaf non-ipv6 {
                   type uint32;
                   description "Non-IPv6 packets";
                 }
                 leaf land-attack {
                   type uint32;
                   description "IP source address same as destination address";
                 }
                 leaf not-ip-packet {
                   type uint32;
                   description "Not IP Packet";
                 }
                 leaf non-ipv4 {
                   type uint32;
                   description "Non-IPv4 packets";
                 }
                 leaf bad-checksum {
                   type uint32;
                   description "Bad checksum";
                 }
                 leaf illegal-fragment-length {
                   type uint32;
                   description "Illegal IP fragment length";
                 }
                 leaf fragment-overlap {
                   type uint32;
                   description "IP fragment overlap";
                 }
                 leaf fragment-reassembly-timeout {
                   type uint32;
                   description "IP fragment reassembly timeout";
                 }
                 leaf fragment-limit-exceeded {
                   type uint32;
                   description "IP fragment limit exceeded";
                 }
                 leaf unknown {
                   type uint32;
                   description "Unknown errors";
                 }
               }
               container tcp-error-counters {
                 description "Extensive output of TCP processing errors";
                 leaf tcp-header-length-error {
                   type uint32;
                   description "TCP header length inconsistencies";
                 }
                 leaf tcp-zero-port {
                   type uint32;
                   description "Source or destination port number is zero";
                 }
                 leaf illegal-sequence-number-flags {
                   type uint32;
                   description "Illegal sequence number and flags combinations";
                 }
                 leaf syn-attack {
                   type uint32;
                   description "SYN attack";
                 }
                 leaf non-syn-first-packet {
                   type uint32;
                   description "First packet not a SYN message";
                 }
                 leaf tcp-port-scan {
                   type uint32;
                   description "TCP port scan";
                 }
                 leaf bad-syn-cookie-response {
                   type uint32;
                   description "Bad SYN cookie response";
                 }
                 leaf tcp-recon-sequence-number-error {
                   type uint32;
                   description "TCP reconstructor sequence number error";
                 }
                 leaf tcp-recon-retransmits {
                   type uint32;
                   description "TCP reconstructor retransmissions";
                 }
                 leaf tcp-partially-opened-connection-timeout-syn-rcvd {
                   type uint32;
                   description "TCP partially opened connection timeout";
                 }
                 leaf tcp-partially-opened-connection-timeout-syn-ack-rcvd {
                   type uint32;
                   description "TCP partially opened connection timeout";
                 }
                 leaf tcp-partially-closed-connection-reuse {
                   type uint32;
                   description "TCP partially closed connection reuse";
                 }
                 leaf tcp-3way-error-client-sent-syn-ack {
                   type uint32;
                   description "TCP 3-way error - client sent SYN+ACK";
                 }
                 leaf tcp-3way-error-server-sent-ack {
                   type uint32;
                   description "TCP 3-way error - server sent ACK";
                 }
                 leaf tcp-3way-error-syn-seq-num-retrans-mismatch {
                   type uint32;
                   description "TCP 3-way error - SYN seq number retransmission mismatch";
                 }
                 leaf tcp-3way-error-rst-seq-num-mismatch {
                   type uint32;
                   description "TCP 3-way error - RST seq number mismatch";
                 }
                 leaf tcp-3way-error-fin-received {
                   type uint32;
                   description "TCP 3-way error - FIN received";
                 }
                 leaf tcp-3way-error-invalid-flags {
                   type uint32;
                   description "TCP 3-way error - invalid TCP flag combination";
                 }
                 leaf tcp-3way-error-syn-no-flow-initiator {
                   type uint32;
                   description "TCP 3-way error - SYN recvd but no client flows";
                 }
                 leaf tcp-3way-error-first-packet-syn-ack {
                   type uint32;
                   description "TCP 3-way error - first packet SYN+ACK";
                 }
                 leaf tcp-3way-error-first-packet-fin-ack {
                   type uint32;
                   description "TCP 3-way error - first packet FIN+ACK";
                 }
                 leaf tcp-3way-error-first-packet-fin {
                   type uint32;
                   description "TCP 3-way error - first packet FIN";
                 }
                 leaf tcp-3way-error-first-packet-rst {
                   type uint32;
                   description "TCP 3-way error - first packet RST";
                 }
                 leaf tcp-3way-error-first-packet-ack {
                   type uint32;
                   description "TCP 3-way error - first packet ack";
                 }
                 leaf tcp-3way-error-first-packet-invalid-flags {
                   type uint32;
                   description "TCP 3-way error - first packet ack";
                 }
                 leaf tcp-close-error-no-final-ack {
                   type uint32;
                   description "TCP close error - no final ack";
                 }
                 leaf tcp-resumed-flow {
                   type uint32;
                   description "TCP Resumed Flow";
                 }
               }
               container udp-error-counters {
                 description "Extensive output of UDP processing errors";
                 leaf udp-header-length-error {
                   type uint32;
                   description "IP data length is less than minimum UDP header length (8 bytes)";
                 }
                 leaf udp-zero-port {
                   type uint32;
                   description "Source or destination port number is zero";
                 }
                 leaf udp-port-scan {
                   type uint32;
                   description "UDP port scan (ICMP error seen for UDP flow)";
                 }
               }
               container icmp-error-counters {
                 description "Extensive output of ICMP processing errors";
                 leaf icmp-length-error {
                   type uint32;
                   description "IP data length less than minimum ICMP header length (8 bytes)";
                 }
                 leaf icmp-error-length-error {
                   type uint32;
                   description "ICMP error length inconsistencies";
                 }
                 leaf ping-duplicate-sequence-number {
                   type uint32;
                   description "Duplicate ping sequence number";
                 }
                 leaf ping-mismatched-sequence-number {
                   type uint32;
                   description "Mismatched ping sequence number";
                 }
                 leaf icmp-error-no-matching-flow {
                   type uint32;
                   description "No matching flow for ICMP error packet";
                 }
               }
               container alg-error-counters {
                 description "Extensive output of ALG processing errors";
                 leaf alg-bootp-errors {
                   type uint32;
                   description "ALG BOOTP errors";
                 }
                 leaf alg-dce-rpc-errors {
                   type uint32;
                   description "ALG DCE-RPC errors";
                 }
                 leaf alg-dce-rpc-portmap-errors {
                   type uint32;
                   description "ALG DCE-RPC portmap errors";
                 }
                 leaf alg-dns-errors {
                   type uint32;
                   description "ALG DNS errors";
                 }
                 leaf alg-exec-errors {
                   type uint32;
                   description "ALG exec errors";
                 }
                 leaf alg-ftp-errors {
                   type uint32;
                   description "ALG FTP errors";
                 }
                 leaf alg-h323-errors {
                   type uint32;
                   description "ALG H323 errors";
                 }
                 leaf alg-icmp-errors {
                   type uint32;
                   description "ALG ICMP errors";
                 }
                 leaf alg-iiop-errors {
                   type uint32;
                   description "ALG IIOP errors";
                 }
                 leaf alg-login-errors {
                   type uint32;
                   description "ALG login errors";
                 }
                 leaf alg-netbios-errors {
                   type uint32;
                   description "ALG NetBIOS errors";
                 }
                 leaf alg-netshow-errors {
                   type uint32;
                   description "ALG NetShow errors";
                 }
                 leaf alg-realaudio-errors {
                   type uint32;
                   description "ALG Real Audio errors";
                 }
                 leaf alg-rpc-errors {
                   type uint32;
                   description "ALG RPC errors";
                 }
                 leaf alg-rpc-portmap-errors {
                   type uint32;
                   description "ALG RPC portmap errors";
                 }
                 leaf alg-rtsp-errors {
                   type uint32;
                   description "ALG Real-Time Streaming Protocol errors";
                 }
                 leaf alg-shell-errors {
                   type uint32;
                   description "ALG shell errors";
                 }
                 leaf alg-sip-errors {
                   type uint32;
                   description "ALG Session Initiation Protocol errors";
                 }
                 leaf alg-snmp-errors {
                   type uint32;
                   description "ALG SNMP errors";
                 }
                 leaf alg-sqlnet-errors {
                   type uint32;
                   description "ALG SQLNet errors";
                 }
                 leaf alg-tftp-errors {
                   type uint32;
                   description "ALG TFTP errors";
                 }
                 leaf alg-traceroute-errors {
                   type uint32;
                   description "ALG traceroute errors";
                 }
               }
               container sip-alg-counters {
                 description "SIP statistics";
                 container alg-sip {
                   description "SIP statistics";
                   container total-counters {
                     description "Total statistics";
                     leaf total-messages {
                       type uint32;
                       description "Total SIP messages";
                     }
                     leaf call-segments {
                       type uint32;
                       description "SIP call segments";
                     }
                   }
                   container parser-counters {
                     description "Parser statistics";
                     leaf syntax-errors {
                       type uint32;
                       description "SIP syntax errors";
                     }
                     leaf content-errors {
                       type uint32;
                       description "SIP message content errors";
                     }
                     leaf unknown-methods {
                       type uint32;
                       description "SIP unknown methods";
                     }
                   }
                   container message-counters {
                     description "SIP message counters";
                     leaf response-provisional {
                       type uint32;
                       description "Number of provisional responses";
                     }
                     leaf response-invite-ok {
                       type uint32;
                       description "Number of 'OK' responses to INVITE messages";
                     }
                     leaf response-non-invite-ok {
                       type uint32;
                       description "Number of 'OK' responses to messages other than INVITE";
                     }
                     leaf response-redir {
                       type uint32;
                       description "Number of redirection (3xx) responses";
                     }
                     leaf response-request-failure {
                       type uint32;
                       description "Number of request failure (4xx) responses";
                     }
                     leaf response-server-failure {
                       type uint32;
                       description "Number of server failure (5xx) responses";
                     }
                     leaf response-global-failure {
                       type uint32;
                       description "Number of global failure (6xx) responses";
                     }
                     leaf response-invalid {
                       type uint32;
                       description "Number of invalid responses";
                     }
                     leaf response-retransmits {
                       type uint32;
                       description "Number of response retransmissions";
                     }
                     leaf register-new {
                       type uint32;
                       description "Number of REGISTER messages";
                     }
                     leaf invite-new {
                       type uint32;
                       description "Number of new INVITE messages";
                     }
                     leaf invite-retransmits {
                       type uint32;
                       description "Number of INVITE message retransmissions";
                     }
                     leaf reinvites {
                       type uint32;
                       description "Number of ReINVITE messages";
                     }
                     leaf cancel-valid {
                       type uint32;
                       description "Number of valid CANCEL messages";
                     }
                     leaf cancel-invalid {
                       type uint32;
                       description "Number of invalid CANCEL messages";
                     }
                     leaf ack-valid {
                       type uint32;
                       description "Number of valid ACK messages";
                     }
                     leaf ack-invalid {
                       type uint32;
                       description "Number of invalid ACK messages";
                     }
                     leaf ack-retransmits {
                       type uint32;
                       description "Number of ACK message retransmissions";
                     }
                     leaf bye-valid {
                       type uint32;
                       description "Number of valid BYE messages";
                     }
                     leaf bye-invalid {
                       type uint32;
                       description "Number of invalid BYE messages";
                     }
                     leaf subscribe-valid {
                       type uint32;
                       description "Number of valid SUBSCRIBE messages";
                     }
                     leaf subscribe-invalid {
                       type uint32;
                       description "Number of invalid SUBSCRIBE messages";
                     }
                     leaf notify-valid {
                       type uint32;
                       description "Number of valid NOTIFY messages";
                     }
                     leaf notify-invalid {
                       type uint32;
                       description "Number of invalid NOTIFY messages";
                     }
                     leaf message-valid {
                       type uint32;
                       description "Number of valid MESSAGE messages";
                     }
                     leaf message-invalid {
                       type uint32;
                       description "Number of invalid MESSAGE messages";
                     }
                     leaf options-valid {
                       type uint32;
                       description "Number of valid OPTIONS messages";
                     }
                     leaf options-invalid {
                       type uint32;
                       description "Number of invalid OPTIONS messages";
                     }
                     leaf info-valid {
                       type uint32;
                       description "Number of valid INFO messages";
                     }
                     leaf info-invalid {
                       type uint32;
                       description "Number of invalid INFO messages";
                     }
                     leaf update-valid {
                       type uint32;
                       description "Number of valid UPDATE messages";
                     }
                     leaf update-invalid {
                       type uint32;
                       description "Number of invalid UPDATE messages";
                     }
                     leaf refer-valid {
                       type uint32;
                       description "Number of valid REFER messages";
                     }
                     leaf refer-invalid {
                       type uint32;
                       description "Number of invalid REFER messages";
                     }
                   }
                 }
               }
               container drop-flows {
                 description "Drop flow statistics";
                 leaf max-ingress-drop-flows {
                   type string;
                   description "Maximum ingress drop flows allowed";
                 }
                 leaf max-egress-drop-flows {
                   type string;
                   description "Maximum egress drop flows allowed";
                 }
                 container drop-flows-counters {
                   leaf current-ingress-drop-flows {
                     type int32;
                     description "Current ingress drop flows count";
                   }
                   leaf current-egress-drop-flows {
                     type int32;
                     description "Current egress drop flows count";
                   }
                   leaf ingress-drop-flowlimit-drops {
                     type uint32;
                     description "Drops because ingress drop flow limit is reached";
                   }
                   leaf egress-drop-flowlimit-drops {
                     type uint32;
                     description "Drops because egress drop flow limit is reached";
                   }
                 }
               }
             }
           }
         }
         container detail {
           description "Stateful firewall statistics information";
           container service-sfw-statistics-entry {
             description "Stateful firewall statistics entry";
             leaf interface-name {
               type string;
               description "Name of the adaptive services interface";
             }
             container sfw-stats-service-set-entry {
               description "Stateful firewall service set statistics entry";
               container new-flow-counters {
                 description "New flow counters";
                 leaf new-flow-accepts {
                   type uint32;
                   description "Packets accepted by new flows";
                 }
                 leaf new-flow-discards {
                   type uint32;
                   description "Packets discarded by new flows";
                 }
                 leaf new-flow-rejects {
                   type uint32;
                   description "Packets rejected by new flows";
                 }
               }
               container existing-flow-counters {
                 description "Existing flow counters";
                 leaf existing-flow-accepts {
                   type uint32;
                   description "Packets accepted by existing accept flow";
                 }
                 leaf existing-flow-discards {
                   type uint32;
                   description "Packets discarded by existing drop flow";
                 }
                 leaf existing-flow-rejects {
                   type uint32;
                   description "Packets rejected by existing reject flow";
                 }
               }
               container hairpinning-counters {
                 description "Hairpinned packets count";
                 leaf slow-path-hairpinned-packets {
                   type uint32;
                   description "Initiator packets for Hairpinning";
                 }
                 leaf fast-path-hairpinned-packets {
                   type uint32;
                   description "Packets recieved on existing Hairpinned flows";
                 }
               }
               container drop_counters {
                 description "Drop counters (rules or resource exhaustion)";
                 leaf ip-option {
                   type uint32;
                   description "IP option drops";
                 }
                 leaf syn-defense {
                   type uint32;
                   description "Incomplete TCP handshakes";
                 }
                 leaf nat-ports-exhausted {
                   type uint32;
                   description "NAT ports exhausted";
                 }
                 leaf subs-flow-limit-exceeded {
                   type uint32;
                   description "Subscriber flow limit exceeded";
                 }
               }
               container error-counters {
                 description "Summarized protocol processing errors";
                 leaf ip-errors {
                   type uint32;
                   description "IP processing errors";
                 }
                 leaf tcp-errors {
                   type uint32;
                   description "TCP processing errors";
                 }
                 leaf udp-errors {
                   type uint32;
                   description "UDP processing errors";
                 }
                 leaf icmp-errors {
                   type uint32;
                   description "ICMP processing errors";
                 }
                 leaf non-ip-packets {
                   type uint32;
                   description "Non-IP packets";
                 }
                 leaf alg-errors {
                   type uint32;
                   description "ALG processing errors";
                 }
               }
               container ip-error-counters {
                 description "Extensive output of IP processing errors";
                 leaf ip-length-error {
                   type uint32;
                   description "IP packet length inconsistencies";
                 }
                 leaf ip-header-length-error {
                   type uint32;
                   description "Minimum IP header length check failures";
                 }
                 leaf long-packet {
                   type uint32;
                   description "Reassembled packet exceeds maximum IP length (65,535 bytes)";
                 }
                 leaf illegal-destination-address {
                   type uint32;
                   description "Illegal destination address";
                 }
                 leaf illegal-source-address {
                   type uint32;
                   description "Illegal source address";
                 }
                 leaf ttl-zero {
                   type uint32;
                   description "IP packets received with a TTL value of 0";
                 }
                 leaf illegal-ip-protocol {
                   type uint32;
                   description "Illegal IP protocol number ";
                 }
                 leaf non-ipv6 {
                   type uint32;
                   description "Non-IPv6 packets";
                 }
                 leaf land-attack {
                   type uint32;
                   description "IP source address same as destination address";
                 }
                 leaf not-ip-packet {
                   type uint32;
                   description "Not IP Packet";
                 }
                 leaf non-ipv4 {
                   type uint32;
                   description "Non-IPv4 packets";
                 }
                 leaf bad-checksum {
                   type uint32;
                   description "Bad checksum";
                 }
                 leaf illegal-fragment-length {
                   type uint32;
                   description "Illegal IP fragment length";
                 }
                 leaf fragment-overlap {
                   type uint32;
                   description "IP fragment overlap";
                 }
                 leaf fragment-reassembly-timeout {
                   type uint32;
                   description "IP fragment reassembly timeout";
                 }
                 leaf fragment-limit-exceeded {
                   type uint32;
                   description "IP fragment limit exceeded";
                 }
                 leaf unknown {
                   type uint32;
                   description "Unknown errors";
                 }
               }
               container tcp-error-counters {
                 description "Extensive output of TCP processing errors";
                 leaf tcp-header-length-error {
                   type uint32;
                   description "TCP header length inconsistencies";
                 }
                 leaf tcp-zero-port {
                   type uint32;
                   description "Source or destination port number is zero";
                 }
                 leaf illegal-sequence-number-flags {
                   type uint32;
                   description "Illegal sequence number and flags combinations";
                 }
                 leaf syn-attack {
                   type uint32;
                   description "SYN attack";
                 }
                 leaf non-syn-first-packet {
                   type uint32;
                   description "First packet not a SYN message";
                 }
                 leaf tcp-port-scan {
                   type uint32;
                   description "TCP port scan";
                 }
                 leaf bad-syn-cookie-response {
                   type uint32;
                   description "Bad SYN cookie response";
                 }
                 leaf tcp-recon-sequence-number-error {
                   type uint32;
                   description "TCP reconstructor sequence number error";
                 }
                 leaf tcp-recon-retransmits {
                   type uint32;
                   description "TCP reconstructor retransmissions";
                 }
                 leaf tcp-partially-opened-connection-timeout-syn-rcvd {
                   type uint32;
                   description "TCP partially opened connection timeout";
                 }
                 leaf tcp-partially-opened-connection-timeout-syn-ack-rcvd {
                   type uint32;
                   description "TCP partially opened connection timeout";
                 }
                 leaf tcp-partially-closed-connection-reuse {
                   type uint32;
                   description "TCP partially closed connection reuse";
                 }
                 leaf tcp-3way-error-client-sent-syn-ack {
                   type uint32;
                   description "TCP 3-way error - client sent SYN+ACK";
                 }
                 leaf tcp-3way-error-server-sent-ack {
                   type uint32;
                   description "TCP 3-way error - server sent ACK";
                 }
                 leaf tcp-3way-error-syn-seq-num-retrans-mismatch {
                   type uint32;
                   description "TCP 3-way error - SYN seq number retransmission mismatch";
                 }
                 leaf tcp-3way-error-rst-seq-num-mismatch {
                   type uint32;
                   description "TCP 3-way error - RST seq number mismatch";
                 }
                 leaf tcp-3way-error-fin-received {
                   type uint32;
                   description "TCP 3-way error - FIN received";
                 }
                 leaf tcp-3way-error-invalid-flags {
                   type uint32;
                   description "TCP 3-way error - invalid TCP flag combination";
                 }
                 leaf tcp-3way-error-syn-no-flow-initiator {
                   type uint32;
                   description "TCP 3-way error - SYN recvd but no client flows";
                 }
                 leaf tcp-3way-error-first-packet-syn-ack {
                   type uint32;
                   description "TCP 3-way error - first packet SYN+ACK";
                 }
                 leaf tcp-3way-error-first-packet-fin-ack {
                   type uint32;
                   description "TCP 3-way error - first packet FIN+ACK";
                 }
                 leaf tcp-3way-error-first-packet-fin {
                   type uint32;
                   description "TCP 3-way error - first packet FIN";
                 }
                 leaf tcp-3way-error-first-packet-rst {
                   type uint32;
                   description "TCP 3-way error - first packet RST";
                 }
                 leaf tcp-3way-error-first-packet-ack {
                   type uint32;
                   description "TCP 3-way error - first packet ack";
                 }
                 leaf tcp-3way-error-first-packet-invalid-flags {
                   type uint32;
                   description "TCP 3-way error - first packet ack";
                 }
                 leaf tcp-close-error-no-final-ack {
                   type uint32;
                   description "TCP close error - no final ack";
                 }
                 leaf tcp-resumed-flow {
                   type uint32;
                   description "TCP Resumed Flow";
                 }
               }
               container udp-error-counters {
                 description "Extensive output of UDP processing errors";
                 leaf udp-header-length-error {
                   type uint32;
                   description "IP data length is less than minimum UDP header length (8 bytes)";
                 }
                 leaf udp-zero-port {
                   type uint32;
                   description "Source or destination port number is zero";
                 }
                 leaf udp-port-scan {
                   type uint32;
                   description "UDP port scan (ICMP error seen for UDP flow)";
                 }
               }
               container icmp-error-counters {
                 description "Extensive output of ICMP processing errors";
                 leaf icmp-length-error {
                   type uint32;
                   description "IP data length less than minimum ICMP header length (8 bytes)";
                 }
                 leaf icmp-error-length-error {
                   type uint32;
                   description "ICMP error length inconsistencies";
                 }
                 leaf ping-duplicate-sequence-number {
                   type uint32;
                   description "Duplicate ping sequence number";
                 }
                 leaf ping-mismatched-sequence-number {
                   type uint32;
                   description "Mismatched ping sequence number";
                 }
                 leaf icmp-error-no-matching-flow {
                   type uint32;
                   description "No matching flow for ICMP error packet";
                 }
               }
               container alg-error-counters {
                 description "Extensive output of ALG processing errors";
                 leaf alg-bootp-errors {
                   type uint32;
                   description "ALG BOOTP errors";
                 }
                 leaf alg-dce-rpc-errors {
                   type uint32;
                   description "ALG DCE-RPC errors";
                 }
                 leaf alg-dce-rpc-portmap-errors {
                   type uint32;
                   description "ALG DCE-RPC portmap errors";
                 }
                 leaf alg-dns-errors {
                   type uint32;
                   description "ALG DNS errors";
                 }
                 leaf alg-exec-errors {
                   type uint32;
                   description "ALG exec errors";
                 }
                 leaf alg-ftp-errors {
                   type uint32;
                   description "ALG FTP errors";
                 }
                 leaf alg-h323-errors {
                   type uint32;
                   description "ALG H323 errors";
                 }
                 leaf alg-icmp-errors {
                   type uint32;
                   description "ALG ICMP errors";
                 }
                 leaf alg-iiop-errors {
                   type uint32;
                   description "ALG IIOP errors";
                 }
                 leaf alg-login-errors {
                   type uint32;
                   description "ALG login errors";
                 }
                 leaf alg-netbios-errors {
                   type uint32;
                   description "ALG NetBIOS errors";
                 }
                 leaf alg-netshow-errors {
                   type uint32;
                   description "ALG NetShow errors";
                 }
                 leaf alg-realaudio-errors {
                   type uint32;
                   description "ALG Real Audio errors";
                 }
                 leaf alg-rpc-errors {
                   type uint32;
                   description "ALG RPC errors";
                 }
                 leaf alg-rpc-portmap-errors {
                   type uint32;
                   description "ALG RPC portmap errors";
                 }
                 leaf alg-rtsp-errors {
                   type uint32;
                   description "ALG Real-Time Streaming Protocol errors";
                 }
                 leaf alg-shell-errors {
                   type uint32;
                   description "ALG shell errors";
                 }
                 leaf alg-sip-errors {
                   type uint32;
                   description "ALG Session Initiation Protocol errors";
                 }
                 leaf alg-snmp-errors {
                   type uint32;
                   description "ALG SNMP errors";
                 }
                 leaf alg-sqlnet-errors {
                   type uint32;
                   description "ALG SQLNet errors";
                 }
                 leaf alg-tftp-errors {
                   type uint32;
                   description "ALG TFTP errors";
                 }
                 leaf alg-traceroute-errors {
                   type uint32;
                   description "ALG traceroute errors";
                 }
               }
               container sip-alg-counters {
                 description "SIP statistics";
                 container alg-sip {
                   description "SIP statistics";
                   container total-counters {
                     description "Total statistics";
                     leaf total-messages {
                       type uint32;
                       description "Total SIP messages";
                     }
                     leaf call-segments {
                       type uint32;
                       description "SIP call segments";
                     }
                   }
                   container parser-counters {
                     description "Parser statistics";
                     leaf syntax-errors {
                       type uint32;
                       description "SIP syntax errors";
                     }
                     leaf content-errors {
                       type uint32;
                       description "SIP message content errors";
                     }
                     leaf unknown-methods {
                       type uint32;
                       description "SIP unknown methods";
                     }
                   }
                   container message-counters {
                     description "SIP message counters";
                     leaf response-provisional {
                       type uint32;
                       description "Number of provisional responses";
                     }
                     leaf response-invite-ok {
                       type uint32;
                       description "Number of 'OK' responses to INVITE messages";
                     }
                     leaf response-non-invite-ok {
                       type uint32;
                       description "Number of 'OK' responses to messages other than INVITE";
                     }
                     leaf response-redir {
                       type uint32;
                       description "Number of redirection (3xx) responses";
                     }
                     leaf response-request-failure {
                       type uint32;
                       description "Number of request failure (4xx) responses";
                     }
                     leaf response-server-failure {
                       type uint32;
                       description "Number of server failure (5xx) responses";
                     }
                     leaf response-global-failure {
                       type uint32;
                       description "Number of global failure (6xx) responses";
                     }
                     leaf response-invalid {
                       type uint32;
                       description "Number of invalid responses";
                     }
                     leaf response-retransmits {
                       type uint32;
                       description "Number of response retransmissions";
                     }
                     leaf register-new {
                       type uint32;
                       description "Number of REGISTER messages";
                     }
                     leaf invite-new {
                       type uint32;
                       description "Number of new INVITE messages";
                     }
                     leaf invite-retransmits {
                       type uint32;
                       description "Number of INVITE message retransmissions";
                     }
                     leaf reinvites {
                       type uint32;
                       description "Number of ReINVITE messages";
                     }
                     leaf cancel-valid {
                       type uint32;
                       description "Number of valid CANCEL messages";
                     }
                     leaf cancel-invalid {
                       type uint32;
                       description "Number of invalid CANCEL messages";
                     }
                     leaf ack-valid {
                       type uint32;
                       description "Number of valid ACK messages";
                     }
                     leaf ack-invalid {
                       type uint32;
                       description "Number of invalid ACK messages";
                     }
                     leaf ack-retransmits {
                       type uint32;
                       description "Number of ACK message retransmissions";
                     }
                     leaf bye-valid {
                       type uint32;
                       description "Number of valid BYE messages";
                     }
                     leaf bye-invalid {
                       type uint32;
                       description "Number of invalid BYE messages";
                     }
                     leaf subscribe-valid {
                       type uint32;
                       description "Number of valid SUBSCRIBE messages";
                     }
                     leaf subscribe-invalid {
                       type uint32;
                       description "Number of invalid SUBSCRIBE messages";
                     }
                     leaf notify-valid {
                       type uint32;
                       description "Number of valid NOTIFY messages";
                     }
                     leaf notify-invalid {
                       type uint32;
                       description "Number of invalid NOTIFY messages";
                     }
                     leaf message-valid {
                       type uint32;
                       description "Number of valid MESSAGE messages";
                     }
                     leaf message-invalid {
                       type uint32;
                       description "Number of invalid MESSAGE messages";
                     }
                     leaf options-valid {
                       type uint32;
                       description "Number of valid OPTIONS messages";
                     }
                     leaf options-invalid {
                       type uint32;
                       description "Number of invalid OPTIONS messages";
                     }
                     leaf info-valid {
                       type uint32;
                       description "Number of valid INFO messages";
                     }
                     leaf info-invalid {
                       type uint32;
                       description "Number of invalid INFO messages";
                     }
                     leaf update-valid {
                       type uint32;
                       description "Number of valid UPDATE messages";
                     }
                     leaf update-invalid {
                       type uint32;
                       description "Number of invalid UPDATE messages";
                     }
                     leaf refer-valid {
                       type uint32;
                       description "Number of valid REFER messages";
                     }
                     leaf refer-invalid {
                       type uint32;
                       description "Number of invalid REFER messages";
                     }
                   }
                 }
               }
               container drop-flows {
                 description "Drop flow statistics";
                 leaf max-ingress-drop-flows {
                   type string;
                   description "Maximum ingress drop flows allowed";
                 }
                 leaf max-egress-drop-flows {
                   type string;
                   description "Maximum egress drop flows allowed";
                 }
                 container drop-flows-counters {
                   leaf current-ingress-drop-flows {
                     type int32;
                     description "Current ingress drop flows count";
                   }
                   leaf current-egress-drop-flows {
                     type int32;
                     description "Current egress drop flows count";
                   }
                   leaf ingress-drop-flowlimit-drops {
                     type uint32;
                     description "Drops because ingress drop flow limit is reached";
                   }
                   leaf egress-drop-flowlimit-drops {
                     type uint32;
                     description "Drops because egress drop flow limit is reached";
                   }
                 }
               }
             }
           }
         }
         container extensive {
           description "Stateful firewall statistics information";
           container service-sfw-statistics-entry {
             description "Stateful firewall statistics entry";
             leaf interface-name {
               type string;
               description "Name of the adaptive services interface";
             }
             container sfw-stats-service-set-entry {
               description "Stateful firewall service set statistics entry";
               container new-flow-counters {
                 description "New flow counters";
                 leaf new-flow-accepts {
                   type uint32;
                   description "Packets accepted by new flows";
                 }
                 leaf new-flow-discards {
                   type uint32;
                   description "Packets discarded by new flows";
                 }
                 leaf new-flow-rejects {
                   type uint32;
                   description "Packets rejected by new flows";
                 }
               }
               container existing-flow-counters {
                 description "Existing flow counters";
                 leaf existing-flow-accepts {
                   type uint32;
                   description "Packets accepted by existing accept flow";
                 }
                 leaf existing-flow-discards {
                   type uint32;
                   description "Packets discarded by existing drop flow";
                 }
                 leaf existing-flow-rejects {
                   type uint32;
                   description "Packets rejected by existing reject flow";
                 }
               }
               container hairpinning-counters {
                 description "Hairpinned packets count";
                 leaf slow-path-hairpinned-packets {
                   type uint32;
                   description "Initiator packets for Hairpinning";
                 }
                 leaf fast-path-hairpinned-packets {
                   type uint32;
                   description "Packets recieved on existing Hairpinned flows";
                 }
               }
               container drop_counters {
                 description "Drop counters (rules or resource exhaustion)";
                 leaf ip-option {
                   type uint32;
                   description "IP option drops";
                 }
                 leaf syn-defense {
                   type uint32;
                   description "Incomplete TCP handshakes";
                 }
                 leaf nat-ports-exhausted {
                   type uint32;
                   description "NAT ports exhausted";
                 }
                 leaf subs-flow-limit-exceeded {
                   type uint32;
                   description "Subscriber flow limit exceeded";
                 }
               }
               container error-counters {
                 description "Summarized protocol processing errors";
                 leaf ip-errors {
                   type uint32;
                   description "IP processing errors";
                 }
                 leaf tcp-errors {
                   type uint32;
                   description "TCP processing errors";
                 }
                 leaf udp-errors {
                   type uint32;
                   description "UDP processing errors";
                 }
                 leaf icmp-errors {
                   type uint32;
                   description "ICMP processing errors";
                 }
                 leaf non-ip-packets {
                   type uint32;
                   description "Non-IP packets";
                 }
                 leaf alg-errors {
                   type uint32;
                   description "ALG processing errors";
                 }
               }
               container ip-error-counters {
                 description "Extensive output of IP processing errors";
                 leaf ip-length-error {
                   type uint32;
                   description "IP packet length inconsistencies";
                 }
                 leaf ip-header-length-error {
                   type uint32;
                   description "Minimum IP header length check failures";
                 }
                 leaf long-packet {
                   type uint32;
                   description "Reassembled packet exceeds maximum IP length (65,535 bytes)";
                 }
                 leaf illegal-destination-address {
                   type uint32;
                   description "Illegal destination address";
                 }
                 leaf illegal-source-address {
                   type uint32;
                   description "Illegal source address";
                 }
                 leaf ttl-zero {
                   type uint32;
                   description "IP packets received with a TTL value of 0";
                 }
                 leaf illegal-ip-protocol {
                   type uint32;
                   description "Illegal IP protocol number ";
                 }
                 leaf non-ipv6 {
                   type uint32;
                   description "Non-IPv6 packets";
                 }
                 leaf land-attack {
                   type uint32;
                   description "IP source address same as destination address";
                 }
                 leaf not-ip-packet {
                   type uint32;
                   description "Not IP Packet";
                 }
                 leaf non-ipv4 {
                   type uint32;
                   description "Non-IPv4 packets";
                 }
                 leaf bad-checksum {
                   type uint32;
                   description "Bad checksum";
                 }
                 leaf illegal-fragment-length {
                   type uint32;
                   description "Illegal IP fragment length";
                 }
                 leaf fragment-overlap {
                   type uint32;
                   description "IP fragment overlap";
                 }
                 leaf fragment-reassembly-timeout {
                   type uint32;
                   description "IP fragment reassembly timeout";
                 }
                 leaf fragment-limit-exceeded {
                   type uint32;
                   description "IP fragment limit exceeded";
                 }
                 leaf unknown {
                   type uint32;
                   description "Unknown errors";
                 }
               }
               container tcp-error-counters {
                 description "Extensive output of TCP processing errors";
                 leaf tcp-header-length-error {
                   type uint32;
                   description "TCP header length inconsistencies";
                 }
                 leaf tcp-zero-port {
                   type uint32;
                   description "Source or destination port number is zero";
                 }
                 leaf illegal-sequence-number-flags {
                   type uint32;
                   description "Illegal sequence number and flags combinations";
                 }
                 leaf syn-attack {
                   type uint32;
                   description "SYN attack";
                 }
                 leaf non-syn-first-packet {
                   type uint32;
                   description "First packet not a SYN message";
                 }
                 leaf tcp-port-scan {
                   type uint32;
                   description "TCP port scan";
                 }
                 leaf bad-syn-cookie-response {
                   type uint32;
                   description "Bad SYN cookie response";
                 }
                 leaf tcp-recon-sequence-number-error {
                   type uint32;
                   description "TCP reconstructor sequence number error";
                 }
                 leaf tcp-recon-retransmits {
                   type uint32;
                   description "TCP reconstructor retransmissions";
                 }
                 leaf tcp-partially-opened-connection-timeout-syn-rcvd {
                   type uint32;
                   description "TCP partially opened connection timeout";
                 }
                 leaf tcp-partially-opened-connection-timeout-syn-ack-rcvd {
                   type uint32;
                   description "TCP partially opened connection timeout";
                 }
                 leaf tcp-partially-closed-connection-reuse {
                   type uint32;
                   description "TCP partially closed connection reuse";
                 }
                 leaf tcp-3way-error-client-sent-syn-ack {
                   type uint32;
                   description "TCP 3-way error - client sent SYN+ACK";
                 }
                 leaf tcp-3way-error-server-sent-ack {
                   type uint32;
                   description "TCP 3-way error - server sent ACK";
                 }
                 leaf tcp-3way-error-syn-seq-num-retrans-mismatch {
                   type uint32;
                   description "TCP 3-way error - SYN seq number retransmission mismatch";
                 }
                 leaf tcp-3way-error-rst-seq-num-mismatch {
                   type uint32;
                   description "TCP 3-way error - RST seq number mismatch";
                 }
                 leaf tcp-3way-error-fin-received {
                   type uint32;
                   description "TCP 3-way error - FIN received";
                 }
                 leaf tcp-3way-error-invalid-flags {
                   type uint32;
                   description "TCP 3-way error - invalid TCP flag combination";
                 }
                 leaf tcp-3way-error-syn-no-flow-initiator {
                   type uint32;
                   description "TCP 3-way error - SYN recvd but no client flows";
                 }
                 leaf tcp-3way-error-first-packet-syn-ack {
                   type uint32;
                   description "TCP 3-way error - first packet SYN+ACK";
                 }
                 leaf tcp-3way-error-first-packet-fin-ack {
                   type uint32;
                   description "TCP 3-way error - first packet FIN+ACK";
                 }
                 leaf tcp-3way-error-first-packet-fin {
                   type uint32;
                   description "TCP 3-way error - first packet FIN";
                 }
                 leaf tcp-3way-error-first-packet-rst {
                   type uint32;
                   description "TCP 3-way error - first packet RST";
                 }
                 leaf tcp-3way-error-first-packet-ack {
                   type uint32;
                   description "TCP 3-way error - first packet ack";
                 }
                 leaf tcp-3way-error-first-packet-invalid-flags {
                   type uint32;
                   description "TCP 3-way error - first packet ack";
                 }
                 leaf tcp-close-error-no-final-ack {
                   type uint32;
                   description "TCP close error - no final ack";
                 }
                 leaf tcp-resumed-flow {
                   type uint32;
                   description "TCP Resumed Flow";
                 }
               }
               container udp-error-counters {
                 description "Extensive output of UDP processing errors";
                 leaf udp-header-length-error {
                   type uint32;
                   description "IP data length is less than minimum UDP header length (8 bytes)";
                 }
                 leaf udp-zero-port {
                   type uint32;
                   description "Source or destination port number is zero";
                 }
                 leaf udp-port-scan {
                   type uint32;
                   description "UDP port scan (ICMP error seen for UDP flow)";
                 }
               }
               container icmp-error-counters {
                 description "Extensive output of ICMP processing errors";
                 leaf icmp-length-error {
                   type uint32;
                   description "IP data length less than minimum ICMP header length (8 bytes)";
                 }
                 leaf icmp-error-length-error {
                   type uint32;
                   description "ICMP error length inconsistencies";
                 }
                 leaf ping-duplicate-sequence-number {
                   type uint32;
                   description "Duplicate ping sequence number";
                 }
                 leaf ping-mismatched-sequence-number {
                   type uint32;
                   description "Mismatched ping sequence number";
                 }
                 leaf icmp-error-no-matching-flow {
                   type uint32;
                   description "No matching flow for ICMP error packet";
                 }
               }
               container alg-error-counters {
                 description "Extensive output of ALG processing errors";
                 leaf alg-bootp-errors {
                   type uint32;
                   description "ALG BOOTP errors";
                 }
                 leaf alg-dce-rpc-errors {
                   type uint32;
                   description "ALG DCE-RPC errors";
                 }
                 leaf alg-dce-rpc-portmap-errors {
                   type uint32;
                   description "ALG DCE-RPC portmap errors";
                 }
                 leaf alg-dns-errors {
                   type uint32;
                   description "ALG DNS errors";
                 }
                 leaf alg-exec-errors {
                   type uint32;
                   description "ALG exec errors";
                 }
                 leaf alg-ftp-errors {
                   type uint32;
                   description "ALG FTP errors";
                 }
                 leaf alg-h323-errors {
                   type uint32;
                   description "ALG H323 errors";
                 }
                 leaf alg-icmp-errors {
                   type uint32;
                   description "ALG ICMP errors";
                 }
                 leaf alg-iiop-errors {
                   type uint32;
                   description "ALG IIOP errors";
                 }
                 leaf alg-login-errors {
                   type uint32;
                   description "ALG login errors";
                 }
                 leaf alg-netbios-errors {
                   type uint32;
                   description "ALG NetBIOS errors";
                 }
                 leaf alg-netshow-errors {
                   type uint32;
                   description "ALG NetShow errors";
                 }
                 leaf alg-realaudio-errors {
                   type uint32;
                   description "ALG Real Audio errors";
                 }
                 leaf alg-rpc-errors {
                   type uint32;
                   description "ALG RPC errors";
                 }
                 leaf alg-rpc-portmap-errors {
                   type uint32;
                   description "ALG RPC portmap errors";
                 }
                 leaf alg-rtsp-errors {
                   type uint32;
                   description "ALG Real-Time Streaming Protocol errors";
                 }
                 leaf alg-shell-errors {
                   type uint32;
                   description "ALG shell errors";
                 }
                 leaf alg-sip-errors {
                   type uint32;
                   description "ALG Session Initiation Protocol errors";
                 }
                 leaf alg-snmp-errors {
                   type uint32;
                   description "ALG SNMP errors";
                 }
                 leaf alg-sqlnet-errors {
                   type uint32;
                   description "ALG SQLNet errors";
                 }
                 leaf alg-tftp-errors {
                   type uint32;
                   description "ALG TFTP errors";
                 }
                 leaf alg-traceroute-errors {
                   type uint32;
                   description "ALG traceroute errors";
                 }
               }
               container sip-alg-counters {
                 description "SIP statistics";
                 container alg-sip {
                   description "SIP statistics";
                   container total-counters {
                     description "Total statistics";
                     leaf total-messages {
                       type uint32;
                       description "Total SIP messages";
                     }
                     leaf call-segments {
                       type uint32;
                       description "SIP call segments";
                     }
                   }
                   container parser-counters {
                     description "Parser statistics";
                     leaf syntax-errors {
                       type uint32;
                       description "SIP syntax errors";
                     }
                     leaf content-errors {
                       type uint32;
                       description "SIP message content errors";
                     }
                     leaf unknown-methods {
                       type uint32;
                       description "SIP unknown methods";
                     }
                   }
                   container message-counters {
                     description "SIP message counters";
                     leaf response-provisional {
                       type uint32;
                       description "Number of provisional responses";
                     }
                     leaf response-invite-ok {
                       type uint32;
                       description "Number of 'OK' responses to INVITE messages";
                     }
                     leaf response-non-invite-ok {
                       type uint32;
                       description "Number of 'OK' responses to messages other than INVITE";
                     }
                     leaf response-redir {
                       type uint32;
                       description "Number of redirection (3xx) responses";
                     }
                     leaf response-request-failure {
                       type uint32;
                       description "Number of request failure (4xx) responses";
                     }
                     leaf response-server-failure {
                       type uint32;
                       description "Number of server failure (5xx) responses";
                     }
                     leaf response-global-failure {
                       type uint32;
                       description "Number of global failure (6xx) responses";
                     }
                     leaf response-invalid {
                       type uint32;
                       description "Number of invalid responses";
                     }
                     leaf response-retransmits {
                       type uint32;
                       description "Number of response retransmissions";
                     }
                     leaf register-new {
                       type uint32;
                       description "Number of REGISTER messages";
                     }
                     leaf invite-new {
                       type uint32;
                       description "Number of new INVITE messages";
                     }
                     leaf invite-retransmits {
                       type uint32;
                       description "Number of INVITE message retransmissions";
                     }
                     leaf reinvites {
                       type uint32;
                       description "Number of ReINVITE messages";
                     }
                     leaf cancel-valid {
                       type uint32;
                       description "Number of valid CANCEL messages";
                     }
                     leaf cancel-invalid {
                       type uint32;
                       description "Number of invalid CANCEL messages";
                     }
                     leaf ack-valid {
                       type uint32;
                       description "Number of valid ACK messages";
                     }
                     leaf ack-invalid {
                       type uint32;
                       description "Number of invalid ACK messages";
                     }
                     leaf ack-retransmits {
                       type uint32;
                       description "Number of ACK message retransmissions";
                     }
                     leaf bye-valid {
                       type uint32;
                       description "Number of valid BYE messages";
                     }
                     leaf bye-invalid {
                       type uint32;
                       description "Number of invalid BYE messages";
                     }
                     leaf subscribe-valid {
                       type uint32;
                       description "Number of valid SUBSCRIBE messages";
                     }
                     leaf subscribe-invalid {
                       type uint32;
                       description "Number of invalid SUBSCRIBE messages";
                     }
                     leaf notify-valid {
                       type uint32;
                       description "Number of valid NOTIFY messages";
                     }
                     leaf notify-invalid {
                       type uint32;
                       description "Number of invalid NOTIFY messages";
                     }
                     leaf message-valid {
                       type uint32;
                       description "Number of valid MESSAGE messages";
                     }
                     leaf message-invalid {
                       type uint32;
                       description "Number of invalid MESSAGE messages";
                     }
                     leaf options-valid {
                       type uint32;
                       description "Number of valid OPTIONS messages";
                     }
                     leaf options-invalid {
                       type uint32;
                       description "Number of invalid OPTIONS messages";
                     }
                     leaf info-valid {
                       type uint32;
                       description "Number of valid INFO messages";
                     }
                     leaf info-invalid {
                       type uint32;
                       description "Number of invalid INFO messages";
                     }
                     leaf update-valid {
                       type uint32;
                       description "Number of valid UPDATE messages";
                     }
                     leaf update-invalid {
                       type uint32;
                       description "Number of invalid UPDATE messages";
                     }
                     leaf refer-valid {
                       type uint32;
                       description "Number of valid REFER messages";
                     }
                     leaf refer-invalid {
                       type uint32;
                       description "Number of invalid REFER messages";
                     }
                   }
                 }
               }
               container drop-flows {
                 description "Drop flow statistics";
                 leaf max-ingress-drop-flows {
                   type string;
                   description "Maximum ingress drop flows allowed";
                 }
                 leaf max-egress-drop-flows {
                   type string;
                   description "Maximum egress drop flows allowed";
                 }
                 container drop-flows-counters {
                   leaf current-ingress-drop-flows {
                     type int32;
                     description "Current ingress drop flows count";
                   }
                   leaf current-egress-drop-flows {
                     type int32;
                     description "Current egress drop flows count";
                   }
                   leaf ingress-drop-flowlimit-drops {
                     type uint32;
                     description "Drops because ingress drop flow limit is reached";
                   }
                   leaf egress-drop-flowlimit-drops {
                     type uint32;
                     description "Drops because egress drop flow limit is reached";
                   }
                 }
               }
             }
           }
         }
         container alg {
           description "Stateful firewall statistics information";
           container service-sfw-statistics-entry {
             description "Stateful firewall statistics entry";
             leaf interface-name {
               type string;
               description "Name of the adaptive services interface";
             }
             container sfw-stats-service-set-entry {
               description "Stateful firewall service set statistics entry";
               container new-flow-counters {
                 description "New flow counters";
                 leaf new-flow-accepts {
                   type uint32;
                   description "Packets accepted by new flows";
                 }
                 leaf new-flow-discards {
                   type uint32;
                   description "Packets discarded by new flows";
                 }
                 leaf new-flow-rejects {
                   type uint32;
                   description "Packets rejected by new flows";
                 }
               }
               container existing-flow-counters {
                 description "Existing flow counters";
                 leaf existing-flow-accepts {
                   type uint32;
                   description "Packets accepted by existing accept flow";
                 }
                 leaf existing-flow-discards {
                   type uint32;
                   description "Packets discarded by existing drop flow";
                 }
                 leaf existing-flow-rejects {
                   type uint32;
                   description "Packets rejected by existing reject flow";
                 }
               }
               container hairpinning-counters {
                 description "Hairpinned packets count";
                 leaf slow-path-hairpinned-packets {
                   type uint32;
                   description "Initiator packets for Hairpinning";
                 }
                 leaf fast-path-hairpinned-packets {
                   type uint32;
                   description "Packets recieved on existing Hairpinned flows";
                 }
               }
               container drop_counters {
                 description "Drop counters (rules or resource exhaustion)";
                 leaf ip-option {
                   type uint32;
                   description "IP option drops";
                 }
                 leaf syn-defense {
                   type uint32;
                   description "Incomplete TCP handshakes";
                 }
                 leaf nat-ports-exhausted {
                   type uint32;
                   description "NAT ports exhausted";
                 }
                 leaf subs-flow-limit-exceeded {
                   type uint32;
                   description "Subscriber flow limit exceeded";
                 }
               }
               container error-counters {
                 description "Summarized protocol processing errors";
                 leaf ip-errors {
                   type uint32;
                   description "IP processing errors";
                 }
                 leaf tcp-errors {
                   type uint32;
                   description "TCP processing errors";
                 }
                 leaf udp-errors {
                   type uint32;
                   description "UDP processing errors";
                 }
                 leaf icmp-errors {
                   type uint32;
                   description "ICMP processing errors";
                 }
                 leaf non-ip-packets {
                   type uint32;
                   description "Non-IP packets";
                 }
                 leaf alg-errors {
                   type uint32;
                   description "ALG processing errors";
                 }
               }
               container ip-error-counters {
                 description "Extensive output of IP processing errors";
                 leaf ip-length-error {
                   type uint32;
                   description "IP packet length inconsistencies";
                 }
                 leaf ip-header-length-error {
                   type uint32;
                   description "Minimum IP header length check failures";
                 }
                 leaf long-packet {
                   type uint32;
                   description "Reassembled packet exceeds maximum IP length (65,535 bytes)";
                 }
                 leaf illegal-destination-address {
                   type uint32;
                   description "Illegal destination address";
                 }
                 leaf illegal-source-address {
                   type uint32;
                   description "Illegal source address";
                 }
                 leaf ttl-zero {
                   type uint32;
                   description "IP packets received with a TTL value of 0";
                 }
                 leaf illegal-ip-protocol {
                   type uint32;
                   description "Illegal IP protocol number ";
                 }
                 leaf non-ipv6 {
                   type uint32;
                   description "Non-IPv6 packets";
                 }
                 leaf land-attack {
                   type uint32;
                   description "IP source address same as destination address";
                 }
                 leaf not-ip-packet {
                   type uint32;
                   description "Not IP Packet";
                 }
                 leaf non-ipv4 {
                   type uint32;
                   description "Non-IPv4 packets";
                 }
                 leaf bad-checksum {
                   type uint32;
                   description "Bad checksum";
                 }
                 leaf illegal-fragment-length {
                   type uint32;
                   description "Illegal IP fragment length";
                 }
                 leaf fragment-overlap {
                   type uint32;
                   description "IP fragment overlap";
                 }
                 leaf fragment-reassembly-timeout {
                   type uint32;
                   description "IP fragment reassembly timeout";
                 }
                 leaf fragment-limit-exceeded {
                   type uint32;
                   description "IP fragment limit exceeded";
                 }
                 leaf unknown {
                   type uint32;
                   description "Unknown errors";
                 }
               }
               container tcp-error-counters {
                 description "Extensive output of TCP processing errors";
                 leaf tcp-header-length-error {
                   type uint32;
                   description "TCP header length inconsistencies";
                 }
                 leaf tcp-zero-port {
                   type uint32;
                   description "Source or destination port number is zero";
                 }
                 leaf illegal-sequence-number-flags {
                   type uint32;
                   description "Illegal sequence number and flags combinations";
                 }
                 leaf syn-attack {
                   type uint32;
                   description "SYN attack";
                 }
                 leaf non-syn-first-packet {
                   type uint32;
                   description "First packet not a SYN message";
                 }
                 leaf tcp-port-scan {
                   type uint32;
                   description "TCP port scan";
                 }
                 leaf bad-syn-cookie-response {
                   type uint32;
                   description "Bad SYN cookie response";
                 }
                 leaf tcp-recon-sequence-number-error {
                   type uint32;
                   description "TCP reconstructor sequence number error";
                 }
                 leaf tcp-recon-retransmits {
                   type uint32;
                   description "TCP reconstructor retransmissions";
                 }
                 leaf tcp-partially-opened-connection-timeout-syn-rcvd {
                   type uint32;
                   description "TCP partially opened connection timeout";
                 }
                 leaf tcp-partially-opened-connection-timeout-syn-ack-rcvd {
                   type uint32;
                   description "TCP partially opened connection timeout";
                 }
                 leaf tcp-partially-closed-connection-reuse {
                   type uint32;
                   description "TCP partially closed connection reuse";
                 }
                 leaf tcp-3way-error-client-sent-syn-ack {
                   type uint32;
                   description "TCP 3-way error - client sent SYN+ACK";
                 }
                 leaf tcp-3way-error-server-sent-ack {
                   type uint32;
                   description "TCP 3-way error - server sent ACK";
                 }
                 leaf tcp-3way-error-syn-seq-num-retrans-mismatch {
                   type uint32;
                   description "TCP 3-way error - SYN seq number retransmission mismatch";
                 }
                 leaf tcp-3way-error-rst-seq-num-mismatch {
                   type uint32;
                   description "TCP 3-way error - RST seq number mismatch";
                 }
                 leaf tcp-3way-error-fin-received {
                   type uint32;
                   description "TCP 3-way error - FIN received";
                 }
                 leaf tcp-3way-error-invalid-flags {
                   type uint32;
                   description "TCP 3-way error - invalid TCP flag combination";
                 }
                 leaf tcp-3way-error-syn-no-flow-initiator {
                   type uint32;
                   description "TCP 3-way error - SYN recvd but no client flows";
                 }
                 leaf tcp-3way-error-first-packet-syn-ack {
                   type uint32;
                   description "TCP 3-way error - first packet SYN+ACK";
                 }
                 leaf tcp-3way-error-first-packet-fin-ack {
                   type uint32;
                   description "TCP 3-way error - first packet FIN+ACK";
                 }
                 leaf tcp-3way-error-first-packet-fin {
                   type uint32;
                   description "TCP 3-way error - first packet FIN";
                 }
                 leaf tcp-3way-error-first-packet-rst {
                   type uint32;
                   description "TCP 3-way error - first packet RST";
                 }
                 leaf tcp-3way-error-first-packet-ack {
                   type uint32;
                   description "TCP 3-way error - first packet ack";
                 }
                 leaf tcp-3way-error-first-packet-invalid-flags {
                   type uint32;
                   description "TCP 3-way error - first packet ack";
                 }
                 leaf tcp-close-error-no-final-ack {
                   type uint32;
                   description "TCP close error - no final ack";
                 }
                 leaf tcp-resumed-flow {
                   type uint32;
                   description "TCP Resumed Flow";
                 }
               }
               container udp-error-counters {
                 description "Extensive output of UDP processing errors";
                 leaf udp-header-length-error {
                   type uint32;
                   description "IP data length is less than minimum UDP header length (8 bytes)";
                 }
                 leaf udp-zero-port {
                   type uint32;
                   description "Source or destination port number is zero";
                 }
                 leaf udp-port-scan {
                   type uint32;
                   description "UDP port scan (ICMP error seen for UDP flow)";
                 }
               }
               container icmp-error-counters {
                 description "Extensive output of ICMP processing errors";
                 leaf icmp-length-error {
                   type uint32;
                   description "IP data length less than minimum ICMP header length (8 bytes)";
                 }
                 leaf icmp-error-length-error {
                   type uint32;
                   description "ICMP error length inconsistencies";
                 }
                 leaf ping-duplicate-sequence-number {
                   type uint32;
                   description "Duplicate ping sequence number";
                 }
                 leaf ping-mismatched-sequence-number {
                   type uint32;
                   description "Mismatched ping sequence number";
                 }
                 leaf icmp-error-no-matching-flow {
                   type uint32;
                   description "No matching flow for ICMP error packet";
                 }
               }
               container alg-error-counters {
                 description "Extensive output of ALG processing errors";
                 leaf alg-bootp-errors {
                   type uint32;
                   description "ALG BOOTP errors";
                 }
                 leaf alg-dce-rpc-errors {
                   type uint32;
                   description "ALG DCE-RPC errors";
                 }
                 leaf alg-dce-rpc-portmap-errors {
                   type uint32;
                   description "ALG DCE-RPC portmap errors";
                 }
                 leaf alg-dns-errors {
                   type uint32;
                   description "ALG DNS errors";
                 }
                 leaf alg-exec-errors {
                   type uint32;
                   description "ALG exec errors";
                 }
                 leaf alg-ftp-errors {
                   type uint32;
                   description "ALG FTP errors";
                 }
                 leaf alg-h323-errors {
                   type uint32;
                   description "ALG H323 errors";
                 }
                 leaf alg-icmp-errors {
                   type uint32;
                   description "ALG ICMP errors";
                 }
                 leaf alg-iiop-errors {
                   type uint32;
                   description "ALG IIOP errors";
                 }
                 leaf alg-login-errors {
                   type uint32;
                   description "ALG login errors";
                 }
                 leaf alg-netbios-errors {
                   type uint32;
                   description "ALG NetBIOS errors";
                 }
                 leaf alg-netshow-errors {
                   type uint32;
                   description "ALG NetShow errors";
                 }
                 leaf alg-realaudio-errors {
                   type uint32;
                   description "ALG Real Audio errors";
                 }
                 leaf alg-rpc-errors {
                   type uint32;
                   description "ALG RPC errors";
                 }
                 leaf alg-rpc-portmap-errors {
                   type uint32;
                   description "ALG RPC portmap errors";
                 }
                 leaf alg-rtsp-errors {
                   type uint32;
                   description "ALG Real-Time Streaming Protocol errors";
                 }
                 leaf alg-shell-errors {
                   type uint32;
                   description "ALG shell errors";
                 }
                 leaf alg-sip-errors {
                   type uint32;
                   description "ALG Session Initiation Protocol errors";
                 }
                 leaf alg-snmp-errors {
                   type uint32;
                   description "ALG SNMP errors";
                 }
                 leaf alg-sqlnet-errors {
                   type uint32;
                   description "ALG SQLNet errors";
                 }
                 leaf alg-tftp-errors {
                   type uint32;
                   description "ALG TFTP errors";
                 }
                 leaf alg-traceroute-errors {
                   type uint32;
                   description "ALG traceroute errors";
                 }
               }
               container sip-alg-counters {
                 description "SIP statistics";
                 container alg-sip {
                   description "SIP statistics";
                   container total-counters {
                     description "Total statistics";
                     leaf total-messages {
                       type uint32;
                       description "Total SIP messages";
                     }
                     leaf call-segments {
                       type uint32;
                       description "SIP call segments";
                     }
                   }
                   container parser-counters {
                     description "Parser statistics";
                     leaf syntax-errors {
                       type uint32;
                       description "SIP syntax errors";
                     }
                     leaf content-errors {
                       type uint32;
                       description "SIP message content errors";
                     }
                     leaf unknown-methods {
                       type uint32;
                       description "SIP unknown methods";
                     }
                   }
                   container message-counters {
                     description "SIP message counters";
                     leaf response-provisional {
                       type uint32;
                       description "Number of provisional responses";
                     }
                     leaf response-invite-ok {
                       type uint32;
                       description "Number of 'OK' responses to INVITE messages";
                     }
                     leaf response-non-invite-ok {
                       type uint32;
                       description "Number of 'OK' responses to messages other than INVITE";
                     }
                     leaf response-redir {
                       type uint32;
                       description "Number of redirection (3xx) responses";
                     }
                     leaf response-request-failure {
                       type uint32;
                       description "Number of request failure (4xx) responses";
                     }
                     leaf response-server-failure {
                       type uint32;
                       description "Number of server failure (5xx) responses";
                     }
                     leaf response-global-failure {
                       type uint32;
                       description "Number of global failure (6xx) responses";
                     }
                     leaf response-invalid {
                       type uint32;
                       description "Number of invalid responses";
                     }
                     leaf response-retransmits {
                       type uint32;
                       description "Number of response retransmissions";
                     }
                     leaf register-new {
                       type uint32;
                       description "Number of REGISTER messages";
                     }
                     leaf invite-new {
                       type uint32;
                       description "Number of new INVITE messages";
                     }
                     leaf invite-retransmits {
                       type uint32;
                       description "Number of INVITE message retransmissions";
                     }
                     leaf reinvites {
                       type uint32;
                       description "Number of ReINVITE messages";
                     }
                     leaf cancel-valid {
                       type uint32;
                       description "Number of valid CANCEL messages";
                     }
                     leaf cancel-invalid {
                       type uint32;
                       description "Number of invalid CANCEL messages";
                     }
                     leaf ack-valid {
                       type uint32;
                       description "Number of valid ACK messages";
                     }
                     leaf ack-invalid {
                       type uint32;
                       description "Number of invalid ACK messages";
                     }
                     leaf ack-retransmits {
                       type uint32;
                       description "Number of ACK message retransmissions";
                     }
                     leaf bye-valid {
                       type uint32;
                       description "Number of valid BYE messages";
                     }
                     leaf bye-invalid {
                       type uint32;
                       description "Number of invalid BYE messages";
                     }
                     leaf subscribe-valid {
                       type uint32;
                       description "Number of valid SUBSCRIBE messages";
                     }
                     leaf subscribe-invalid {
                       type uint32;
                       description "Number of invalid SUBSCRIBE messages";
                     }
                     leaf notify-valid {
                       type uint32;
                       description "Number of valid NOTIFY messages";
                     }
                     leaf notify-invalid {
                       type uint32;
                       description "Number of invalid NOTIFY messages";
                     }
                     leaf message-valid {
                       type uint32;
                       description "Number of valid MESSAGE messages";
                     }
                     leaf message-invalid {
                       type uint32;
                       description "Number of invalid MESSAGE messages";
                     }
                     leaf options-valid {
                       type uint32;
                       description "Number of valid OPTIONS messages";
                     }
                     leaf options-invalid {
                       type uint32;
                       description "Number of invalid OPTIONS messages";
                     }
                     leaf info-valid {
                       type uint32;
                       description "Number of valid INFO messages";
                     }
                     leaf info-invalid {
                       type uint32;
                       description "Number of invalid INFO messages";
                     }
                     leaf update-valid {
                       type uint32;
                       description "Number of valid UPDATE messages";
                     }
                     leaf update-invalid {
                       type uint32;
                       description "Number of invalid UPDATE messages";
                     }
                     leaf refer-valid {
                       type uint32;
                       description "Number of valid REFER messages";
                     }
                     leaf refer-invalid {
                       type uint32;
                       description "Number of invalid REFER messages";
                     }
                   }
                 }
               }
               container drop-flows {
                 description "Drop flow statistics";
                 leaf max-ingress-drop-flows {
                   type string;
                   description "Maximum ingress drop flows allowed";
                 }
                 leaf max-egress-drop-flows {
                   type string;
                   description "Maximum egress drop flows allowed";
                 }
                 container drop-flows-counters {
                   leaf current-ingress-drop-flows {
                     type int32;
                     description "Current ingress drop flows count";
                   }
                   leaf current-egress-drop-flows {
                     type int32;
                     description "Current egress drop flows count";
                   }
                   leaf ingress-drop-flowlimit-drops {
                     type uint32;
                     description "Drops because ingress drop flow limit is reached";
                   }
                   leaf egress-drop-flowlimit-drops {
                     type uint32;
                     description "Drops because egress drop flow limit is reached";
                   }
                 }
               }
             }
           }
         }
       }
     }
   }
   rpc get-sfw-application-protocol-statistics {
     description "Application protocol type to use as filter";
     input {
       leaf protocol {
         description "Application protocol type to use as filter";
         type enumeration {
           enum "sip" {
             description "Session Initiation Protocol";
           }
         }
       }
     }
     output {
       container service-sfw-statistics-information {
         container summary {
           description "Stateful firewall statistics information";
           container service-sfw-statistics-entry {
             description "Stateful firewall statistics entry";
             leaf interface-name {
               type string;
               description "Name of the adaptive services interface";
             }
             container sfw-stats-service-set-entry {
               description "Stateful firewall service set statistics entry";
               container new-flow-counters {
                 description "New flow counters";
                 leaf new-flow-accepts {
                   type uint32;
                   description "Packets accepted by new flows";
                 }
                 leaf new-flow-discards {
                   type uint32;
                   description "Packets discarded by new flows";
                 }
                 leaf new-flow-rejects {
                   type uint32;
                   description "Packets rejected by new flows";
                 }
               }
               container existing-flow-counters {
                 description "Existing flow counters";
                 leaf existing-flow-accepts {
                   type uint32;
                   description "Packets accepted by existing accept flow";
                 }
                 leaf existing-flow-discards {
                   type uint32;
                   description "Packets discarded by existing drop flow";
                 }
                 leaf existing-flow-rejects {
                   type uint32;
                   description "Packets rejected by existing reject flow";
                 }
               }
               container hairpinning-counters {
                 description "Hairpinned packets count";
                 leaf slow-path-hairpinned-packets {
                   type uint32;
                   description "Initiator packets for Hairpinning";
                 }
                 leaf fast-path-hairpinned-packets {
                   type uint32;
                   description "Packets recieved on existing Hairpinned flows";
                 }
               }
               container drop_counters {
                 description "Drop counters (rules or resource exhaustion)";
                 leaf ip-option {
                   type uint32;
                   description "IP option drops";
                 }
                 leaf syn-defense {
                   type uint32;
                   description "Incomplete TCP handshakes";
                 }
                 leaf nat-ports-exhausted {
                   type uint32;
                   description "NAT ports exhausted";
                 }
                 leaf subs-flow-limit-exceeded {
                   type uint32;
                   description "Subscriber flow limit exceeded";
                 }
               }
               container error-counters {
                 description "Summarized protocol processing errors";
                 leaf ip-errors {
                   type uint32;
                   description "IP processing errors";
                 }
                 leaf tcp-errors {
                   type uint32;
                   description "TCP processing errors";
                 }
                 leaf udp-errors {
                   type uint32;
                   description "UDP processing errors";
                 }
                 leaf icmp-errors {
                   type uint32;
                   description "ICMP processing errors";
                 }
                 leaf non-ip-packets {
                   type uint32;
                   description "Non-IP packets";
                 }
                 leaf alg-errors {
                   type uint32;
                   description "ALG processing errors";
                 }
               }
               container ip-error-counters {
                 description "Extensive output of IP processing errors";
                 leaf ip-length-error {
                   type uint32;
                   description "IP packet length inconsistencies";
                 }
                 leaf ip-header-length-error {
                   type uint32;
                   description "Minimum IP header length check failures";
                 }
                 leaf long-packet {
                   type uint32;
                   description "Reassembled packet exceeds maximum IP length (65,535 bytes)";
                 }
                 leaf illegal-destination-address {
                   type uint32;
                   description "Illegal destination address";
                 }
                 leaf illegal-source-address {
                   type uint32;
                   description "Illegal source address";
                 }
                 leaf ttl-zero {
                   type uint32;
                   description "IP packets received with a TTL value of 0";
                 }
                 leaf illegal-ip-protocol {
                   type uint32;
                   description "Illegal IP protocol number ";
                 }
                 leaf non-ipv6 {
                   type uint32;
                   description "Non-IPv6 packets";
                 }
                 leaf land-attack {
                   type uint32;
                   description "IP source address same as destination address";
                 }
                 leaf not-ip-packet {
                   type uint32;
                   description "Not IP Packet";
                 }
                 leaf non-ipv4 {
                   type uint32;
                   description "Non-IPv4 packets";
                 }
                 leaf bad-checksum {
                   type uint32;
                   description "Bad checksum";
                 }
                 leaf illegal-fragment-length {
                   type uint32;
                   description "Illegal IP fragment length";
                 }
                 leaf fragment-overlap {
                   type uint32;
                   description "IP fragment overlap";
                 }
                 leaf fragment-reassembly-timeout {
                   type uint32;
                   description "IP fragment reassembly timeout";
                 }
                 leaf fragment-limit-exceeded {
                   type uint32;
                   description "IP fragment limit exceeded";
                 }
                 leaf unknown {
                   type uint32;
                   description "Unknown errors";
                 }
               }
               container tcp-error-counters {
                 description "Extensive output of TCP processing errors";
                 leaf tcp-header-length-error {
                   type uint32;
                   description "TCP header length inconsistencies";
                 }
                 leaf tcp-zero-port {
                   type uint32;
                   description "Source or destination port number is zero";
                 }
                 leaf illegal-sequence-number-flags {
                   type uint32;
                   description "Illegal sequence number and flags combinations";
                 }
                 leaf syn-attack {
                   type uint32;
                   description "SYN attack";
                 }
                 leaf non-syn-first-packet {
                   type uint32;
                   description "First packet not a SYN message";
                 }
                 leaf tcp-port-scan {
                   type uint32;
                   description "TCP port scan";
                 }
                 leaf bad-syn-cookie-response {
                   type uint32;
                   description "Bad SYN cookie response";
                 }
                 leaf tcp-recon-sequence-number-error {
                   type uint32;
                   description "TCP reconstructor sequence number error";
                 }
                 leaf tcp-recon-retransmits {
                   type uint32;
                   description "TCP reconstructor retransmissions";
                 }
                 leaf tcp-partially-opened-connection-timeout-syn-rcvd {
                   type uint32;
                   description "TCP partially opened connection timeout";
                 }
                 leaf tcp-partially-opened-connection-timeout-syn-ack-rcvd {
                   type uint32;
                   description "TCP partially opened connection timeout";
                 }
                 leaf tcp-partially-closed-connection-reuse {
                   type uint32;
                   description "TCP partially closed connection reuse";
                 }
                 leaf tcp-3way-error-client-sent-syn-ack {
                   type uint32;
                   description "TCP 3-way error - client sent SYN+ACK";
                 }
                 leaf tcp-3way-error-server-sent-ack {
                   type uint32;
                   description "TCP 3-way error - server sent ACK";
                 }
                 leaf tcp-3way-error-syn-seq-num-retrans-mismatch {
                   type uint32;
                   description "TCP 3-way error - SYN seq number retransmission mismatch";
                 }
                 leaf tcp-3way-error-rst-seq-num-mismatch {
                   type uint32;
                   description "TCP 3-way error - RST seq number mismatch";
                 }
                 leaf tcp-3way-error-fin-received {
                   type uint32;
                   description "TCP 3-way error - FIN received";
                 }
                 leaf tcp-3way-error-invalid-flags {
                   type uint32;
                   description "TCP 3-way error - invalid TCP flag combination";
                 }
                 leaf tcp-3way-error-syn-no-flow-initiator {
                   type uint32;
                   description "TCP 3-way error - SYN recvd but no client flows";
                 }
                 leaf tcp-3way-error-first-packet-syn-ack {
                   type uint32;
                   description "TCP 3-way error - first packet SYN+ACK";
                 }
                 leaf tcp-3way-error-first-packet-fin-ack {
                   type uint32;
                   description "TCP 3-way error - first packet FIN+ACK";
                 }
                 leaf tcp-3way-error-first-packet-fin {
                   type uint32;
                   description "TCP 3-way error - first packet FIN";
                 }
                 leaf tcp-3way-error-first-packet-rst {
                   type uint32;
                   description "TCP 3-way error - first packet RST";
                 }
                 leaf tcp-3way-error-first-packet-ack {
                   type uint32;
                   description "TCP 3-way error - first packet ack";
                 }
                 leaf tcp-3way-error-first-packet-invalid-flags {
                   type uint32;
                   description "TCP 3-way error - first packet ack";
                 }
                 leaf tcp-close-error-no-final-ack {
                   type uint32;
                   description "TCP close error - no final ack";
                 }
                 leaf tcp-resumed-flow {
                   type uint32;
                   description "TCP Resumed Flow";
                 }
               }
               container udp-error-counters {
                 description "Extensive output of UDP processing errors";
                 leaf udp-header-length-error {
                   type uint32;
                   description "IP data length is less than minimum UDP header length (8 bytes)";
                 }
                 leaf udp-zero-port {
                   type uint32;
                   description "Source or destination port number is zero";
                 }
                 leaf udp-port-scan {
                   type uint32;
                   description "UDP port scan (ICMP error seen for UDP flow)";
                 }
               }
               container icmp-error-counters {
                 description "Extensive output of ICMP processing errors";
                 leaf icmp-length-error {
                   type uint32;
                   description "IP data length less than minimum ICMP header length (8 bytes)";
                 }
                 leaf icmp-error-length-error {
                   type uint32;
                   description "ICMP error length inconsistencies";
                 }
                 leaf ping-duplicate-sequence-number {
                   type uint32;
                   description "Duplicate ping sequence number";
                 }
                 leaf ping-mismatched-sequence-number {
                   type uint32;
                   description "Mismatched ping sequence number";
                 }
                 leaf icmp-error-no-matching-flow {
                   type uint32;
                   description "No matching flow for ICMP error packet";
                 }
               }
               container alg-error-counters {
                 description "Extensive output of ALG processing errors";
                 leaf alg-bootp-errors {
                   type uint32;
                   description "ALG BOOTP errors";
                 }
                 leaf alg-dce-rpc-errors {
                   type uint32;
                   description "ALG DCE-RPC errors";
                 }
                 leaf alg-dce-rpc-portmap-errors {
                   type uint32;
                   description "ALG DCE-RPC portmap errors";
                 }
                 leaf alg-dns-errors {
                   type uint32;
                   description "ALG DNS errors";
                 }
                 leaf alg-exec-errors {
                   type uint32;
                   description "ALG exec errors";
                 }
                 leaf alg-ftp-errors {
                   type uint32;
                   description "ALG FTP errors";
                 }
                 leaf alg-h323-errors {
                   type uint32;
                   description "ALG H323 errors";
                 }
                 leaf alg-icmp-errors {
                   type uint32;
                   description "ALG ICMP errors";
                 }
                 leaf alg-iiop-errors {
                   type uint32;
                   description "ALG IIOP errors";
                 }
                 leaf alg-login-errors {
                   type uint32;
                   description "ALG login errors";
                 }
                 leaf alg-netbios-errors {
                   type uint32;
                   description "ALG NetBIOS errors";
                 }
                 leaf alg-netshow-errors {
                   type uint32;
                   description "ALG NetShow errors";
                 }
                 leaf alg-realaudio-errors {
                   type uint32;
                   description "ALG Real Audio errors";
                 }
                 leaf alg-rpc-errors {
                   type uint32;
                   description "ALG RPC errors";
                 }
                 leaf alg-rpc-portmap-errors {
                   type uint32;
                   description "ALG RPC portmap errors";
                 }
                 leaf alg-rtsp-errors {
                   type uint32;
                   description "ALG Real-Time Streaming Protocol errors";
                 }
                 leaf alg-shell-errors {
                   type uint32;
                   description "ALG shell errors";
                 }
                 leaf alg-sip-errors {
                   type uint32;
                   description "ALG Session Initiation Protocol errors";
                 }
                 leaf alg-snmp-errors {
                   type uint32;
                   description "ALG SNMP errors";
                 }
                 leaf alg-sqlnet-errors {
                   type uint32;
                   description "ALG SQLNet errors";
                 }
                 leaf alg-tftp-errors {
                   type uint32;
                   description "ALG TFTP errors";
                 }
                 leaf alg-traceroute-errors {
                   type uint32;
                   description "ALG traceroute errors";
                 }
               }
               container sip-alg-counters {
                 description "SIP statistics";
                 container alg-sip {
                   description "SIP statistics";
                   container total-counters {
                     description "Total statistics";
                     leaf total-messages {
                       type uint32;
                       description "Total SIP messages";
                     }
                     leaf call-segments {
                       type uint32;
                       description "SIP call segments";
                     }
                   }
                   container parser-counters {
                     description "Parser statistics";
                     leaf syntax-errors {
                       type uint32;
                       description "SIP syntax errors";
                     }
                     leaf content-errors {
                       type uint32;
                       description "SIP message content errors";
                     }
                     leaf unknown-methods {
                       type uint32;
                       description "SIP unknown methods";
                     }
                   }
                   container message-counters {
                     description "SIP message counters";
                     leaf response-provisional {
                       type uint32;
                       description "Number of provisional responses";
                     }
                     leaf response-invite-ok {
                       type uint32;
                       description "Number of 'OK' responses to INVITE messages";
                     }
                     leaf response-non-invite-ok {
                       type uint32;
                       description "Number of 'OK' responses to messages other than INVITE";
                     }
                     leaf response-redir {
                       type uint32;
                       description "Number of redirection (3xx) responses";
                     }
                     leaf response-request-failure {
                       type uint32;
                       description "Number of request failure (4xx) responses";
                     }
                     leaf response-server-failure {
                       type uint32;
                       description "Number of server failure (5xx) responses";
                     }
                     leaf response-global-failure {
                       type uint32;
                       description "Number of global failure (6xx) responses";
                     }
                     leaf response-invalid {
                       type uint32;
                       description "Number of invalid responses";
                     }
                     leaf response-retransmits {
                       type uint32;
                       description "Number of response retransmissions";
                     }
                     leaf register-new {
                       type uint32;
                       description "Number of REGISTER messages";
                     }
                     leaf invite-new {
                       type uint32;
                       description "Number of new INVITE messages";
                     }
                     leaf invite-retransmits {
                       type uint32;
                       description "Number of INVITE message retransmissions";
                     }
                     leaf reinvites {
                       type uint32;
                       description "Number of ReINVITE messages";
                     }
                     leaf cancel-valid {
                       type uint32;
                       description "Number of valid CANCEL messages";
                     }
                     leaf cancel-invalid {
                       type uint32;
                       description "Number of invalid CANCEL messages";
                     }
                     leaf ack-valid {
                       type uint32;
                       description "Number of valid ACK messages";
                     }
                     leaf ack-invalid {
                       type uint32;
                       description "Number of invalid ACK messages";
                     }
                     leaf ack-retransmits {
                       type uint32;
                       description "Number of ACK message retransmissions";
                     }
                     leaf bye-valid {
                       type uint32;
                       description "Number of valid BYE messages";
                     }
                     leaf bye-invalid {
                       type uint32;
                       description "Number of invalid BYE messages";
                     }
                     leaf subscribe-valid {
                       type uint32;
                       description "Number of valid SUBSCRIBE messages";
                     }
                     leaf subscribe-invalid {
                       type uint32;
                       description "Number of invalid SUBSCRIBE messages";
                     }
                     leaf notify-valid {
                       type uint32;
                       description "Number of valid NOTIFY messages";
                     }
                     leaf notify-invalid {
                       type uint32;
                       description "Number of invalid NOTIFY messages";
                     }
                     leaf message-valid {
                       type uint32;
                       description "Number of valid MESSAGE messages";
                     }
                     leaf message-invalid {
                       type uint32;
                       description "Number of invalid MESSAGE messages";
                     }
                     leaf options-valid {
                       type uint32;
                       description "Number of valid OPTIONS messages";
                     }
                     leaf options-invalid {
                       type uint32;
                       description "Number of invalid OPTIONS messages";
                     }
                     leaf info-valid {
                       type uint32;
                       description "Number of valid INFO messages";
                     }
                     leaf info-invalid {
                       type uint32;
                       description "Number of invalid INFO messages";
                     }
                     leaf update-valid {
                       type uint32;
                       description "Number of valid UPDATE messages";
                     }
                     leaf update-invalid {
                       type uint32;
                       description "Number of invalid UPDATE messages";
                     }
                     leaf refer-valid {
                       type uint32;
                       description "Number of valid REFER messages";
                     }
                     leaf refer-invalid {
                       type uint32;
                       description "Number of invalid REFER messages";
                     }
                   }
                 }
               }
               container drop-flows {
                 description "Drop flow statistics";
                 leaf max-ingress-drop-flows {
                   type string;
                   description "Maximum ingress drop flows allowed";
                 }
                 leaf max-egress-drop-flows {
                   type string;
                   description "Maximum egress drop flows allowed";
                 }
                 container drop-flows-counters {
                   leaf current-ingress-drop-flows {
                     type int32;
                     description "Current ingress drop flows count";
                   }
                   leaf current-egress-drop-flows {
                     type int32;
                     description "Current egress drop flows count";
                   }
                   leaf ingress-drop-flowlimit-drops {
                     type uint32;
                     description "Drops because ingress drop flow limit is reached";
                   }
                   leaf egress-drop-flowlimit-drops {
                     type uint32;
                     description "Drops because egress drop flow limit is reached";
                   }
                 }
               }
             }
           }
         }
         container brief {
           description "Stateful firewall statistics information";
           container service-sfw-statistics-entry {
             description "Stateful firewall statistics entry";
             leaf interface-name {
               type string;
               description "Name of the adaptive services interface";
             }
             container sfw-stats-service-set-entry {
               description "Stateful firewall service set statistics entry";
               container new-flow-counters {
                 description "New flow counters";
                 leaf new-flow-accepts {
                   type uint32;
                   description "Packets accepted by new flows";
                 }
                 leaf new-flow-discards {
                   type uint32;
                   description "Packets discarded by new flows";
                 }
                 leaf new-flow-rejects {
                   type uint32;
                   description "Packets rejected by new flows";
                 }
               }
               container existing-flow-counters {
                 description "Existing flow counters";
                 leaf existing-flow-accepts {
                   type uint32;
                   description "Packets accepted by existing accept flow";
                 }
                 leaf existing-flow-discards {
                   type uint32;
                   description "Packets discarded by existing drop flow";
                 }
                 leaf existing-flow-rejects {
                   type uint32;
                   description "Packets rejected by existing reject flow";
                 }
               }
               container hairpinning-counters {
                 description "Hairpinned packets count";
                 leaf slow-path-hairpinned-packets {
                   type uint32;
                   description "Initiator packets for Hairpinning";
                 }
                 leaf fast-path-hairpinned-packets {
                   type uint32;
                   description "Packets recieved on existing Hairpinned flows";
                 }
               }
               container drop_counters {
                 description "Drop counters (rules or resource exhaustion)";
                 leaf ip-option {
                   type uint32;
                   description "IP option drops";
                 }
                 leaf syn-defense {
                   type uint32;
                   description "Incomplete TCP handshakes";
                 }
                 leaf nat-ports-exhausted {
                   type uint32;
                   description "NAT ports exhausted";
                 }
                 leaf subs-flow-limit-exceeded {
                   type uint32;
                   description "Subscriber flow limit exceeded";
                 }
               }
               container error-counters {
                 description "Summarized protocol processing errors";
                 leaf ip-errors {
                   type uint32;
                   description "IP processing errors";
                 }
                 leaf tcp-errors {
                   type uint32;
                   description "TCP processing errors";
                 }
                 leaf udp-errors {
                   type uint32;
                   description "UDP processing errors";
                 }
                 leaf icmp-errors {
                   type uint32;
                   description "ICMP processing errors";
                 }
                 leaf non-ip-packets {
                   type uint32;
                   description "Non-IP packets";
                 }
                 leaf alg-errors {
                   type uint32;
                   description "ALG processing errors";
                 }
               }
               container ip-error-counters {
                 description "Extensive output of IP processing errors";
                 leaf ip-length-error {
                   type uint32;
                   description "IP packet length inconsistencies";
                 }
                 leaf ip-header-length-error {
                   type uint32;
                   description "Minimum IP header length check failures";
                 }
                 leaf long-packet {
                   type uint32;
                   description "Reassembled packet exceeds maximum IP length (65,535 bytes)";
                 }
                 leaf illegal-destination-address {
                   type uint32;
                   description "Illegal destination address";
                 }
                 leaf illegal-source-address {
                   type uint32;
                   description "Illegal source address";
                 }
                 leaf ttl-zero {
                   type uint32;
                   description "IP packets received with a TTL value of 0";
                 }
                 leaf illegal-ip-protocol {
                   type uint32;
                   description "Illegal IP protocol number ";
                 }
                 leaf non-ipv6 {
                   type uint32;
                   description "Non-IPv6 packets";
                 }
                 leaf land-attack {
                   type uint32;
                   description "IP source address same as destination address";
                 }
                 leaf not-ip-packet {
                   type uint32;
                   description "Not IP Packet";
                 }
                 leaf non-ipv4 {
                   type uint32;
                   description "Non-IPv4 packets";
                 }
                 leaf bad-checksum {
                   type uint32;
                   description "Bad checksum";
                 }
                 leaf illegal-fragment-length {
                   type uint32;
                   description "Illegal IP fragment length";
                 }
                 leaf fragment-overlap {
                   type uint32;
                   description "IP fragment overlap";
                 }
                 leaf fragment-reassembly-timeout {
                   type uint32;
                   description "IP fragment reassembly timeout";
                 }
                 leaf fragment-limit-exceeded {
                   type uint32;
                   description "IP fragment limit exceeded";
                 }
                 leaf unknown {
                   type uint32;
                   description "Unknown errors";
                 }
               }
               container tcp-error-counters {
                 description "Extensive output of TCP processing errors";
                 leaf tcp-header-length-error {
                   type uint32;
                   description "TCP header length inconsistencies";
                 }
                 leaf tcp-zero-port {
                   type uint32;
                   description "Source or destination port number is zero";
                 }
                 leaf illegal-sequence-number-flags {
                   type uint32;
                   description "Illegal sequence number and flags combinations";
                 }
                 leaf syn-attack {
                   type uint32;
                   description "SYN attack";
                 }
                 leaf non-syn-first-packet {
                   type uint32;
                   description "First packet not a SYN message";
                 }
                 leaf tcp-port-scan {
                   type uint32;
                   description "TCP port scan";
                 }
                 leaf bad-syn-cookie-response {
                   type uint32;
                   description "Bad SYN cookie response";
                 }
                 leaf tcp-recon-sequence-number-error {
                   type uint32;
                   description "TCP reconstructor sequence number error";
                 }
                 leaf tcp-recon-retransmits {
                   type uint32;
                   description "TCP reconstructor retransmissions";
                 }
                 leaf tcp-partially-opened-connection-timeout-syn-rcvd {
                   type uint32;
                   description "TCP partially opened connection timeout";
                 }
                 leaf tcp-partially-opened-connection-timeout-syn-ack-rcvd {
                   type uint32;
                   description "TCP partially opened connection timeout";
                 }
                 leaf tcp-partially-closed-connection-reuse {
                   type uint32;
                   description "TCP partially closed connection reuse";
                 }
                 leaf tcp-3way-error-client-sent-syn-ack {
                   type uint32;
                   description "TCP 3-way error - client sent SYN+ACK";
                 }
                 leaf tcp-3way-error-server-sent-ack {
                   type uint32;
                   description "TCP 3-way error - server sent ACK";
                 }
                 leaf tcp-3way-error-syn-seq-num-retrans-mismatch {
                   type uint32;
                   description "TCP 3-way error - SYN seq number retransmission mismatch";
                 }
                 leaf tcp-3way-error-rst-seq-num-mismatch {
                   type uint32;
                   description "TCP 3-way error - RST seq number mismatch";
                 }
                 leaf tcp-3way-error-fin-received {
                   type uint32;
                   description "TCP 3-way error - FIN received";
                 }
                 leaf tcp-3way-error-invalid-flags {
                   type uint32;
                   description "TCP 3-way error - invalid TCP flag combination";
                 }
                 leaf tcp-3way-error-syn-no-flow-initiator {
                   type uint32;
                   description "TCP 3-way error - SYN recvd but no client flows";
                 }
                 leaf tcp-3way-error-first-packet-syn-ack {
                   type uint32;
                   description "TCP 3-way error - first packet SYN+ACK";
                 }
                 leaf tcp-3way-error-first-packet-fin-ack {
                   type uint32;
                   description "TCP 3-way error - first packet FIN+ACK";
                 }
                 leaf tcp-3way-error-first-packet-fin {
                   type uint32;
                   description "TCP 3-way error - first packet FIN";
                 }
                 leaf tcp-3way-error-first-packet-rst {
                   type uint32;
                   description "TCP 3-way error - first packet RST";
                 }
                 leaf tcp-3way-error-first-packet-ack {
                   type uint32;
                   description "TCP 3-way error - first packet ack";
                 }
                 leaf tcp-3way-error-first-packet-invalid-flags {
                   type uint32;
                   description "TCP 3-way error - first packet ack";
                 }
                 leaf tcp-close-error-no-final-ack {
                   type uint32;
                   description "TCP close error - no final ack";
                 }
                 leaf tcp-resumed-flow {
                   type uint32;
                   description "TCP Resumed Flow";
                 }
               }
               container udp-error-counters {
                 description "Extensive output of UDP processing errors";
                 leaf udp-header-length-error {
                   type uint32;
                   description "IP data length is less than minimum UDP header length (8 bytes)";
                 }
                 leaf udp-zero-port {
                   type uint32;
                   description "Source or destination port number is zero";
                 }
                 leaf udp-port-scan {
                   type uint32;
                   description "UDP port scan (ICMP error seen for UDP flow)";
                 }
               }
               container icmp-error-counters {
                 description "Extensive output of ICMP processing errors";
                 leaf icmp-length-error {
                   type uint32;
                   description "IP data length less than minimum ICMP header length (8 bytes)";
                 }
                 leaf icmp-error-length-error {
                   type uint32;
                   description "ICMP error length inconsistencies";
                 }
                 leaf ping-duplicate-sequence-number {
                   type uint32;
                   description "Duplicate ping sequence number";
                 }
                 leaf ping-mismatched-sequence-number {
                   type uint32;
                   description "Mismatched ping sequence number";
                 }
                 leaf icmp-error-no-matching-flow {
                   type uint32;
                   description "No matching flow for ICMP error packet";
                 }
               }
               container alg-error-counters {
                 description "Extensive output of ALG processing errors";
                 leaf alg-bootp-errors {
                   type uint32;
                   description "ALG BOOTP errors";
                 }
                 leaf alg-dce-rpc-errors {
                   type uint32;
                   description "ALG DCE-RPC errors";
                 }
                 leaf alg-dce-rpc-portmap-errors {
                   type uint32;
                   description "ALG DCE-RPC portmap errors";
                 }
                 leaf alg-dns-errors {
                   type uint32;
                   description "ALG DNS errors";
                 }
                 leaf alg-exec-errors {
                   type uint32;
                   description "ALG exec errors";
                 }
                 leaf alg-ftp-errors {
                   type uint32;
                   description "ALG FTP errors";
                 }
                 leaf alg-h323-errors {
                   type uint32;
                   description "ALG H323 errors";
                 }
                 leaf alg-icmp-errors {
                   type uint32;
                   description "ALG ICMP errors";
                 }
                 leaf alg-iiop-errors {
                   type uint32;
                   description "ALG IIOP errors";
                 }
                 leaf alg-login-errors {
                   type uint32;
                   description "ALG login errors";
                 }
                 leaf alg-netbios-errors {
                   type uint32;
                   description "ALG NetBIOS errors";
                 }
                 leaf alg-netshow-errors {
                   type uint32;
                   description "ALG NetShow errors";
                 }
                 leaf alg-realaudio-errors {
                   type uint32;
                   description "ALG Real Audio errors";
                 }
                 leaf alg-rpc-errors {
                   type uint32;
                   description "ALG RPC errors";
                 }
                 leaf alg-rpc-portmap-errors {
                   type uint32;
                   description "ALG RPC portmap errors";
                 }
                 leaf alg-rtsp-errors {
                   type uint32;
                   description "ALG Real-Time Streaming Protocol errors";
                 }
                 leaf alg-shell-errors {
                   type uint32;
                   description "ALG shell errors";
                 }
                 leaf alg-sip-errors {
                   type uint32;
                   description "ALG Session Initiation Protocol errors";
                 }
                 leaf alg-snmp-errors {
                   type uint32;
                   description "ALG SNMP errors";
                 }
                 leaf alg-sqlnet-errors {
                   type uint32;
                   description "ALG SQLNet errors";
                 }
                 leaf alg-tftp-errors {
                   type uint32;
                   description "ALG TFTP errors";
                 }
                 leaf alg-traceroute-errors {
                   type uint32;
                   description "ALG traceroute errors";
                 }
               }
               container sip-alg-counters {
                 description "SIP statistics";
                 container alg-sip {
                   description "SIP statistics";
                   container total-counters {
                     description "Total statistics";
                     leaf total-messages {
                       type uint32;
                       description "Total SIP messages";
                     }
                     leaf call-segments {
                       type uint32;
                       description "SIP call segments";
                     }
                   }
                   container parser-counters {
                     description "Parser statistics";
                     leaf syntax-errors {
                       type uint32;
                       description "SIP syntax errors";
                     }
                     leaf content-errors {
                       type uint32;
                       description "SIP message content errors";
                     }
                     leaf unknown-methods {
                       type uint32;
                       description "SIP unknown methods";
                     }
                   }
                   container message-counters {
                     description "SIP message counters";
                     leaf response-provisional {
                       type uint32;
                       description "Number of provisional responses";
                     }
                     leaf response-invite-ok {
                       type uint32;
                       description "Number of 'OK' responses to INVITE messages";
                     }
                     leaf response-non-invite-ok {
                       type uint32;
                       description "Number of 'OK' responses to messages other than INVITE";
                     }
                     leaf response-redir {
                       type uint32;
                       description "Number of redirection (3xx) responses";
                     }
                     leaf response-request-failure {
                       type uint32;
                       description "Number of request failure (4xx) responses";
                     }
                     leaf response-server-failure {
                       type uint32;
                       description "Number of server failure (5xx) responses";
                     }
                     leaf response-global-failure {
                       type uint32;
                       description "Number of global failure (6xx) responses";
                     }
                     leaf response-invalid {
                       type uint32;
                       description "Number of invalid responses";
                     }
                     leaf response-retransmits {
                       type uint32;
                       description "Number of response retransmissions";
                     }
                     leaf register-new {
                       type uint32;
                       description "Number of REGISTER messages";
                     }
                     leaf invite-new {
                       type uint32;
                       description "Number of new INVITE messages";
                     }
                     leaf invite-retransmits {
                       type uint32;
                       description "Number of INVITE message retransmissions";
                     }
                     leaf reinvites {
                       type uint32;
                       description "Number of ReINVITE messages";
                     }
                     leaf cancel-valid {
                       type uint32;
                       description "Number of valid CANCEL messages";
                     }
                     leaf cancel-invalid {
                       type uint32;
                       description "Number of invalid CANCEL messages";
                     }
                     leaf ack-valid {
                       type uint32;
                       description "Number of valid ACK messages";
                     }
                     leaf ack-invalid {
                       type uint32;
                       description "Number of invalid ACK messages";
                     }
                     leaf ack-retransmits {
                       type uint32;
                       description "Number of ACK message retransmissions";
                     }
                     leaf bye-valid {
                       type uint32;
                       description "Number of valid BYE messages";
                     }
                     leaf bye-invalid {
                       type uint32;
                       description "Number of invalid BYE messages";
                     }
                     leaf subscribe-valid {
                       type uint32;
                       description "Number of valid SUBSCRIBE messages";
                     }
                     leaf subscribe-invalid {
                       type uint32;
                       description "Number of invalid SUBSCRIBE messages";
                     }
                     leaf notify-valid {
                       type uint32;
                       description "Number of valid NOTIFY messages";
                     }
                     leaf notify-invalid {
                       type uint32;
                       description "Number of invalid NOTIFY messages";
                     }
                     leaf message-valid {
                       type uint32;
                       description "Number of valid MESSAGE messages";
                     }
                     leaf message-invalid {
                       type uint32;
                       description "Number of invalid MESSAGE messages";
                     }
                     leaf options-valid {
                       type uint32;
                       description "Number of valid OPTIONS messages";
                     }
                     leaf options-invalid {
                       type uint32;
                       description "Number of invalid OPTIONS messages";
                     }
                     leaf info-valid {
                       type uint32;
                       description "Number of valid INFO messages";
                     }
                     leaf info-invalid {
                       type uint32;
                       description "Number of invalid INFO messages";
                     }
                     leaf update-valid {
                       type uint32;
                       description "Number of valid UPDATE messages";
                     }
                     leaf update-invalid {
                       type uint32;
                       description "Number of invalid UPDATE messages";
                     }
                     leaf refer-valid {
                       type uint32;
                       description "Number of valid REFER messages";
                     }
                     leaf refer-invalid {
                       type uint32;
                       description "Number of invalid REFER messages";
                     }
                   }
                 }
               }
               container drop-flows {
                 description "Drop flow statistics";
                 leaf max-ingress-drop-flows {
                   type string;
                   description "Maximum ingress drop flows allowed";
                 }
                 leaf max-egress-drop-flows {
                   type string;
                   description "Maximum egress drop flows allowed";
                 }
                 container drop-flows-counters {
                   leaf current-ingress-drop-flows {
                     type int32;
                     description "Current ingress drop flows count";
                   }
                   leaf current-egress-drop-flows {
                     type int32;
                     description "Current egress drop flows count";
                   }
                   leaf ingress-drop-flowlimit-drops {
                     type uint32;
                     description "Drops because ingress drop flow limit is reached";
                   }
                   leaf egress-drop-flowlimit-drops {
                     type uint32;
                     description "Drops because egress drop flow limit is reached";
                   }
                 }
               }
             }
           }
         }
         container detail {
           description "Stateful firewall statistics information";
           container service-sfw-statistics-entry {
             description "Stateful firewall statistics entry";
             leaf interface-name {
               type string;
               description "Name of the adaptive services interface";
             }
             container sfw-stats-service-set-entry {
               description "Stateful firewall service set statistics entry";
               container new-flow-counters {
                 description "New flow counters";
                 leaf new-flow-accepts {
                   type uint32;
                   description "Packets accepted by new flows";
                 }
                 leaf new-flow-discards {
                   type uint32;
                   description "Packets discarded by new flows";
                 }
                 leaf new-flow-rejects {
                   type uint32;
                   description "Packets rejected by new flows";
                 }
               }
               container existing-flow-counters {
                 description "Existing flow counters";
                 leaf existing-flow-accepts {
                   type uint32;
                   description "Packets accepted by existing accept flow";
                 }
                 leaf existing-flow-discards {
                   type uint32;
                   description "Packets discarded by existing drop flow";
                 }
                 leaf existing-flow-rejects {
                   type uint32;
                   description "Packets rejected by existing reject flow";
                 }
               }
               container hairpinning-counters {
                 description "Hairpinned packets count";
                 leaf slow-path-hairpinned-packets {
                   type uint32;
                   description "Initiator packets for Hairpinning";
                 }
                 leaf fast-path-hairpinned-packets {
                   type uint32;
                   description "Packets recieved on existing Hairpinned flows";
                 }
               }
               container drop_counters {
                 description "Drop counters (rules or resource exhaustion)";
                 leaf ip-option {
                   type uint32;
                   description "IP option drops";
                 }
                 leaf syn-defense {
                   type uint32;
                   description "Incomplete TCP handshakes";
                 }
                 leaf nat-ports-exhausted {
                   type uint32;
                   description "NAT ports exhausted";
                 }
                 leaf subs-flow-limit-exceeded {
                   type uint32;
                   description "Subscriber flow limit exceeded";
                 }
               }
               container error-counters {
                 description "Summarized protocol processing errors";
                 leaf ip-errors {
                   type uint32;
                   description "IP processing errors";
                 }
                 leaf tcp-errors {
                   type uint32;
                   description "TCP processing errors";
                 }
                 leaf udp-errors {
                   type uint32;
                   description "UDP processing errors";
                 }
                 leaf icmp-errors {
                   type uint32;
                   description "ICMP processing errors";
                 }
                 leaf non-ip-packets {
                   type uint32;
                   description "Non-IP packets";
                 }
                 leaf alg-errors {
                   type uint32;
                   description "ALG processing errors";
                 }
               }
               container ip-error-counters {
                 description "Extensive output of IP processing errors";
                 leaf ip-length-error {
                   type uint32;
                   description "IP packet length inconsistencies";
                 }
                 leaf ip-header-length-error {
                   type uint32;
                   description "Minimum IP header length check failures";
                 }
                 leaf long-packet {
                   type uint32;
                   description "Reassembled packet exceeds maximum IP length (65,535 bytes)";
                 }
                 leaf illegal-destination-address {
                   type uint32;
                   description "Illegal destination address";
                 }
                 leaf illegal-source-address {
                   type uint32;
                   description "Illegal source address";
                 }
                 leaf ttl-zero {
                   type uint32;
                   description "IP packets received with a TTL value of 0";
                 }
                 leaf illegal-ip-protocol {
                   type uint32;
                   description "Illegal IP protocol number ";
                 }
                 leaf non-ipv6 {
                   type uint32;
                   description "Non-IPv6 packets";
                 }
                 leaf land-attack {
                   type uint32;
                   description "IP source address same as destination address";
                 }
                 leaf not-ip-packet {
                   type uint32;
                   description "Not IP Packet";
                 }
                 leaf non-ipv4 {
                   type uint32;
                   description "Non-IPv4 packets";
                 }
                 leaf bad-checksum {
                   type uint32;
                   description "Bad checksum";
                 }
                 leaf illegal-fragment-length {
                   type uint32;
                   description "Illegal IP fragment length";
                 }
                 leaf fragment-overlap {
                   type uint32;
                   description "IP fragment overlap";
                 }
                 leaf fragment-reassembly-timeout {
                   type uint32;
                   description "IP fragment reassembly timeout";
                 }
                 leaf fragment-limit-exceeded {
                   type uint32;
                   description "IP fragment limit exceeded";
                 }
                 leaf unknown {
                   type uint32;
                   description "Unknown errors";
                 }
               }
               container tcp-error-counters {
                 description "Extensive output of TCP processing errors";
                 leaf tcp-header-length-error {
                   type uint32;
                   description "TCP header length inconsistencies";
                 }
                 leaf tcp-zero-port {
                   type uint32;
                   description "Source or destination port number is zero";
                 }
                 leaf illegal-sequence-number-flags {
                   type uint32;
                   description "Illegal sequence number and flags combinations";
                 }
                 leaf syn-attack {
                   type uint32;
                   description "SYN attack";
                 }
                 leaf non-syn-first-packet {
                   type uint32;
                   description "First packet not a SYN message";
                 }
                 leaf tcp-port-scan {
                   type uint32;
                   description "TCP port scan";
                 }
                 leaf bad-syn-cookie-response {
                   type uint32;
                   description "Bad SYN cookie response";
                 }
                 leaf tcp-recon-sequence-number-error {
                   type uint32;
                   description "TCP reconstructor sequence number error";
                 }
                 leaf tcp-recon-retransmits {
                   type uint32;
                   description "TCP reconstructor retransmissions";
                 }
                 leaf tcp-partially-opened-connection-timeout-syn-rcvd {
                   type uint32;
                   description "TCP partially opened connection timeout";
                 }
                 leaf tcp-partially-opened-connection-timeout-syn-ack-rcvd {
                   type uint32;
                   description "TCP partially opened connection timeout";
                 }
                 leaf tcp-partially-closed-connection-reuse {
                   type uint32;
                   description "TCP partially closed connection reuse";
                 }
                 leaf tcp-3way-error-client-sent-syn-ack {
                   type uint32;
                   description "TCP 3-way error - client sent SYN+ACK";
                 }
                 leaf tcp-3way-error-server-sent-ack {
                   type uint32;
                   description "TCP 3-way error - server sent ACK";
                 }
                 leaf tcp-3way-error-syn-seq-num-retrans-mismatch {
                   type uint32;
                   description "TCP 3-way error - SYN seq number retransmission mismatch";
                 }
                 leaf tcp-3way-error-rst-seq-num-mismatch {
                   type uint32;
                   description "TCP 3-way error - RST seq number mismatch";
                 }
                 leaf tcp-3way-error-fin-received {
                   type uint32;
                   description "TCP 3-way error - FIN received";
                 }
                 leaf tcp-3way-error-invalid-flags {
                   type uint32;
                   description "TCP 3-way error - invalid TCP flag combination";
                 }
                 leaf tcp-3way-error-syn-no-flow-initiator {
                   type uint32;
                   description "TCP 3-way error - SYN recvd but no client flows";
                 }
                 leaf tcp-3way-error-first-packet-syn-ack {
                   type uint32;
                   description "TCP 3-way error - first packet SYN+ACK";
                 }
                 leaf tcp-3way-error-first-packet-fin-ack {
                   type uint32;
                   description "TCP 3-way error - first packet FIN+ACK";
                 }
                 leaf tcp-3way-error-first-packet-fin {
                   type uint32;
                   description "TCP 3-way error - first packet FIN";
                 }
                 leaf tcp-3way-error-first-packet-rst {
                   type uint32;
                   description "TCP 3-way error - first packet RST";
                 }
                 leaf tcp-3way-error-first-packet-ack {
                   type uint32;
                   description "TCP 3-way error - first packet ack";
                 }
                 leaf tcp-3way-error-first-packet-invalid-flags {
                   type uint32;
                   description "TCP 3-way error - first packet ack";
                 }
                 leaf tcp-close-error-no-final-ack {
                   type uint32;
                   description "TCP close error - no final ack";
                 }
                 leaf tcp-resumed-flow {
                   type uint32;
                   description "TCP Resumed Flow";
                 }
               }
               container udp-error-counters {
                 description "Extensive output of UDP processing errors";
                 leaf udp-header-length-error {
                   type uint32;
                   description "IP data length is less than minimum UDP header length (8 bytes)";
                 }
                 leaf udp-zero-port {
                   type uint32;
                   description "Source or destination port number is zero";
                 }
                 leaf udp-port-scan {
                   type uint32;
                   description "UDP port scan (ICMP error seen for UDP flow)";
                 }
               }
               container icmp-error-counters {
                 description "Extensive output of ICMP processing errors";
                 leaf icmp-length-error {
                   type uint32;
                   description "IP data length less than minimum ICMP header length (8 bytes)";
                 }
                 leaf icmp-error-length-error {
                   type uint32;
                   description "ICMP error length inconsistencies";
                 }
                 leaf ping-duplicate-sequence-number {
                   type uint32;
                   description "Duplicate ping sequence number";
                 }
                 leaf ping-mismatched-sequence-number {
                   type uint32;
                   description "Mismatched ping sequence number";
                 }
                 leaf icmp-error-no-matching-flow {
                   type uint32;
                   description "No matching flow for ICMP error packet";
                 }
               }
               container alg-error-counters {
                 description "Extensive output of ALG processing errors";
                 leaf alg-bootp-errors {
                   type uint32;
                   description "ALG BOOTP errors";
                 }
                 leaf alg-dce-rpc-errors {
                   type uint32;
                   description "ALG DCE-RPC errors";
                 }
                 leaf alg-dce-rpc-portmap-errors {
                   type uint32;
                   description "ALG DCE-RPC portmap errors";
                 }
                 leaf alg-dns-errors {
                   type uint32;
                   description "ALG DNS errors";
                 }
                 leaf alg-exec-errors {
                   type uint32;
                   description "ALG exec errors";
                 }
                 leaf alg-ftp-errors {
                   type uint32;
                   description "ALG FTP errors";
                 }
                 leaf alg-h323-errors {
                   type uint32;
                   description "ALG H323 errors";
                 }
                 leaf alg-icmp-errors {
                   type uint32;
                   description "ALG ICMP errors";
                 }
                 leaf alg-iiop-errors {
                   type uint32;
                   description "ALG IIOP errors";
                 }
                 leaf alg-login-errors {
                   type uint32;
                   description "ALG login errors";
                 }
                 leaf alg-netbios-errors {
                   type uint32;
                   description "ALG NetBIOS errors";
                 }
                 leaf alg-netshow-errors {
                   type uint32;
                   description "ALG NetShow errors";
                 }
                 leaf alg-realaudio-errors {
                   type uint32;
                   description "ALG Real Audio errors";
                 }
                 leaf alg-rpc-errors {
                   type uint32;
                   description "ALG RPC errors";
                 }
                 leaf alg-rpc-portmap-errors {
                   type uint32;
                   description "ALG RPC portmap errors";
                 }
                 leaf alg-rtsp-errors {
                   type uint32;
                   description "ALG Real-Time Streaming Protocol errors";
                 }
                 leaf alg-shell-errors {
                   type uint32;
                   description "ALG shell errors";
                 }
                 leaf alg-sip-errors {
                   type uint32;
                   description "ALG Session Initiation Protocol errors";
                 }
                 leaf alg-snmp-errors {
                   type uint32;
                   description "ALG SNMP errors";
                 }
                 leaf alg-sqlnet-errors {
                   type uint32;
                   description "ALG SQLNet errors";
                 }
                 leaf alg-tftp-errors {
                   type uint32;
                   description "ALG TFTP errors";
                 }
                 leaf alg-traceroute-errors {
                   type uint32;
                   description "ALG traceroute errors";
                 }
               }
               container sip-alg-counters {
                 description "SIP statistics";
                 container alg-sip {
                   description "SIP statistics";
                   container total-counters {
                     description "Total statistics";
                     leaf total-messages {
                       type uint32;
                       description "Total SIP messages";
                     }
                     leaf call-segments {
                       type uint32;
                       description "SIP call segments";
                     }
                   }
                   container parser-counters {
                     description "Parser statistics";
                     leaf syntax-errors {
                       type uint32;
                       description "SIP syntax errors";
                     }
                     leaf content-errors {
                       type uint32;
                       description "SIP message content errors";
                     }
                     leaf unknown-methods {
                       type uint32;
                       description "SIP unknown methods";
                     }
                   }
                   container message-counters {
                     description "SIP message counters";
                     leaf response-provisional {
                       type uint32;
                       description "Number of provisional responses";
                     }
                     leaf response-invite-ok {
                       type uint32;
                       description "Number of 'OK' responses to INVITE messages";
                     }
                     leaf response-non-invite-ok {
                       type uint32;
                       description "Number of 'OK' responses to messages other than INVITE";
                     }
                     leaf response-redir {
                       type uint32;
                       description "Number of redirection (3xx) responses";
                     }
                     leaf response-request-failure {
                       type uint32;
                       description "Number of request failure (4xx) responses";
                     }
                     leaf response-server-failure {
                       type uint32;
                       description "Number of server failure (5xx) responses";
                     }
                     leaf response-global-failure {
                       type uint32;
                       description "Number of global failure (6xx) responses";
                     }
                     leaf response-invalid {
                       type uint32;
                       description "Number of invalid responses";
                     }
                     leaf response-retransmits {
                       type uint32;
                       description "Number of response retransmissions";
                     }
                     leaf register-new {
                       type uint32;
                       description "Number of REGISTER messages";
                     }
                     leaf invite-new {
                       type uint32;
                       description "Number of new INVITE messages";
                     }
                     leaf invite-retransmits {
                       type uint32;
                       description "Number of INVITE message retransmissions";
                     }
                     leaf reinvites {
                       type uint32;
                       description "Number of ReINVITE messages";
                     }
                     leaf cancel-valid {
                       type uint32;
                       description "Number of valid CANCEL messages";
                     }
                     leaf cancel-invalid {
                       type uint32;
                       description "Number of invalid CANCEL messages";
                     }
                     leaf ack-valid {
                       type uint32;
                       description "Number of valid ACK messages";
                     }
                     leaf ack-invalid {
                       type uint32;
                       description "Number of invalid ACK messages";
                     }
                     leaf ack-retransmits {
                       type uint32;
                       description "Number of ACK message retransmissions";
                     }
                     leaf bye-valid {
                       type uint32;
                       description "Number of valid BYE messages";
                     }
                     leaf bye-invalid {
                       type uint32;
                       description "Number of invalid BYE messages";
                     }
                     leaf subscribe-valid {
                       type uint32;
                       description "Number of valid SUBSCRIBE messages";
                     }
                     leaf subscribe-invalid {
                       type uint32;
                       description "Number of invalid SUBSCRIBE messages";
                     }
                     leaf notify-valid {
                       type uint32;
                       description "Number of valid NOTIFY messages";
                     }
                     leaf notify-invalid {
                       type uint32;
                       description "Number of invalid NOTIFY messages";
                     }
                     leaf message-valid {
                       type uint32;
                       description "Number of valid MESSAGE messages";
                     }
                     leaf message-invalid {
                       type uint32;
                       description "Number of invalid MESSAGE messages";
                     }
                     leaf options-valid {
                       type uint32;
                       description "Number of valid OPTIONS messages";
                     }
                     leaf options-invalid {
                       type uint32;
                       description "Number of invalid OPTIONS messages";
                     }
                     leaf info-valid {
                       type uint32;
                       description "Number of valid INFO messages";
                     }
                     leaf info-invalid {
                       type uint32;
                       description "Number of invalid INFO messages";
                     }
                     leaf update-valid {
                       type uint32;
                       description "Number of valid UPDATE messages";
                     }
                     leaf update-invalid {
                       type uint32;
                       description "Number of invalid UPDATE messages";
                     }
                     leaf refer-valid {
                       type uint32;
                       description "Number of valid REFER messages";
                     }
                     leaf refer-invalid {
                       type uint32;
                       description "Number of invalid REFER messages";
                     }
                   }
                 }
               }
               container drop-flows {
                 description "Drop flow statistics";
                 leaf max-ingress-drop-flows {
                   type string;
                   description "Maximum ingress drop flows allowed";
                 }
                 leaf max-egress-drop-flows {
                   type string;
                   description "Maximum egress drop flows allowed";
                 }
                 container drop-flows-counters {
                   leaf current-ingress-drop-flows {
                     type int32;
                     description "Current ingress drop flows count";
                   }
                   leaf current-egress-drop-flows {
                     type int32;
                     description "Current egress drop flows count";
                   }
                   leaf ingress-drop-flowlimit-drops {
                     type uint32;
                     description "Drops because ingress drop flow limit is reached";
                   }
                   leaf egress-drop-flowlimit-drops {
                     type uint32;
                     description "Drops because egress drop flow limit is reached";
                   }
                 }
               }
             }
           }
         }
         container extensive {
           description "Stateful firewall statistics information";
           container service-sfw-statistics-entry {
             description "Stateful firewall statistics entry";
             leaf interface-name {
               type string;
               description "Name of the adaptive services interface";
             }
             container sfw-stats-service-set-entry {
               description "Stateful firewall service set statistics entry";
               container new-flow-counters {
                 description "New flow counters";
                 leaf new-flow-accepts {
                   type uint32;
                   description "Packets accepted by new flows";
                 }
                 leaf new-flow-discards {
                   type uint32;
                   description "Packets discarded by new flows";
                 }
                 leaf new-flow-rejects {
                   type uint32;
                   description "Packets rejected by new flows";
                 }
               }
               container existing-flow-counters {
                 description "Existing flow counters";
                 leaf existing-flow-accepts {
                   type uint32;
                   description "Packets accepted by existing accept flow";
                 }
                 leaf existing-flow-discards {
                   type uint32;
                   description "Packets discarded by existing drop flow";
                 }
                 leaf existing-flow-rejects {
                   type uint32;
                   description "Packets rejected by existing reject flow";
                 }
               }
               container hairpinning-counters {
                 description "Hairpinned packets count";
                 leaf slow-path-hairpinned-packets {
                   type uint32;
                   description "Initiator packets for Hairpinning";
                 }
                 leaf fast-path-hairpinned-packets {
                   type uint32;
                   description "Packets recieved on existing Hairpinned flows";
                 }
               }
               container drop_counters {
                 description "Drop counters (rules or resource exhaustion)";
                 leaf ip-option {
                   type uint32;
                   description "IP option drops";
                 }
                 leaf syn-defense {
                   type uint32;
                   description "Incomplete TCP handshakes";
                 }
                 leaf nat-ports-exhausted {
                   type uint32;
                   description "NAT ports exhausted";
                 }
                 leaf subs-flow-limit-exceeded {
                   type uint32;
                   description "Subscriber flow limit exceeded";
                 }
               }
               container error-counters {
                 description "Summarized protocol processing errors";
                 leaf ip-errors {
                   type uint32;
                   description "IP processing errors";
                 }
                 leaf tcp-errors {
                   type uint32;
                   description "TCP processing errors";
                 }
                 leaf udp-errors {
                   type uint32;
                   description "UDP processing errors";
                 }
                 leaf icmp-errors {
                   type uint32;
                   description "ICMP processing errors";
                 }
                 leaf non-ip-packets {
                   type uint32;
                   description "Non-IP packets";
                 }
                 leaf alg-errors {
                   type uint32;
                   description "ALG processing errors";
                 }
               }
               container ip-error-counters {
                 description "Extensive output of IP processing errors";
                 leaf ip-length-error {
                   type uint32;
                   description "IP packet length inconsistencies";
                 }
                 leaf ip-header-length-error {
                   type uint32;
                   description "Minimum IP header length check failures";
                 }
                 leaf long-packet {
                   type uint32;
                   description "Reassembled packet exceeds maximum IP length (65,535 bytes)";
                 }
                 leaf illegal-destination-address {
                   type uint32;
                   description "Illegal destination address";
                 }
                 leaf illegal-source-address {
                   type uint32;
                   description "Illegal source address";
                 }
                 leaf ttl-zero {
                   type uint32;
                   description "IP packets received with a TTL value of 0";
                 }
                 leaf illegal-ip-protocol {
                   type uint32;
                   description "Illegal IP protocol number ";
                 }
                 leaf non-ipv6 {
                   type uint32;
                   description "Non-IPv6 packets";
                 }
                 leaf land-attack {
                   type uint32;
                   description "IP source address same as destination address";
                 }
                 leaf not-ip-packet {
                   type uint32;
                   description "Not IP Packet";
                 }
                 leaf non-ipv4 {
                   type uint32;
                   description "Non-IPv4 packets";
                 }
                 leaf bad-checksum {
                   type uint32;
                   description "Bad checksum";
                 }
                 leaf illegal-fragment-length {
                   type uint32;
                   description "Illegal IP fragment length";
                 }
                 leaf fragment-overlap {
                   type uint32;
                   description "IP fragment overlap";
                 }
                 leaf fragment-reassembly-timeout {
                   type uint32;
                   description "IP fragment reassembly timeout";
                 }
                 leaf fragment-limit-exceeded {
                   type uint32;
                   description "IP fragment limit exceeded";
                 }
                 leaf unknown {
                   type uint32;
                   description "Unknown errors";
                 }
               }
               container tcp-error-counters {
                 description "Extensive output of TCP processing errors";
                 leaf tcp-header-length-error {
                   type uint32;
                   description "TCP header length inconsistencies";
                 }
                 leaf tcp-zero-port {
                   type uint32;
                   description "Source or destination port number is zero";
                 }
                 leaf illegal-sequence-number-flags {
                   type uint32;
                   description "Illegal sequence number and flags combinations";
                 }
                 leaf syn-attack {
                   type uint32;
                   description "SYN attack";
                 }
                 leaf non-syn-first-packet {
                   type uint32;
                   description "First packet not a SYN message";
                 }
                 leaf tcp-port-scan {
                   type uint32;
                   description "TCP port scan";
                 }
                 leaf bad-syn-cookie-response {
                   type uint32;
                   description "Bad SYN cookie response";
                 }
                 leaf tcp-recon-sequence-number-error {
                   type uint32;
                   description "TCP reconstructor sequence number error";
                 }
                 leaf tcp-recon-retransmits {
                   type uint32;
                   description "TCP reconstructor retransmissions";
                 }
                 leaf tcp-partially-opened-connection-timeout-syn-rcvd {
                   type uint32;
                   description "TCP partially opened connection timeout";
                 }
                 leaf tcp-partially-opened-connection-timeout-syn-ack-rcvd {
                   type uint32;
                   description "TCP partially opened connection timeout";
                 }
                 leaf tcp-partially-closed-connection-reuse {
                   type uint32;
                   description "TCP partially closed connection reuse";
                 }
                 leaf tcp-3way-error-client-sent-syn-ack {
                   type uint32;
                   description "TCP 3-way error - client sent SYN+ACK";
                 }
                 leaf tcp-3way-error-server-sent-ack {
                   type uint32;
                   description "TCP 3-way error - server sent ACK";
                 }
                 leaf tcp-3way-error-syn-seq-num-retrans-mismatch {
                   type uint32;
                   description "TCP 3-way error - SYN seq number retransmission mismatch";
                 }
                 leaf tcp-3way-error-rst-seq-num-mismatch {
                   type uint32;
                   description "TCP 3-way error - RST seq number mismatch";
                 }
                 leaf tcp-3way-error-fin-received {
                   type uint32;
                   description "TCP 3-way error - FIN received";
                 }
                 leaf tcp-3way-error-invalid-flags {
                   type uint32;
                   description "TCP 3-way error - invalid TCP flag combination";
                 }
                 leaf tcp-3way-error-syn-no-flow-initiator {
                   type uint32;
                   description "TCP 3-way error - SYN recvd but no client flows";
                 }
                 leaf tcp-3way-error-first-packet-syn-ack {
                   type uint32;
                   description "TCP 3-way error - first packet SYN+ACK";
                 }
                 leaf tcp-3way-error-first-packet-fin-ack {
                   type uint32;
                   description "TCP 3-way error - first packet FIN+ACK";
                 }
                 leaf tcp-3way-error-first-packet-fin {
                   type uint32;
                   description "TCP 3-way error - first packet FIN";
                 }
                 leaf tcp-3way-error-first-packet-rst {
                   type uint32;
                   description "TCP 3-way error - first packet RST";
                 }
                 leaf tcp-3way-error-first-packet-ack {
                   type uint32;
                   description "TCP 3-way error - first packet ack";
                 }
                 leaf tcp-3way-error-first-packet-invalid-flags {
                   type uint32;
                   description "TCP 3-way error - first packet ack";
                 }
                 leaf tcp-close-error-no-final-ack {
                   type uint32;
                   description "TCP close error - no final ack";
                 }
                 leaf tcp-resumed-flow {
                   type uint32;
                   description "TCP Resumed Flow";
                 }
               }
               container udp-error-counters {
                 description "Extensive output of UDP processing errors";
                 leaf udp-header-length-error {
                   type uint32;
                   description "IP data length is less than minimum UDP header length (8 bytes)";
                 }
                 leaf udp-zero-port {
                   type uint32;
                   description "Source or destination port number is zero";
                 }
                 leaf udp-port-scan {
                   type uint32;
                   description "UDP port scan (ICMP error seen for UDP flow)";
                 }
               }
               container icmp-error-counters {
                 description "Extensive output of ICMP processing errors";
                 leaf icmp-length-error {
                   type uint32;
                   description "IP data length less than minimum ICMP header length (8 bytes)";
                 }
                 leaf icmp-error-length-error {
                   type uint32;
                   description "ICMP error length inconsistencies";
                 }
                 leaf ping-duplicate-sequence-number {
                   type uint32;
                   description "Duplicate ping sequence number";
                 }
                 leaf ping-mismatched-sequence-number {
                   type uint32;
                   description "Mismatched ping sequence number";
                 }
                 leaf icmp-error-no-matching-flow {
                   type uint32;
                   description "No matching flow for ICMP error packet";
                 }
               }
               container alg-error-counters {
                 description "Extensive output of ALG processing errors";
                 leaf alg-bootp-errors {
                   type uint32;
                   description "ALG BOOTP errors";
                 }
                 leaf alg-dce-rpc-errors {
                   type uint32;
                   description "ALG DCE-RPC errors";
                 }
                 leaf alg-dce-rpc-portmap-errors {
                   type uint32;
                   description "ALG DCE-RPC portmap errors";
                 }
                 leaf alg-dns-errors {
                   type uint32;
                   description "ALG DNS errors";
                 }
                 leaf alg-exec-errors {
                   type uint32;
                   description "ALG exec errors";
                 }
                 leaf alg-ftp-errors {
                   type uint32;
                   description "ALG FTP errors";
                 }
                 leaf alg-h323-errors {
                   type uint32;
                   description "ALG H323 errors";
                 }
                 leaf alg-icmp-errors {
                   type uint32;
                   description "ALG ICMP errors";
                 }
                 leaf alg-iiop-errors {
                   type uint32;
                   description "ALG IIOP errors";
                 }
                 leaf alg-login-errors {
                   type uint32;
                   description "ALG login errors";
                 }
                 leaf alg-netbios-errors {
                   type uint32;
                   description "ALG NetBIOS errors";
                 }
                 leaf alg-netshow-errors {
                   type uint32;
                   description "ALG NetShow errors";
                 }
                 leaf alg-realaudio-errors {
                   type uint32;
                   description "ALG Real Audio errors";
                 }
                 leaf alg-rpc-errors {
                   type uint32;
                   description "ALG RPC errors";
                 }
                 leaf alg-rpc-portmap-errors {
                   type uint32;
                   description "ALG RPC portmap errors";
                 }
                 leaf alg-rtsp-errors {
                   type uint32;
                   description "ALG Real-Time Streaming Protocol errors";
                 }
                 leaf alg-shell-errors {
                   type uint32;
                   description "ALG shell errors";
                 }
                 leaf alg-sip-errors {
                   type uint32;
                   description "ALG Session Initiation Protocol errors";
                 }
                 leaf alg-snmp-errors {
                   type uint32;
                   description "ALG SNMP errors";
                 }
                 leaf alg-sqlnet-errors {
                   type uint32;
                   description "ALG SQLNet errors";
                 }
                 leaf alg-tftp-errors {
                   type uint32;
                   description "ALG TFTP errors";
                 }
                 leaf alg-traceroute-errors {
                   type uint32;
                   description "ALG traceroute errors";
                 }
               }
               container sip-alg-counters {
                 description "SIP statistics";
                 container alg-sip {
                   description "SIP statistics";
                   container total-counters {
                     description "Total statistics";
                     leaf total-messages {
                       type uint32;
                       description "Total SIP messages";
                     }
                     leaf call-segments {
                       type uint32;
                       description "SIP call segments";
                     }
                   }
                   container parser-counters {
                     description "Parser statistics";
                     leaf syntax-errors {
                       type uint32;
                       description "SIP syntax errors";
                     }
                     leaf content-errors {
                       type uint32;
                       description "SIP message content errors";
                     }
                     leaf unknown-methods {
                       type uint32;
                       description "SIP unknown methods";
                     }
                   }
                   container message-counters {
                     description "SIP message counters";
                     leaf response-provisional {
                       type uint32;
                       description "Number of provisional responses";
                     }
                     leaf response-invite-ok {
                       type uint32;
                       description "Number of 'OK' responses to INVITE messages";
                     }
                     leaf response-non-invite-ok {
                       type uint32;
                       description "Number of 'OK' responses to messages other than INVITE";
                     }
                     leaf response-redir {
                       type uint32;
                       description "Number of redirection (3xx) responses";
                     }
                     leaf response-request-failure {
                       type uint32;
                       description "Number of request failure (4xx) responses";
                     }
                     leaf response-server-failure {
                       type uint32;
                       description "Number of server failure (5xx) responses";
                     }
                     leaf response-global-failure {
                       type uint32;
                       description "Number of global failure (6xx) responses";
                     }
                     leaf response-invalid {
                       type uint32;
                       description "Number of invalid responses";
                     }
                     leaf response-retransmits {
                       type uint32;
                       description "Number of response retransmissions";
                     }
                     leaf register-new {
                       type uint32;
                       description "Number of REGISTER messages";
                     }
                     leaf invite-new {
                       type uint32;
                       description "Number of new INVITE messages";
                     }
                     leaf invite-retransmits {
                       type uint32;
                       description "Number of INVITE message retransmissions";
                     }
                     leaf reinvites {
                       type uint32;
                       description "Number of ReINVITE messages";
                     }
                     leaf cancel-valid {
                       type uint32;
                       description "Number of valid CANCEL messages";
                     }
                     leaf cancel-invalid {
                       type uint32;
                       description "Number of invalid CANCEL messages";
                     }
                     leaf ack-valid {
                       type uint32;
                       description "Number of valid ACK messages";
                     }
                     leaf ack-invalid {
                       type uint32;
                       description "Number of invalid ACK messages";
                     }
                     leaf ack-retransmits {
                       type uint32;
                       description "Number of ACK message retransmissions";
                     }
                     leaf bye-valid {
                       type uint32;
                       description "Number of valid BYE messages";
                     }
                     leaf bye-invalid {
                       type uint32;
                       description "Number of invalid BYE messages";
                     }
                     leaf subscribe-valid {
                       type uint32;
                       description "Number of valid SUBSCRIBE messages";
                     }
                     leaf subscribe-invalid {
                       type uint32;
                       description "Number of invalid SUBSCRIBE messages";
                     }
                     leaf notify-valid {
                       type uint32;
                       description "Number of valid NOTIFY messages";
                     }
                     leaf notify-invalid {
                       type uint32;
                       description "Number of invalid NOTIFY messages";
                     }
                     leaf message-valid {
                       type uint32;
                       description "Number of valid MESSAGE messages";
                     }
                     leaf message-invalid {
                       type uint32;
                       description "Number of invalid MESSAGE messages";
                     }
                     leaf options-valid {
                       type uint32;
                       description "Number of valid OPTIONS messages";
                     }
                     leaf options-invalid {
                       type uint32;
                       description "Number of invalid OPTIONS messages";
                     }
                     leaf info-valid {
                       type uint32;
                       description "Number of valid INFO messages";
                     }
                     leaf info-invalid {
                       type uint32;
                       description "Number of invalid INFO messages";
                     }
                     leaf update-valid {
                       type uint32;
                       description "Number of valid UPDATE messages";
                     }
                     leaf update-invalid {
                       type uint32;
                       description "Number of invalid UPDATE messages";
                     }
                     leaf refer-valid {
                       type uint32;
                       description "Number of valid REFER messages";
                     }
                     leaf refer-invalid {
                       type uint32;
                       description "Number of invalid REFER messages";
                     }
                   }
                 }
               }
               container drop-flows {
                 description "Drop flow statistics";
                 leaf max-ingress-drop-flows {
                   type string;
                   description "Maximum ingress drop flows allowed";
                 }
                 leaf max-egress-drop-flows {
                   type string;
                   description "Maximum egress drop flows allowed";
                 }
                 container drop-flows-counters {
                   leaf current-ingress-drop-flows {
                     type int32;
                     description "Current ingress drop flows count";
                   }
                   leaf current-egress-drop-flows {
                     type int32;
                     description "Current egress drop flows count";
                   }
                   leaf ingress-drop-flowlimit-drops {
                     type uint32;
                     description "Drops because ingress drop flow limit is reached";
                   }
                   leaf egress-drop-flowlimit-drops {
                     type uint32;
                     description "Drops because egress drop flow limit is reached";
                   }
                 }
               }
             }
           }
         }
         container alg {
           description "Stateful firewall statistics information";
           container service-sfw-statistics-entry {
             description "Stateful firewall statistics entry";
             leaf interface-name {
               type string;
               description "Name of the adaptive services interface";
             }
             container sfw-stats-service-set-entry {
               description "Stateful firewall service set statistics entry";
               container new-flow-counters {
                 description "New flow counters";
                 leaf new-flow-accepts {
                   type uint32;
                   description "Packets accepted by new flows";
                 }
                 leaf new-flow-discards {
                   type uint32;
                   description "Packets discarded by new flows";
                 }
                 leaf new-flow-rejects {
                   type uint32;
                   description "Packets rejected by new flows";
                 }
               }
               container existing-flow-counters {
                 description "Existing flow counters";
                 leaf existing-flow-accepts {
                   type uint32;
                   description "Packets accepted by existing accept flow";
                 }
                 leaf existing-flow-discards {
                   type uint32;
                   description "Packets discarded by existing drop flow";
                 }
                 leaf existing-flow-rejects {
                   type uint32;
                   description "Packets rejected by existing reject flow";
                 }
               }
               container hairpinning-counters {
                 description "Hairpinned packets count";
                 leaf slow-path-hairpinned-packets {
                   type uint32;
                   description "Initiator packets for Hairpinning";
                 }
                 leaf fast-path-hairpinned-packets {
                   type uint32;
                   description "Packets recieved on existing Hairpinned flows";
                 }
               }
               container drop_counters {
                 description "Drop counters (rules or resource exhaustion)";
                 leaf ip-option {
                   type uint32;
                   description "IP option drops";
                 }
                 leaf syn-defense {
                   type uint32;
                   description "Incomplete TCP handshakes";
                 }
                 leaf nat-ports-exhausted {
                   type uint32;
                   description "NAT ports exhausted";
                 }
                 leaf subs-flow-limit-exceeded {
                   type uint32;
                   description "Subscriber flow limit exceeded";
                 }
               }
               container error-counters {
                 description "Summarized protocol processing errors";
                 leaf ip-errors {
                   type uint32;
                   description "IP processing errors";
                 }
                 leaf tcp-errors {
                   type uint32;
                   description "TCP processing errors";
                 }
                 leaf udp-errors {
                   type uint32;
                   description "UDP processing errors";
                 }
                 leaf icmp-errors {
                   type uint32;
                   description "ICMP processing errors";
                 }
                 leaf non-ip-packets {
                   type uint32;
                   description "Non-IP packets";
                 }
                 leaf alg-errors {
                   type uint32;
                   description "ALG processing errors";
                 }
               }
               container ip-error-counters {
                 description "Extensive output of IP processing errors";
                 leaf ip-length-error {
                   type uint32;
                   description "IP packet length inconsistencies";
                 }
                 leaf ip-header-length-error {
                   type uint32;
                   description "Minimum IP header length check failures";
                 }
                 leaf long-packet {
                   type uint32;
                   description "Reassembled packet exceeds maximum IP length (65,535 bytes)";
                 }
                 leaf illegal-destination-address {
                   type uint32;
                   description "Illegal destination address";
                 }
                 leaf illegal-source-address {
                   type uint32;
                   description "Illegal source address";
                 }
                 leaf ttl-zero {
                   type uint32;
                   description "IP packets received with a TTL value of 0";
                 }
                 leaf illegal-ip-protocol {
                   type uint32;
                   description "Illegal IP protocol number ";
                 }
                 leaf non-ipv6 {
                   type uint32;
                   description "Non-IPv6 packets";
                 }
                 leaf land-attack {
                   type uint32;
                   description "IP source address same as destination address";
                 }
                 leaf not-ip-packet {
                   type uint32;
                   description "Not IP Packet";
                 }
                 leaf non-ipv4 {
                   type uint32;
                   description "Non-IPv4 packets";
                 }
                 leaf bad-checksum {
                   type uint32;
                   description "Bad checksum";
                 }
                 leaf illegal-fragment-length {
                   type uint32;
                   description "Illegal IP fragment length";
                 }
                 leaf fragment-overlap {
                   type uint32;
                   description "IP fragment overlap";
                 }
                 leaf fragment-reassembly-timeout {
                   type uint32;
                   description "IP fragment reassembly timeout";
                 }
                 leaf fragment-limit-exceeded {
                   type uint32;
                   description "IP fragment limit exceeded";
                 }
                 leaf unknown {
                   type uint32;
                   description "Unknown errors";
                 }
               }
               container tcp-error-counters {
                 description "Extensive output of TCP processing errors";
                 leaf tcp-header-length-error {
                   type uint32;
                   description "TCP header length inconsistencies";
                 }
                 leaf tcp-zero-port {
                   type uint32;
                   description "Source or destination port number is zero";
                 }
                 leaf illegal-sequence-number-flags {
                   type uint32;
                   description "Illegal sequence number and flags combinations";
                 }
                 leaf syn-attack {
                   type uint32;
                   description "SYN attack";
                 }
                 leaf non-syn-first-packet {
                   type uint32;
                   description "First packet not a SYN message";
                 }
                 leaf tcp-port-scan {
                   type uint32;
                   description "TCP port scan";
                 }
                 leaf bad-syn-cookie-response {
                   type uint32;
                   description "Bad SYN cookie response";
                 }
                 leaf tcp-recon-sequence-number-error {
                   type uint32;
                   description "TCP reconstructor sequence number error";
                 }
                 leaf tcp-recon-retransmits {
                   type uint32;
                   description "TCP reconstructor retransmissions";
                 }
                 leaf tcp-partially-opened-connection-timeout-syn-rcvd {
                   type uint32;
                   description "TCP partially opened connection timeout";
                 }
                 leaf tcp-partially-opened-connection-timeout-syn-ack-rcvd {
                   type uint32;
                   description "TCP partially opened connection timeout";
                 }
                 leaf tcp-partially-closed-connection-reuse {
                   type uint32;
                   description "TCP partially closed connection reuse";
                 }
                 leaf tcp-3way-error-client-sent-syn-ack {
                   type uint32;
                   description "TCP 3-way error - client sent SYN+ACK";
                 }
                 leaf tcp-3way-error-server-sent-ack {
                   type uint32;
                   description "TCP 3-way error - server sent ACK";
                 }
                 leaf tcp-3way-error-syn-seq-num-retrans-mismatch {
                   type uint32;
                   description "TCP 3-way error - SYN seq number retransmission mismatch";
                 }
                 leaf tcp-3way-error-rst-seq-num-mismatch {
                   type uint32;
                   description "TCP 3-way error - RST seq number mismatch";
                 }
                 leaf tcp-3way-error-fin-received {
                   type uint32;
                   description "TCP 3-way error - FIN received";
                 }
                 leaf tcp-3way-error-invalid-flags {
                   type uint32;
                   description "TCP 3-way error - invalid TCP flag combination";
                 }
                 leaf tcp-3way-error-syn-no-flow-initiator {
                   type uint32;
                   description "TCP 3-way error - SYN recvd but no client flows";
                 }
                 leaf tcp-3way-error-first-packet-syn-ack {
                   type uint32;
                   description "TCP 3-way error - first packet SYN+ACK";
                 }
                 leaf tcp-3way-error-first-packet-fin-ack {
                   type uint32;
                   description "TCP 3-way error - first packet FIN+ACK";
                 }
                 leaf tcp-3way-error-first-packet-fin {
                   type uint32;
                   description "TCP 3-way error - first packet FIN";
                 }
                 leaf tcp-3way-error-first-packet-rst {
                   type uint32;
                   description "TCP 3-way error - first packet RST";
                 }
                 leaf tcp-3way-error-first-packet-ack {
                   type uint32;
                   description "TCP 3-way error - first packet ack";
                 }
                 leaf tcp-3way-error-first-packet-invalid-flags {
                   type uint32;
                   description "TCP 3-way error - first packet ack";
                 }
                 leaf tcp-close-error-no-final-ack {
                   type uint32;
                   description "TCP close error - no final ack";
                 }
                 leaf tcp-resumed-flow {
                   type uint32;
                   description "TCP Resumed Flow";
                 }
               }
               container udp-error-counters {
                 description "Extensive output of UDP processing errors";
                 leaf udp-header-length-error {
                   type uint32;
                   description "IP data length is less than minimum UDP header length (8 bytes)";
                 }
                 leaf udp-zero-port {
                   type uint32;
                   description "Source or destination port number is zero";
                 }
                 leaf udp-port-scan {
                   type uint32;
                   description "UDP port scan (ICMP error seen for UDP flow)";
                 }
               }
               container icmp-error-counters {
                 description "Extensive output of ICMP processing errors";
                 leaf icmp-length-error {
                   type uint32;
                   description "IP data length less than minimum ICMP header length (8 bytes)";
                 }
                 leaf icmp-error-length-error {
                   type uint32;
                   description "ICMP error length inconsistencies";
                 }
                 leaf ping-duplicate-sequence-number {
                   type uint32;
                   description "Duplicate ping sequence number";
                 }
                 leaf ping-mismatched-sequence-number {
                   type uint32;
                   description "Mismatched ping sequence number";
                 }
                 leaf icmp-error-no-matching-flow {
                   type uint32;
                   description "No matching flow for ICMP error packet";
                 }
               }
               container alg-error-counters {
                 description "Extensive output of ALG processing errors";
                 leaf alg-bootp-errors {
                   type uint32;
                   description "ALG BOOTP errors";
                 }
                 leaf alg-dce-rpc-errors {
                   type uint32;
                   description "ALG DCE-RPC errors";
                 }
                 leaf alg-dce-rpc-portmap-errors {
                   type uint32;
                   description "ALG DCE-RPC portmap errors";
                 }
                 leaf alg-dns-errors {
                   type uint32;
                   description "ALG DNS errors";
                 }
                 leaf alg-exec-errors {
                   type uint32;
                   description "ALG exec errors";
                 }
                 leaf alg-ftp-errors {
                   type uint32;
                   description "ALG FTP errors";
                 }
                 leaf alg-h323-errors {
                   type uint32;
                   description "ALG H323 errors";
                 }
                 leaf alg-icmp-errors {
                   type uint32;
                   description "ALG ICMP errors";
                 }
                 leaf alg-iiop-errors {
                   type uint32;
                   description "ALG IIOP errors";
                 }
                 leaf alg-login-errors {
                   type uint32;
                   description "ALG login errors";
                 }
                 leaf alg-netbios-errors {
                   type uint32;
                   description "ALG NetBIOS errors";
                 }
                 leaf alg-netshow-errors {
                   type uint32;
                   description "ALG NetShow errors";
                 }
                 leaf alg-realaudio-errors {
                   type uint32;
                   description "ALG Real Audio errors";
                 }
                 leaf alg-rpc-errors {
                   type uint32;
                   description "ALG RPC errors";
                 }
                 leaf alg-rpc-portmap-errors {
                   type uint32;
                   description "ALG RPC portmap errors";
                 }
                 leaf alg-rtsp-errors {
                   type uint32;
                   description "ALG Real-Time Streaming Protocol errors";
                 }
                 leaf alg-shell-errors {
                   type uint32;
                   description "ALG shell errors";
                 }
                 leaf alg-sip-errors {
                   type uint32;
                   description "ALG Session Initiation Protocol errors";
                 }
                 leaf alg-snmp-errors {
                   type uint32;
                   description "ALG SNMP errors";
                 }
                 leaf alg-sqlnet-errors {
                   type uint32;
                   description "ALG SQLNet errors";
                 }
                 leaf alg-tftp-errors {
                   type uint32;
                   description "ALG TFTP errors";
                 }
                 leaf alg-traceroute-errors {
                   type uint32;
                   description "ALG traceroute errors";
                 }
               }
               container sip-alg-counters {
                 description "SIP statistics";
                 container alg-sip {
                   description "SIP statistics";
                   container total-counters {
                     description "Total statistics";
                     leaf total-messages {
                       type uint32;
                       description "Total SIP messages";
                     }
                     leaf call-segments {
                       type uint32;
                       description "SIP call segments";
                     }
                   }
                   container parser-counters {
                     description "Parser statistics";
                     leaf syntax-errors {
                       type uint32;
                       description "SIP syntax errors";
                     }
                     leaf content-errors {
                       type uint32;
                       description "SIP message content errors";
                     }
                     leaf unknown-methods {
                       type uint32;
                       description "SIP unknown methods";
                     }
                   }
                   container message-counters {
                     description "SIP message counters";
                     leaf response-provisional {
                       type uint32;
                       description "Number of provisional responses";
                     }
                     leaf response-invite-ok {
                       type uint32;
                       description "Number of 'OK' responses to INVITE messages";
                     }
                     leaf response-non-invite-ok {
                       type uint32;
                       description "Number of 'OK' responses to messages other than INVITE";
                     }
                     leaf response-redir {
                       type uint32;
                       description "Number of redirection (3xx) responses";
                     }
                     leaf response-request-failure {
                       type uint32;
                       description "Number of request failure (4xx) responses";
                     }
                     leaf response-server-failure {
                       type uint32;
                       description "Number of server failure (5xx) responses";
                     }
                     leaf response-global-failure {
                       type uint32;
                       description "Number of global failure (6xx) responses";
                     }
                     leaf response-invalid {
                       type uint32;
                       description "Number of invalid responses";
                     }
                     leaf response-retransmits {
                       type uint32;
                       description "Number of response retransmissions";
                     }
                     leaf register-new {
                       type uint32;
                       description "Number of REGISTER messages";
                     }
                     leaf invite-new {
                       type uint32;
                       description "Number of new INVITE messages";
                     }
                     leaf invite-retransmits {
                       type uint32;
                       description "Number of INVITE message retransmissions";
                     }
                     leaf reinvites {
                       type uint32;
                       description "Number of ReINVITE messages";
                     }
                     leaf cancel-valid {
                       type uint32;
                       description "Number of valid CANCEL messages";
                     }
                     leaf cancel-invalid {
                       type uint32;
                       description "Number of invalid CANCEL messages";
                     }
                     leaf ack-valid {
                       type uint32;
                       description "Number of valid ACK messages";
                     }
                     leaf ack-invalid {
                       type uint32;
                       description "Number of invalid ACK messages";
                     }
                     leaf ack-retransmits {
                       type uint32;
                       description "Number of ACK message retransmissions";
                     }
                     leaf bye-valid {
                       type uint32;
                       description "Number of valid BYE messages";
                     }
                     leaf bye-invalid {
                       type uint32;
                       description "Number of invalid BYE messages";
                     }
                     leaf subscribe-valid {
                       type uint32;
                       description "Number of valid SUBSCRIBE messages";
                     }
                     leaf subscribe-invalid {
                       type uint32;
                       description "Number of invalid SUBSCRIBE messages";
                     }
                     leaf notify-valid {
                       type uint32;
                       description "Number of valid NOTIFY messages";
                     }
                     leaf notify-invalid {
                       type uint32;
                       description "Number of invalid NOTIFY messages";
                     }
                     leaf message-valid {
                       type uint32;
                       description "Number of valid MESSAGE messages";
                     }
                     leaf message-invalid {
                       type uint32;
                       description "Number of invalid MESSAGE messages";
                     }
                     leaf options-valid {
                       type uint32;
                       description "Number of valid OPTIONS messages";
                     }
                     leaf options-invalid {
                       type uint32;
                       description "Number of invalid OPTIONS messages";
                     }
                     leaf info-valid {
                       type uint32;
                       description "Number of valid INFO messages";
                     }
                     leaf info-invalid {
                       type uint32;
                       description "Number of invalid INFO messages";
                     }
                     leaf update-valid {
                       type uint32;
                       description "Number of valid UPDATE messages";
                     }
                     leaf update-invalid {
                       type uint32;
                       description "Number of invalid UPDATE messages";
                     }
                     leaf refer-valid {
                       type uint32;
                       description "Number of valid REFER messages";
                     }
                     leaf refer-invalid {
                       type uint32;
                       description "Number of invalid REFER messages";
                     }
                   }
                 }
               }
               container drop-flows {
                 description "Drop flow statistics";
                 leaf max-ingress-drop-flows {
                   type string;
                   description "Maximum ingress drop flows allowed";
                 }
                 leaf max-egress-drop-flows {
                   type string;
                   description "Maximum egress drop flows allowed";
                 }
                 container drop-flows-counters {
                   leaf current-ingress-drop-flows {
                     type int32;
                     description "Current ingress drop flows count";
                   }
                   leaf current-egress-drop-flows {
                     type int32;
                     description "Current egress drop flows count";
                   }
                   leaf ingress-drop-flowlimit-drops {
                     type uint32;
                     description "Drops because ingress drop flow limit is reached";
                   }
                   leaf egress-drop-flowlimit-drops {
                     type uint32;
                     description "Drops because egress drop flow limit is reached";
                   }
                 }
               }
             }
           }
         }
       }
     }
   }
   rpc get-service-sfw-redundancy-statistics {
     description "Show redundancy statistics";
     input {
       leaf backup-data-pic {
         description "Query the backup data PIC";
         type empty;
       }
       leaf display {
         default "brief";
         type enumeration {
           enum "extensive" {
             description "Display extensive output";
           }
           enum "brief" {
             description "Display brief output (default)";
           }
         }
       }
     }
   }
   rpc get-service-capture {
     description "Show Services PIC packet capture";
     input {
       leaf file {
         type string;
         mandatory true;
       }
       leaf level {
         default "brief";
         type enumeration {
           enum "brief" {
             description "Display brief output";
           }
           enum "detail" {
             description "Display detailed output";
           }
           enum "extensive" {
             description "Display extensive output";
           }
         }
       }
       leaf packet-id {
         description "Packet-id to be used as filter";
         type string;
       }
     }
   }
   rpc get-service-softwire-table-information {
     description "Show softwire information";
     input {
       leaf get-service-current-softwire-count-information {
         description "Show count of softwires created";
         type empty;
       }
     }
     output {
       container service-softwire-table-information {
         container softwire-per-service-set-flow-table {
           description "Flows sorted by service set";
           leaf interface-name {
             type string;
             description "Name of the adaptive services interface";
           }
           leaf service-set-name {
             type string;
             description "Name of the service set";
           }
           container service-softwire-table {
             description "Softwire flows";
             leaf service-softwire-table.heading {
               type string;
               description "Softwire flows";
             }
             container softwire-entry {
               description "Flow brief information";
               leaf softwire-source-ip {
                 type string;
                 description "Softwire source IP address";
               }
               leaf softwire-destination-ip {
                 type string;
                 description "Softwire destination IP address";
               }
               leaf softwire-direction {
                 type string;
                 description "Softwire direction";
               }
               leaf softwire-flow-count {
                 type string;
                 description "Number of flows in softwire";
               }
               leaf softwire-table-timeout {
                 type uint64;
                 description "Timeout value of flow (seconds)";
               }
             }
             container sfw-flow-entry {
               description "Flow brief information";
               container sfw-flow-nat {
                 description "NAT translation";
                 leaf sfw-flow-nat-type {
                   type string;
                   description "Type of NAT translation";
                 }
                 leaf sfw-flow-nat-ip {
                   type string;
                   description "Original IP address";
                 }
                 leaf sfw-flow-nat-port {
                   type string;
                   description "Original port";
                 }
                 leaf sfw-flow-translated-ip {
                   type string;
                   description "Translated IP address";
                 }
                 leaf sfw-flow-translated-port {
                   type string;
                   description "Translated port";
                 }
               }
             }
           }
         }
       }
     }
   }
   rpc get-service-softwire-flow-table-information {
     description "Show flow table entries";
     input {
       leaf service-set {
         description "Name of service set";
         type string;
       }
       leaf interface {
         description "Name of adaptive services interface";
         type string;
       }
       leaf get-service-softwire-count-information {
         description "Show count of matching entries";
         type empty;
       }
     }
     output {
       container service-softwire-flow-table-information {
         container softwire-per-service-set-flow-table {
           description "Flows sorted by service set";
           leaf interface-name {
             type string;
             description "Name of the adaptive services interface";
           }
           leaf service-set-name {
             type string;
             description "Name of the service set";
           }
           container service-softwire-table {
             description "Softwire flows";
             leaf service-softwire-table.heading {
               type string;
               description "Softwire flows";
             }
             container softwire-entry {
               description "Flow brief information";
               leaf softwire-source-ip {
                 type string;
                 description "Softwire source IP address";
               }
               leaf softwire-destination-ip {
                 type string;
                 description "Softwire destination IP address";
               }
               leaf softwire-direction {
                 type string;
                 description "Softwire direction";
               }
               leaf softwire-flow-count {
                 type string;
                 description "Number of flows in softwire";
               }
               leaf softwire-table-timeout {
                 type uint64;
                 description "Timeout value of flow (seconds)";
               }
             }
             container sfw-flow-entry {
               description "Flow brief information";
               container sfw-flow-nat {
                 description "NAT translation";
                 leaf sfw-flow-nat-type {
                   type string;
                   description "Type of NAT translation";
                 }
                 leaf sfw-flow-nat-ip {
                   type string;
                   description "Original IP address";
                 }
                 leaf sfw-flow-nat-port {
                   type string;
                   description "Original port";
                 }
                 leaf sfw-flow-translated-ip {
                   type string;
                   description "Translated IP address";
                 }
                 leaf sfw-flow-translated-port {
                   type string;
                   description "Translated port";
                 }
               }
               container sw-flow-nat-entry {
                 description "NAT translation";
               }
             }
           }
         }
       }
     }
   }
   rpc get-service-softwire-ds-lite-flow-table-information {
     description "Show ds-lite related softwire flows";
     input {
       leaf AFTR {
         description "AFTR IPV6 Address";
         type ipv6addr;
       }
       leaf B4 {
         description "B4 IPV6 Address";
         type ipv6addr;
       }
     }
     output {
       container service-softwire-flow-table-information {
         container softwire-per-service-set-flow-table {
           description "Flows sorted by service set";
           leaf interface-name {
             type string;
             description "Name of the adaptive services interface";
           }
           leaf service-set-name {
             type string;
             description "Name of the service set";
           }
           container service-softwire-table {
             description "Softwire flows";
             leaf service-softwire-table.heading {
               type string;
               description "Softwire flows";
             }
             container softwire-entry {
               description "Flow brief information";
               leaf softwire-source-ip {
                 type string;
                 description "Softwire source IP address";
               }
               leaf softwire-destination-ip {
                 type string;
                 description "Softwire destination IP address";
               }
               leaf softwire-direction {
                 type string;
                 description "Softwire direction";
               }
               leaf softwire-flow-count {
                 type string;
                 description "Number of flows in softwire";
               }
               leaf softwire-table-timeout {
                 type uint64;
                 description "Timeout value of flow (seconds)";
               }
             }
             container sfw-flow-entry {
               description "Flow brief information";
               container sfw-flow-nat {
                 description "NAT translation";
                 leaf sfw-flow-nat-type {
                   type string;
                   description "Type of NAT translation";
                 }
                 leaf sfw-flow-nat-ip {
                   type string;
                   description "Original IP address";
                 }
                 leaf sfw-flow-nat-port {
                   type string;
                   description "Original port";
                 }
                 leaf sfw-flow-translated-ip {
                   type string;
                   description "Translated IP address";
                 }
                 leaf sfw-flow-translated-port {
                   type string;
                   description "Translated port";
                 }
               }
               container sw-flow-nat-entry {
                 description "NAT translation";
               }
             }
           }
         }
       }
     }
   }
   rpc get-service-softwire-v6rd-flow-table-information {
     description "Show v6rd related softwire flows";
     input {
       leaf concentrator {
         description "Softwire concentrator IPV4 Address";
         type ipv4addr;
       }
       leaf initiator {
         description "Softwire initiator IPV4 Address";
         type ipv4addr;
       }
     }
     output {
       container service-softwire-flow-table-information {
         container softwire-per-service-set-flow-table {
           description "Flows sorted by service set";
           leaf interface-name {
             type string;
             description "Name of the adaptive services interface";
           }
           leaf service-set-name {
             type string;
             description "Name of the service set";
           }
           container service-softwire-table {
             description "Softwire flows";
             leaf service-softwire-table.heading {
               type string;
               description "Softwire flows";
             }
             container softwire-entry {
               description "Flow brief information";
               leaf softwire-source-ip {
                 type string;
                 description "Softwire source IP address";
               }
               leaf softwire-destination-ip {
                 type string;
                 description "Softwire destination IP address";
               }
               leaf softwire-direction {
                 type string;
                 description "Softwire direction";
               }
               leaf softwire-flow-count {
                 type string;
                 description "Number of flows in softwire";
               }
               leaf softwire-table-timeout {
                 type uint64;
                 description "Timeout value of flow (seconds)";
               }
             }
             container sfw-flow-entry {
               description "Flow brief information";
               container sfw-flow-nat {
                 description "NAT translation";
                 leaf sfw-flow-nat-type {
                   type string;
                   description "Type of NAT translation";
                 }
                 leaf sfw-flow-nat-ip {
                   type string;
                   description "Original IP address";
                 }
                 leaf sfw-flow-nat-port {
                   type string;
                   description "Original port";
                 }
                 leaf sfw-flow-translated-ip {
                   type string;
                   description "Translated IP address";
                 }
                 leaf sfw-flow-translated-port {
                   type string;
                   description "Translated port";
                 }
               }
               container sw-flow-nat-entry {
                 description "NAT translation";
               }
             }
           }
         }
       }
     }
   }
   rpc get-service-softwire-statistics-information {
     description "Show global softwire statistics";
     input {
       leaf interface {
         description "Name of adaptive services interface";
         type string;
       }
       leaf display {
         type enumeration {
           enum "ds-lite" {
             description "Show softwire statistics for dslite";
           }
           enum "v6rd" {
             description "Show softwire statistics for v6rd";
           }
         }
       }
     }
     output {
       container service-softwire-statistics-information {
         container ds-lite {
           description "Softwire statistics information";
           container service-softwire-dslite-statistics-entry {
             description "DS-Lite Statistics";
             leaf srv-pic-name {
               type string;
               description "Services PIC Name";
             }
             leaf softwire-created {
               type uint32;
               description "Number of Softwires Created";
             }
             leaf softwire-created-for-reverse-packet {
               type uint32;
               description "Number of Softwires Created for EIF/HP packets";
             }
             leaf softwire-deleted {
               type uint32;
               description "Number of Softwires Deleted";
             }
             leaf flows-created {
               type uint32;
               description "Number of Flows Created";
             }
             leaf flows-deleted {
               type uint32;
               description "Number of Flows Deleted";
             }
             leaf slow-path {
               type uint32;
               description "Slow Path Packets Processed";
             }
             leaf slow-path-reverse-packet {
               type uint32;
               description "Slow Path Packets Processed for EIF/HP";
             }
             leaf fast-path {
               type uint32;
               description "Fast Path Packets Processed";
             }
             leaf fast-path-encap {
               type uint32;
               description "Fast Path Packets Encapsulated";
             }
             leaf softwire-eif-rule-accepts {
               type uint32;
               description "Softwire EIF accepts";
             }
             leaf rule-match-succeeded {
               type uint32;
               description "Rule Match Succeeded";
             }
             leaf rule-match-failed {
               type uint32;
               description "Rule Match Failed";
             }
             leaf ipv6-packets-fragmented {
               type uint32;
               description "IPv6 Packets Fragmented";
             }
             leaf ipv4-client-fragments {
               type uint32;
               description "IPv4 Client Fragments";
             }
             leaf ipv4-server-first-fragments {
               type uint32;
               description "IPv4 Server First Fragments";
             }
             leaf ipv4-server-more-fragments {
               type uint32;
               description "IPv4 Server More Fragments";
             }
             leaf ipv4-server-last-fragments {
               type uint32;
               description "IPv4 Server Last Fragments";
             }
             leaf softwire-icmpv4-sent {
               type uint32;
               description "ICMPv4 Packets sent";
             }
             leaf softwire-icmpv4-err-sent {
               type uint32;
               description "ICMPv4 Error Packets sent";
             }
             leaf softwire-icmpv6-sent {
               type uint32;
               description "ICMPv6 Packets sent";
             }
             leaf softwire-icmpv6-drop {
               type uint32;
               description "Dropped ICMPv6 packets destined to AFTR";
             }
             leaf flow-creation-failed-retry {
               type uint32;
               description "Flow Creation Failed - Retry";
             }
             leaf flow-creation-failed-retry-for-reverse-packet {
               type uint32;
               description "Flow Creation Failed - Retry for EIF/HP";
             }
             leaf slow-path-failed-retry {
               type uint32;
               description "Slow Path Failed - Retry";
             }
             leaf softwire-creation-failed {
               type uint32;
               description "Softwire Creation Failed";
             }
             leaf softwire-creation-failed-for-reverse-packet {
               type uint32;
               description "Softwire Creation Failed for EIF/HP";
             }
             leaf flow-creation-failed {
               type uint32;
               description "Flow Creation Failed";
             }
             leaf flow-creation-failed-for-reverse-packet {
               type uint32;
               description "Flow Creation Failed for EIF/HP";
             }
             leaf slow-path-failed {
               type uint32;
               description "Slow Path Failed";
             }
             leaf packet-not-ipv4-in-ipv6 {
               type uint32;
               description "Packet not IPv4 in IPv6";
             }
             leaf ipv6-fragmentation-error {
               type uint32;
               description "IPv6 Fragmentation Error";
             }
             leaf softwire-creation-failed-ipv6-next-header-offset {
               type uint32;
               description "Softwire Creation Failed - IPv6 Next Header Offset";
             }
             leaf decap-failed-packet-not-ipv4 {
               type uint32;
               description "Decapsulated Packet not IPv4";
             }
             leaf decap-failed-ipv6-next-header-offset {
               type uint32;
               description "Decap Failed - IPv6 Next Header Offset";
             }
             leaf decap-failed-ipv4-l3-integrity {
               type uint32;
               description "Decap Failed - IPv4 L3 Integrity";
             }
             leaf decap-failed-ipv4-l4-integrity {
               type uint32;
               description "Decap Failed - IPv4 L4 Integrity";
             }
             leaf decap-failed-ipv6-frag-no-mem {
               type uint32;
               description "Decap Failed - IPv4 Frag Out of Memory";
             }
             leaf no-softwire-id {
               type uint32;
               description "No Softwire ID";
             }
             leaf no-flow-extension {
               type uint32;
               description "No Flow Extension";
             }
             leaf flow-limit-exceeded {
               type uint32;
               description "Flow Limit Exceeded";
             }
             leaf session-limit-exceeded {
               type uint32;
               description "Session Limit Exceeded";
             }
           }
           container service-softwire-6rd-statistics-entry {
             description "6rd Statistics";
             leaf srv-pic-name {
               type string;
               description "Services PIC Name";
             }
             leaf softwire-created {
               type uint32;
               description "Number of Softwires Created";
             }
             leaf softwire-deleted {
               type uint32;
               description "Number of Softwires Deleted";
             }
             leaf flows-created {
               type uint32;
               description "Number of Flows Created";
             }
             leaf flows-deleted {
               type uint32;
               description "Number of Flows Deleted";
             }
             leaf slow-path {
               type uint32;
               description "Slow Path Packets Processed";
             }
             leaf slow-path-gratuitous-packet {
               type uint32;
               description "Slow Path for Gratuitous Packet";
             }
             leaf fast-path {
               type uint32;
               description "Fast Path Packets Processed";
             }
             leaf fast-path-encap {
               type uint32;
               description "Fast Path Packets Encapsulated";
             }
             leaf rule-match-succeeded {
               type uint32;
               description "Rule Match Succeeded";
             }
             leaf rule-match-failed {
               type uint32;
               description "Rule Match Failed";
             }
             leaf flow-creation-failed-retry {
               type uint32;
               description "Flow Creation Failed - Retry";
             }
             leaf slow-path-failed-retry {
               type uint32;
               description "Slow Path Failed - Retry";
             }
             leaf softwire-creation-failed {
               type uint32;
               description "Softwire Creation Failed";
             }
             leaf flow-creation-failed {
               type uint32;
               description "Flow Creation Failed";
             }
             leaf slow-path-failed {
               type uint32;
               description "Slow Path Failed";
             }
             leaf packet-not-ipv6-in-ipv4 {
               type uint32;
               description "Packet not IPv6 in IPv4";
             }
             leaf softwire-creation-failed-ipv6-next-header-offset {
               type uint32;
               description "Softwire Creation Failed - IPv6 Next Header Offset";
             }
             leaf decap-packet-not-ipv6 {
               type uint32;
               description "Decapsulated Packet not IPv6";
             }
             leaf no-space-for-outer-header {
               type uint32;
               description "Encapsulation Failed - No space for Outer Header";
             }
             leaf no-softwire-id {
               type uint32;
               description "No Softwire ID";
             }
             leaf no-flow-extension {
               type uint32;
               description "No Flow Extension";
             }
             leaf icmpv4-dropped-packets {
               type uint32;
               description "ICMPv4 Dropped Packets";
             }
           }
         }
         container v6rd {
           description "Softwire statistics information";
           container service-softwire-dslite-statistics-entry {
             description "DS-Lite Statistics";
             leaf srv-pic-name {
               type string;
               description "Services PIC Name";
             }
             leaf softwire-created {
               type uint32;
               description "Number of Softwires Created";
             }
             leaf softwire-created-for-reverse-packet {
               type uint32;
               description "Number of Softwires Created for EIF/HP packets";
             }
             leaf softwire-deleted {
               type uint32;
               description "Number of Softwires Deleted";
             }
             leaf flows-created {
               type uint32;
               description "Number of Flows Created";
             }
             leaf flows-deleted {
               type uint32;
               description "Number of Flows Deleted";
             }
             leaf slow-path {
               type uint32;
               description "Slow Path Packets Processed";
             }
             leaf slow-path-reverse-packet {
               type uint32;
               description "Slow Path Packets Processed for EIF/HP";
             }
             leaf fast-path {
               type uint32;
               description "Fast Path Packets Processed";
             }
             leaf fast-path-encap {
               type uint32;
               description "Fast Path Packets Encapsulated";
             }
             leaf softwire-eif-rule-accepts {
               type uint32;
               description "Softwire EIF accepts";
             }
             leaf rule-match-succeeded {
               type uint32;
               description "Rule Match Succeeded";
             }
             leaf rule-match-failed {
               type uint32;
               description "Rule Match Failed";
             }
             leaf ipv6-packets-fragmented {
               type uint32;
               description "IPv6 Packets Fragmented";
             }
             leaf ipv4-client-fragments {
               type uint32;
               description "IPv4 Client Fragments";
             }
             leaf ipv4-server-first-fragments {
               type uint32;
               description "IPv4 Server First Fragments";
             }
             leaf ipv4-server-more-fragments {
               type uint32;
               description "IPv4 Server More Fragments";
             }
             leaf ipv4-server-last-fragments {
               type uint32;
               description "IPv4 Server Last Fragments";
             }
             leaf softwire-icmpv4-sent {
               type uint32;
               description "ICMPv4 Packets sent";
             }
             leaf softwire-icmpv4-err-sent {
               type uint32;
               description "ICMPv4 Error Packets sent";
             }
             leaf softwire-icmpv6-sent {
               type uint32;
               description "ICMPv6 Packets sent";
             }
             leaf softwire-icmpv6-drop {
               type uint32;
               description "Dropped ICMPv6 packets destined to AFTR";
             }
             leaf flow-creation-failed-retry {
               type uint32;
               description "Flow Creation Failed - Retry";
             }
             leaf flow-creation-failed-retry-for-reverse-packet {
               type uint32;
               description "Flow Creation Failed - Retry for EIF/HP";
             }
             leaf slow-path-failed-retry {
               type uint32;
               description "Slow Path Failed - Retry";
             }
             leaf softwire-creation-failed {
               type uint32;
               description "Softwire Creation Failed";
             }
             leaf softwire-creation-failed-for-reverse-packet {
               type uint32;
               description "Softwire Creation Failed for EIF/HP";
             }
             leaf flow-creation-failed {
               type uint32;
               description "Flow Creation Failed";
             }
             leaf flow-creation-failed-for-reverse-packet {
               type uint32;
               description "Flow Creation Failed for EIF/HP";
             }
             leaf slow-path-failed {
               type uint32;
               description "Slow Path Failed";
             }
             leaf packet-not-ipv4-in-ipv6 {
               type uint32;
               description "Packet not IPv4 in IPv6";
             }
             leaf ipv6-fragmentation-error {
               type uint32;
               description "IPv6 Fragmentation Error";
             }
             leaf softwire-creation-failed-ipv6-next-header-offset {
               type uint32;
               description "Softwire Creation Failed - IPv6 Next Header Offset";
             }
             leaf decap-failed-packet-not-ipv4 {
               type uint32;
               description "Decapsulated Packet not IPv4";
             }
             leaf decap-failed-ipv6-next-header-offset {
               type uint32;
               description "Decap Failed - IPv6 Next Header Offset";
             }
             leaf decap-failed-ipv4-l3-integrity {
               type uint32;
               description "Decap Failed - IPv4 L3 Integrity";
             }
             leaf decap-failed-ipv4-l4-integrity {
               type uint32;
               description "Decap Failed - IPv4 L4 Integrity";
             }
             leaf decap-failed-ipv6-frag-no-mem {
               type uint32;
               description "Decap Failed - IPv4 Frag Out of Memory";
             }
             leaf no-softwire-id {
               type uint32;
               description "No Softwire ID";
             }
             leaf no-flow-extension {
               type uint32;
               description "No Flow Extension";
             }
             leaf flow-limit-exceeded {
               type uint32;
               description "Flow Limit Exceeded";
             }
             leaf session-limit-exceeded {
               type uint32;
               description "Session Limit Exceeded";
             }
             leaf slow-path-gratuitous-packet {
               type uint32;
               description "Slow Path for Gratuitous Packet";
             }
             leaf packet-not-ipv6-in-ipv4 {
               type uint32;
               description "Packet not IPv6 in IPv4";
             }
             leaf decap-packet-not-ipv6 {
               type uint32;
               description "Decapsulated Packet not IPv6";
             }
             leaf no-space-for-outer-header {
               type uint32;
               description "Encapsulation Failed - No space for Outer Header";
             }
             leaf icmpv4-dropped-packets {
               type uint32;
               description "ICMPv4 Dropped Packets";
             }
           }
           container service-softwire-6rd-statistics-entry {
             description "6rd Statistics";
             leaf srv-pic-name {
               type string;
               description "Services PIC Name";
             }
             leaf softwire-created {
               type uint32;
               description "Number of Softwires Created";
             }
             leaf softwire-deleted {
               type uint32;
               description "Number of Softwires Deleted";
             }
             leaf flows-created {
               type uint32;
               description "Number of Flows Created";
             }
             leaf flows-deleted {
               type uint32;
               description "Number of Flows Deleted";
             }
             leaf slow-path {
               type uint32;
               description "Slow Path Packets Processed";
             }
             leaf slow-path-gratuitous-packet {
               type uint32;
               description "Slow Path for Gratuitous Packet";
             }
             leaf fast-path {
               type uint32;
               description "Fast Path Packets Processed";
             }
             leaf fast-path-encap {
               type uint32;
               description "Fast Path Packets Encapsulated";
             }
             leaf rule-match-succeeded {
               type uint32;
               description "Rule Match Succeeded";
             }
             leaf rule-match-failed {
               type uint32;
               description "Rule Match Failed";
             }
             leaf flow-creation-failed-retry {
               type uint32;
               description "Flow Creation Failed - Retry";
             }
             leaf slow-path-failed-retry {
               type uint32;
               description "Slow Path Failed - Retry";
             }
             leaf softwire-creation-failed {
               type uint32;
               description "Softwire Creation Failed";
             }
             leaf flow-creation-failed {
               type uint32;
               description "Flow Creation Failed";
             }
             leaf slow-path-failed {
               type uint32;
               description "Slow Path Failed";
             }
             leaf packet-not-ipv6-in-ipv4 {
               type uint32;
               description "Packet not IPv6 in IPv4";
             }
             leaf softwire-creation-failed-ipv6-next-header-offset {
               type uint32;
               description "Softwire Creation Failed - IPv6 Next Header Offset";
             }
             leaf decap-packet-not-ipv6 {
               type uint32;
               description "Decapsulated Packet not IPv6";
             }
             leaf no-space-for-outer-header {
               type uint32;
               description "Encapsulation Failed - No space for Outer Header";
             }
             leaf no-softwire-id {
               type uint32;
               description "No Softwire ID";
             }
             leaf no-flow-extension {
               type uint32;
               description "No Flow Extension";
             }
             leaf icmpv4-dropped-packets {
               type uint32;
               description "ICMPv4 Dropped Packets";
             }
           }
         }
       }
     }
   }
   rpc get-service-ids-source-table-information {
     description "Show attack source address table";
     input {
       leaf source-prefix {
         description "Source prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type int32;
       }
       leaf limit {
         description "Maximum number of entries to display";
         type int32;
       }
       leaf display {
         default "brief";
         type enumeration {
           enum "extensive" {
             description "Display extensive output";
           }
           enum "brief" {
             description "Display brief output (default)";
           }
           enum "terse" {
             description "Display terse output";
           }
         }
       }
     }
     output {
       container service-ids-flow-table-information {
         container ids-show-summary {
           description "IDS table summary";
           leaf interface-name {
             type string;
             description "Name of the adaptive services interface";
           }
           leaf ids-total-entries {
             type uint64;
             description "Total number of filled entries in IDS table";
           }
           leaf ids-total-failed-insertions {
             type uint64;
             description "Total number of failed IDS table entry insertions";
           }
           leaf ids-total-events {
             type uint64;
             description "Total number of events (closed flows and anomalies)";
           }
         }
         container ids-per-service-set-flow-table {
           description "IDS table sorted by service set";
           leaf interface-name {
             type string;
             description "Name of the adaptive services interface";
           }
           leaf service-set-name {
             type string;
             description "Name of the service set";
           }
           leaf ids-sort-order {
             type string;
             description "IDS table sorting order";
           }
           container ids-flow-table {
             description "IDS table sorted by service set";
             leaf ids-flow-table.heading {
               type string;
               description "IDS table sorted by service set";
             }
             container ids-flow-entry {
               description "IDS terse information";
               container brief {
                 description "IDS terse information";
                 leaf ids-flow-source-ip {
                   type ipaddr;
                   description "Source IP address";
                 }
                 leaf ids-flow-destination-ip {
                   type ipaddr;
                   description "Destination IP address";
                 }
                 leaf ids-flow-time {
                   type string;
                   description "Time from last event";
                 }
                 leaf ids-flow-flags {
                   type string;
                   description "S - SYN cookie enabled, F - Forced entry";
                 }
                 leaf ids-flow-count {
                   type string;
                   description "Value depend from request (packet number, bytes, and so on)";
                 }
                 leaf ids-flow-application {
                   type string;
                   description "Application name";
                 }
                 container ids-anomaly-entry {
                   description "IDS anomaly information";
                   leaf ids-anomaly-description {
                     type string;
                     description "Anomaly description";
                   }
                   leaf ids-anomaly-count {
                     type string;
                     description "Number of anomalies for current type";
                   }
                   leaf ids-anomaly-rate {
                     type string;
                     description "Rate of anomalies (events per second)";
                   }
                   leaf ids-anomaly-elapsed {
                     type string;
                     description "Elapsed time from last event";
                   }
                 }
               }
               container verbose {
                 description "IDS terse information";
                 leaf ids-flow-source-ip {
                   type ipaddr;
                   description "Source IP address";
                 }
                 leaf ids-flow-destination-ip {
                   type ipaddr;
                   description "Destination IP address";
                 }
                 leaf ids-flow-time {
                   type string;
                   description "Time from last event";
                 }
                 leaf ids-flow-long-flags {
                   type string;
                   description "SYN cookie enabled, Forced entry";
                 }
                 leaf ids-flow-application {
                   type string;
                   description "Application name";
                 }
                 leaf ids-bytes-count {
                   type string;
                   description "Number of bytes";
                 }
                 leaf ids-packets-count {
                   type string;
                   description "Number of packets";
                 }
                 leaf ids-flows-count {
                   type string;
                   description "Number of flows";
                 }
                 leaf ids-anomalies-count {
                   type string;
                   description "Number of anomalies";
                 }
                 container ids-anomaly-entry {
                   description "IDS anomaly information";
                   leaf ids-anomaly-description {
                     type string;
                     description "Anomaly description";
                   }
                   leaf ids-anomaly-count {
                     type string;
                     description "Number of anomalies for current type";
                   }
                   leaf ids-anomaly-rate {
                     type string;
                     description "Rate of anomalies (events per second)";
                   }
                   leaf ids-anomaly-elapsed {
                     type string;
                     description "Elapsed time from last event";
                   }
                 }
               }
             }
           }
         }
       }
     }
   }
   rpc get-service-ids-destination-table-information {
     description "Show attack destination address table";
     input {
       leaf destination-prefix {
         description "Destination prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type int32;
       }
       leaf limit {
         description "Maximum number of entries to display";
         type int32;
       }
       leaf display {
         default "brief";
         type enumeration {
           enum "extensive" {
             description "Display extensive output";
           }
           enum "brief" {
             description "Display brief output (default)";
           }
           enum "terse" {
             description "Display terse output";
           }
         }
       }
     }
     output {
       container service-ids-flow-table-information {
         container ids-show-summary {
           description "IDS table summary";
           leaf interface-name {
             type string;
             description "Name of the adaptive services interface";
           }
           leaf ids-total-entries {
             type uint64;
             description "Total number of filled entries in IDS table";
           }
           leaf ids-total-failed-insertions {
             type uint64;
             description "Total number of failed IDS table entry insertions";
           }
           leaf ids-total-events {
             type uint64;
             description "Total number of events (closed flows and anomalies)";
           }
         }
         container ids-per-service-set-flow-table {
           description "IDS table sorted by service set";
           leaf interface-name {
             type string;
             description "Name of the adaptive services interface";
           }
           leaf service-set-name {
             type string;
             description "Name of the service set";
           }
           leaf ids-sort-order {
             type string;
             description "IDS table sorting order";
           }
           container ids-flow-table {
             description "IDS table sorted by service set";
             leaf ids-flow-table.heading {
               type string;
               description "IDS table sorted by service set";
             }
             container ids-flow-entry {
               description "IDS terse information";
               container brief {
                 description "IDS terse information";
                 leaf ids-flow-source-ip {
                   type ipaddr;
                   description "Source IP address";
                 }
                 leaf ids-flow-destination-ip {
                   type ipaddr;
                   description "Destination IP address";
                 }
                 leaf ids-flow-time {
                   type string;
                   description "Time from last event";
                 }
                 leaf ids-flow-flags {
                   type string;
                   description "S - SYN cookie enabled, F - Forced entry";
                 }
                 leaf ids-flow-count {
                   type string;
                   description "Value depend from request (packet number, bytes, and so on)";
                 }
                 leaf ids-flow-application {
                   type string;
                   description "Application name";
                 }
                 container ids-anomaly-entry {
                   description "IDS anomaly information";
                   leaf ids-anomaly-description {
                     type string;
                     description "Anomaly description";
                   }
                   leaf ids-anomaly-count {
                     type string;
                     description "Number of anomalies for current type";
                   }
                   leaf ids-anomaly-rate {
                     type string;
                     description "Rate of anomalies (events per second)";
                   }
                   leaf ids-anomaly-elapsed {
                     type string;
                     description "Elapsed time from last event";
                   }
                 }
               }
               container verbose {
                 description "IDS terse information";
                 leaf ids-flow-source-ip {
                   type ipaddr;
                   description "Source IP address";
                 }
                 leaf ids-flow-destination-ip {
                   type ipaddr;
                   description "Destination IP address";
                 }
                 leaf ids-flow-time {
                   type string;
                   description "Time from last event";
                 }
                 leaf ids-flow-long-flags {
                   type string;
                   description "SYN cookie enabled, Forced entry";
                 }
                 leaf ids-flow-application {
                   type string;
                   description "Application name";
                 }
                 leaf ids-bytes-count {
                   type string;
                   description "Number of bytes";
                 }
                 leaf ids-packets-count {
                   type string;
                   description "Number of packets";
                 }
                 leaf ids-flows-count {
                   type string;
                   description "Number of flows";
                 }
                 leaf ids-anomalies-count {
                   type string;
                   description "Number of anomalies";
                 }
                 container ids-anomaly-entry {
                   description "IDS anomaly information";
                   leaf ids-anomaly-description {
                     type string;
                     description "Anomaly description";
                   }
                   leaf ids-anomaly-count {
                     type string;
                     description "Number of anomalies for current type";
                   }
                   leaf ids-anomaly-rate {
                     type string;
                     description "Rate of anomalies (events per second)";
                   }
                   leaf ids-anomaly-elapsed {
                     type string;
                     description "Elapsed time from last event";
                   }
                 }
               }
             }
           }
         }
       }
     }
   }
   rpc get-service-ids-pair-table-information {
     description "Show attack source and destination address pair table";
     input {
       leaf source-prefix {
         description "Source prefix to use as filter";
         type string;
       }
       leaf destination-prefix {
         description "Destination prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type int32;
       }
       leaf limit {
         description "Maximum number of entries to display";
         type int32;
       }
       leaf display {
         default "brief";
         type enumeration {
           enum "extensive" {
             description "Display extensive output";
           }
           enum "brief" {
             description "Display brief output (default)";
           }
           enum "terse" {
             description "Display terse output";
           }
         }
       }
     }
     output {
       container service-ids-flow-table-information {
         container ids-show-summary {
           description "IDS table summary";
           leaf interface-name {
             type string;
             description "Name of the adaptive services interface";
           }
           leaf ids-total-entries {
             type uint64;
             description "Total number of filled entries in IDS table";
           }
           leaf ids-total-failed-insertions {
             type uint64;
             description "Total number of failed IDS table entry insertions";
           }
           leaf ids-total-events {
             type uint64;
             description "Total number of events (closed flows and anomalies)";
           }
         }
         container ids-per-service-set-flow-table {
           description "IDS table sorted by service set";
           leaf interface-name {
             type string;
             description "Name of the adaptive services interface";
           }
           leaf service-set-name {
             type string;
             description "Name of the service set";
           }
           leaf ids-sort-order {
             type string;
             description "IDS table sorting order";
           }
           container ids-flow-table {
             description "IDS table sorted by service set";
             leaf ids-flow-table.heading {
               type string;
               description "IDS table sorted by service set";
             }
             container ids-flow-entry {
               description "IDS terse information";
               container brief {
                 description "IDS terse information";
                 leaf ids-flow-source-ip {
                   type ipaddr;
                   description "Source IP address";
                 }
                 leaf ids-flow-destination-ip {
                   type ipaddr;
                   description "Destination IP address";
                 }
                 leaf ids-flow-time {
                   type string;
                   description "Time from last event";
                 }
                 leaf ids-flow-flags {
                   type string;
                   description "S - SYN cookie enabled, F - Forced entry";
                 }
                 leaf ids-flow-count {
                   type string;
                   description "Value depend from request (packet number, bytes, and so on)";
                 }
                 leaf ids-flow-application {
                   type string;
                   description "Application name";
                 }
                 container ids-anomaly-entry {
                   description "IDS anomaly information";
                   leaf ids-anomaly-description {
                     type string;
                     description "Anomaly description";
                   }
                   leaf ids-anomaly-count {
                     type string;
                     description "Number of anomalies for current type";
                   }
                   leaf ids-anomaly-rate {
                     type string;
                     description "Rate of anomalies (events per second)";
                   }
                   leaf ids-anomaly-elapsed {
                     type string;
                     description "Elapsed time from last event";
                   }
                 }
               }
               container verbose {
                 description "IDS terse information";
                 leaf ids-flow-source-ip {
                   type ipaddr;
                   description "Source IP address";
                 }
                 leaf ids-flow-destination-ip {
                   type ipaddr;
                   description "Destination IP address";
                 }
                 leaf ids-flow-time {
                   type string;
                   description "Time from last event";
                 }
                 leaf ids-flow-long-flags {
                   type string;
                   description "SYN cookie enabled, Forced entry";
                 }
                 leaf ids-flow-application {
                   type string;
                   description "Application name";
                 }
                 leaf ids-bytes-count {
                   type string;
                   description "Number of bytes";
                 }
                 leaf ids-packets-count {
                   type string;
                   description "Number of packets";
                 }
                 leaf ids-flows-count {
                   type string;
                   description "Number of flows";
                 }
                 leaf ids-anomalies-count {
                   type string;
                   description "Number of anomalies";
                 }
                 container ids-anomaly-entry {
                   description "IDS anomaly information";
                   leaf ids-anomaly-description {
                     type string;
                     description "Anomaly description";
                   }
                   leaf ids-anomaly-count {
                     type string;
                     description "Number of anomalies for current type";
                   }
                   leaf ids-anomaly-rate {
                     type string;
                     description "Rate of anomalies (events per second)";
                   }
                   leaf ids-anomaly-elapsed {
                     type string;
                     description "Elapsed time from last event";
                   }
                 }
               }
             }
           }
         }
       }
     }
   }
   rpc get-service-identification-statistics-information {
     description "Show service identification statistics";
     input {
       leaf detail {
         description "Display detailed statistics";
         type empty;
       }
     }
     output {
       container service-identification-statistics-information {
         container service-identification-statistics {
           description "Statistics for the service-identification service";
           leaf interface-name {
             type string;
             description "Name of the adaptive services interface";
           }
           leaf interfaces {
             type uint32;
             description "Total number of interfaces summarized";
           }
           leaf packets {
             type uint64;
             description "Total packets processed by service";
           }
           leaf bytes {
             type uint64;
             description "Total bytes for all packets processed by the service-identification service";
           }
           leaf errored-packets {
             type uint64;
             description "Packets errored by the service-identification service in processing";
           }
           leaf errored-bytes {
             type uint64;
             description "Total bytes for all packets errored by the service-identification service";
           }
           leaf header-examination-packets {
             type uint64;
             description "Packets processed by header examination";
           }
           leaf header-examination-bytes {
             type uint64;
             description "Total bytes for all packets processed by header examination";
           }
           leaf header-examination-flow {
             type uint64;
             description "Total flows examined by header examination";
           }
           leaf header-examination-flow-matched {
             type uint64;
             description "Total flows that matched a header examination rule";
           }
           leaf header-examination-protocol-required {
             type uint64;
             description "Flows identified as requiring protocol inspection";
           }
           leaf header-examination-http-protocol-required {
             type uint64;
             description "Flows identified as possible HTTP flows by header examination rules";
           }
           leaf header-examination-wap-protocol-required {
             type uint64;
             description "Flows identified as possible WAP flows by header examination rules";
           }
           leaf protocol-inspected-flow {
             type uint64;
             description "Total flows that have been protocol inspected";
           }
           leaf protocol-inspection-flow {
             type uint32;
             description "Total flows currently undergoing protocol inspection";
           }
           leaf protocol-inspection-packets {
             type uint64;
             description "Packets processed by protocol inspection";
           }
           leaf protocol-inspection-bytes {
             type uint64;
             description "Total bytes for all packets processed by protocol inspection";
           }
           leaf protocol-inspection-flow-protocol-identified {
             type uint64;
             description "Total flows that have been protocol-identified by protocol inspection";
           }
           leaf protocol-inspection-http-uri {
             type uint64;
             description "HTTP URI by protocol inspection";
           }
           leaf protocol-inspection-http-uri-matched {
             type uint64;
             description "HTTP URI that matched a URI rule";
           }
           leaf protocol-inspection-wap-uri {
             type uint64;
             description "WAP URI by protocol inspection";
           }
           leaf protocol-inspection-wap-uri-matched {
             type uint64;
             description "WAP URI that matched a URI rule";
           }
           leaf wap-transaction-created {
             type uint64;
             description "WAP transaction sessions created";
           }
           leaf wap-transaction-maximum {
             type int32;
             description "Peak WAP transaction sessions";
           }
           leaf wap-transaction-freed {
             type uint64;
             description "WAP transaction sessions freed";
           }
           leaf wap-transaction-idle-freed {
             type uint64;
             description "WAP transaction sessions freed by idle clean-up";
           }
           leaf http-transaction-created {
             type uint64;
             description "HTTP transaction sessions created";
           }
           leaf http-transaction-maximum {
             type int32;
             description "Peak HTTP transaction sessions";
           }
           leaf http-transaction-freed {
             type uint64;
             description "HTTP transaction sessions freed";
           }
           leaf http-transaction-idle-freed {
             type uint64;
             description "HTTP transaction sessions freed by idle clean-up";
           }
           leaf packet-processing-error {
             type uint64;
             description "Total for all packet-processing errors";
           }
           leaf errored-packets-tcp-malformed {
             type uint64;
             description "TCP packets errored because they were malformed";
           }
           leaf errored-packets-http-transaction-in-error {
             type uint64;
             description "HTTP packets errored because the transaction is in error";
           }
           leaf errored-packets-wap-invalid-transaction {
             type uint64;
             description "WAP packets errored for referencing an invalid transaction";
           }
           leaf errored-packets-wap-transaction-in-error {
             type uint64;
             description "WAP packets errored because the transaction is in error";
           }
           leaf uri-processing-error {
             type uint64;
             description "Total for all URI processing errors";
           }
           leaf uri-error-failed-to-process {
             type uint64;
             description "Failures to process a URI due to internal error";
           }
           leaf uri-error-too-long {
             type uint64;
             description "Failures to process a URI due to maximum length exceeded";
           }
           leaf transaction-error-failed-to-parse {
             type uint64;
             description "Failures to parse a transaction";
           }
           leaf uri-error-no-system-resources {
             type uint64;
             description "Failures to process a transaction or URI due to lack of resources";
           }
           leaf header-examination-failed-configuration {
             type uint64;
             description "Number of header examinations failing due to configuration error";
           }
           leaf uri-examination-failed-configuration {
             type uint64;
             description "Number of URI examinations failing due to configuration error";
           }
         }
       }
     }
   }
   rpc get-header-redirect-set-statistics-information {
     description "Show header redirect set statistics";
     input {
       leaf detail {
         description "Display detailed statistics";
         type empty;
       }
     }
     output {
       container header-redirect-set-statistics-information {
         leaf interface-name {
           type string;
           description "Name of the adaptive services interface";
         }
         leaf interfaces {
           type uint32;
           description "Total number of interfaces summarized";
         }
         container header-redirect-set-statistics {
           description "Statistics for the header redirect sets";
           leaf header-redirect-set-name {
             type string;
             description "Name of the header redirect set";
           }
           leaf cause-roaming {
             type uint32;
             description "Number of redirects due to roaming";
           }
           leaf cause-time-of-day {
             type uint32;
             description "Number of redirects due to time of day";
           }
           leaf cause-quality-of-service {
             type uint32;
             description "Number of redirects due to QoS";
           }
           leaf cause-volume-expired {
             type uint32;
             description "Number of redirects due to expiration of volume limit";
           }
           leaf cause-cost-warning {
             type uint32;
             description "Number of redirects due to cost warning limit";
           }
           leaf cause-not-allowed {
             type uint32;
             description "Number of redirects due to disallowed service class";
           }
           leaf cause-unsubscribed {
             type uint32;
             description "Number of redirects due to unsubscribed service class";
           }
           leaf cause-credit-expiry {
             type uint32;
             description "Number of redirects due to expiration of credit";
           }
           leaf cause-unknown {
             type uint32;
             description "Number of redirects due to unknown reason";
           }
           leaf cause-default {
             type uint32;
             description "Number of redirects due to default reason match";
           }
         }
       }
     }
   }
   rpc get-uri-redirect-set-statistics-information {
     description "Show URI redirect set statistics";
     input {
       leaf detail {
         description "Display detailed statistics";
         type empty;
       }
     }
     output {
       container uri-redirect-set-statistics-information {
         leaf interface-name {
           type string;
           description "Name of the adaptive services interface";
         }
         leaf interfaces {
           type uint32;
           description "Total number of interfaces summarized";
         }
         container uri-redirect-set-statistics {
           description "Statistics for the URI redirect sets";
           leaf uri-redirect-set-name {
             type string;
             description "Name of header redirect set";
           }
           leaf cause-roaming {
             type uint32;
             description "Number of redirects due to roaming";
           }
           leaf cause-time-of-day {
             type uint32;
             description "Number of redirects due to time of day";
           }
           leaf cause-quality-of-service {
             type uint32;
             description "Number of redirects due to QoS";
           }
           leaf cause-volume-expired {
             type uint32;
             description "Number of redirects due to expiration of volume limit";
           }
           leaf cause-cost-warning {
             type uint32;
             description "Number of redirects due to cost warning limit";
           }
           leaf cause-not-allowed {
             type uint32;
             description "Number of redirects due to disallowed service class";
           }
           leaf cause-unsubscribed {
             type uint32;
             description "Number of redirects due to unsubscribed service class";
           }
           leaf cause-credit-expiry {
             type uint32;
             description "Number of redirects due to expiration of credit";
           }
           leaf cause-unknown {
             type uint32;
             description "Number of redirects due to unknown reason";
           }
           leaf cause-default {
             type uint32;
             description "Number of redirects due to default reason match";
           }
         }
       }
     }
   }
   rpc get-flow-table-statistics-information {
     description "Show flow table statistics";
     input {
       leaf detail {
         description "Show detailed statistics information";
         type empty;
       }
     }
     output {
       container flow-table-statistics-information {
         container flow-table-statistics {
           description "Statistics for one or more flow tables";
           leaf interface-name {
             type string;
             description "Name of the adaptive services interface";
           }
           leaf flow-tables {
             type uint32;
             description "Total number of flow tables being summarized";
           }
           leaf flow {
             type uint32;
             description "Total number of flows in the table";
           }
           leaf flow-peak {
             type uint32;
             description "Sampled peak number of flows in the table";
           }
           leaf flow-tcp {
             type uint32;
             description "Total number of TCP flows in the table";
           }
           leaf flow-tcp-peak {
             type uint32;
             description "Sampled peak number of TCP flows in the table";
           }
           leaf flow-udp {
             type uint32;
             description "Total number of UDP flows in the table";
           }
           leaf flow-udp-peak {
             type uint32;
             description "Peak number of UDP flows in the table";
           }
           leaf flow-created {
             type uint64;
             description "Total flows created";
           }
           leaf flow-freed {
             type uint64;
             description "Total flows freed";
           }
           leaf flow-freed-idle {
             type uint64;
             description "Total flows freed by idle flow detection";
           }
           leaf flow-tcp-created {
             type uint64;
             description "Total TCP flows created";
           }
           leaf flow-tcp-freed {
             type uint64;
             description "Total TCP flows freed";
           }
           leaf flow-tcp-freed-idle {
             type uint64;
             description "Total TCP flows freed by idle detection";
           }
           leaf flow-udp-created {
             type uint64;
             description "Total UDP flows created";
           }
           leaf flow-udp-freed {
             type uint64;
             description "Total UDP flows freed";
           }
           leaf flow-udp-freed-idle {
             type uint64;
             description "Total UDP flows freed by idle detection";
           }
           leaf flow-packets-processed {
             type uint64;
             description "Total packets processed by flow table";
           }
           leaf flow-bytes-processed {
             type uint64;
             description "Total bytes for all packets processed by flow table";
           }
           leaf flow-packets-errored {
             type uint64;
             description "Total packets errored by flow table processing";
           }
           leaf flow-byte-errored {
             type uint64;
             description "Total bytes for all packets errored by flow table processing";
           }
           leaf flow-tcp-packets-processed {
             type uint64;
             description "Total TCP packets processed";
           }
           leaf flow-tcp-bytes-processed {
             type uint64;
             description "Total bytes for all processed TCP packets";
           }
           leaf flow-tcp-packets-errored {
             type uint64;
             description "Total TCP packets errored in processing";
           }
           leaf flow-tcp-bytes-errored {
             type uint64;
             description "Total bytes for all TCP packets errored in processing";
           }
           leaf flow-tcp-packets-errored-bad-flow {
             type uint64;
             description "Total TCP packets errored due to referencing an invalid flow";
           }
           leaf flow-udp-packets-processed {
             type uint64;
             description "Total UDP packets processed";
           }
           leaf flow-udp-bytes-processed {
             type uint64;
             description "Total bytes for all processed UDP packets";
           }
           leaf flow-udp-packets-errored {
             type uint64;
             description "Total UDP packets errored in processing";
           }
           leaf flow-udp-bytes-errored {
             type uint64;
             description "Total bytes for all UDP packets errored in processing";
           }
           leaf flow-udp-packets-errored-bad-flow {
             type uint64;
             description "Total UDP packets errored due to referencing an invalid flow";
           }
           leaf flow-icmp-packets-processed {
             type uint64;
             description "Total ICMP packets";
           }
           leaf flow-icmp-bytes-processed {
             type uint64;
             description "Total bytes for all processed ICMP packets";
           }
           leaf flow-icmp-packets-errored {
             type uint64;
             description "Total ICMP packets errored in processing";
           }
           leaf flow-icmp-bytes-errored {
             type uint64;
             description "Total bytes for all ICMP packets errored in processing";
           }
           leaf flow-icmp-packets-errored-bad-flow {
             type uint64;
             description "Total ICMP packets errored due to referencing an invalid flow";
           }
         }
       }
     }
   }
   rpc get-global-pcp-statistics-information {
     description "Show global PCP statistics";
     input {
       leaf interface {
         description "Name of adaptive services interface";
         type string;
       }
       leaf level {
         type enumeration {
           enum "protocol" {
             description "Display PCP protocol statistics";
           }
         }
       }
     }
   }
   rpc get-services-redundancy-group-information {
     description "Show services redundancy-group information";
     input {
       leaf verbose {
         default "terse";
         type enumeration {
           enum "terse" {
             description "Display terse output(default)";
           }
           enum "brief" {
             description "Display brief output";
           }
           enum "extensive" {
             description "Display detailed output";
           }
         }
       }
     }
   }
   rpc get-services-redundancy-group-id-information {
     description "Show redundancy group-id information";
     input {
       leaf verbose {
         default "terse";
         type enumeration {
           enum "terse" {
             description "Display terse output(default)";
           }
           enum "brief" {
             description "Display brief output";
           }
           enum "extensive" {
             description "Display detailed output";
           }
         }
       }
       leaf id {
         description "Show redundancy group-id information";
         type uint32;
         mandatory true;
       }
     }
   }
   rpc get-traffic-load-balance-statistics {
     description "Traffic load balance statistics";
     input {
       leaf verbose {
         type enumeration {
           enum "summary" {
             description "Display summary output";
           }
           enum "extensive" {
             description "Display extensive output";
           }
         }
       }
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
     }
   }
 }
