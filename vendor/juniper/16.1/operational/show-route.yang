/*
 * Copyright (c) 2017 Juniper Networks, Inc.
 * All rights reserved.
 */

 module show-route {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-route-information {
     description "Show routing table information";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
       leaf destination {
         description "IP address and optional prefix length of destination";
         type ipprefix-optional;
       }
       leaf all {
         description "Show all entries, including hidden entries";
         type empty;
       }
       leaf level {
         type enumeration {
           enum "terse" {
             description "Display terse output";
           }
           enum "brief" {
             description "Display brief output";
           }
           enum "detail" {
             description "Display detailed output";
           }
           enum "extensive" {
             description "Display extensive output";
           }
         }
       }
       leaf match {
         type enumeration {
           enum "best" {
             description "Show longest matching route";
           }
           enum "exact" {
             description "Show routes that match exactly";
           }
           enum "range" {
             description "Show all entries in prefix range";
           }
         }
       }
       leaf table {
         description "Name of routing table";
         type string;
       }
       leaf label {
         description "Label of entry in MPLS routing table";
         type uint32;
       }
       leaf ccc {
         description "Name of entry in MPLS table with a circuit cross-connect interface";
         type string;
       }
       leaf inactive-prefix {
         description "Show inactive route destinations";
         type empty;
       }
       leaf inactive-path {
         description "Show inactive paths";
         type empty;
       }
       leaf active-path {
         description "Show active paths";
         type empty;
       }
       leaf private {
         description "Show private table routes";
         type empty;
       }
       leaf damping {
         description "Show entries subjected to particular kind of route damping";
         type enumeration {
           enum "suppressed" {
             description "Entries suppressed due to route damping";
           }
           enum "history" {
             description "Entries that are withdrawn but have history";
           }
           enum "decayed" {
             description "Entries that are decayed but not suppressed";
           }
         }
       }
       container output {
         leaf interface {
           description "Name of interface";
           type interface-unit;
         }
         leaf address {
           description "Address of interface";
           type string;
         }
       }
       leaf next-hop {
         description "IP address of next hop that is destination for entries";
         type ipaddr;
       }
       leaf source-gateway {
         description "IP address of source router for entries";
         type ipaddr;
       }
       leaf protocol {
         description "Name of protocol that is source for entries";
         type enumeration {
           enum "aggregate" {
             description "Locally generated aggregate route";
           }
           enum "bgp" {
             description "Border Gateway Protocol";
           }
           enum "direct" {
             description "Directly connected routes";
           }
           enum "dvmrp" {
             description "Distance Vector Multicast Routing Protocol";
           }
           enum "evpn" {
             description "EVPN";
           }
           enum "isis" {
             description "Intermediate System-to-Intermediate System";
           }
           enum "esis" {
             description "End System-to-Intermediate System";
           }
           enum "ldp" {
             description "Label Distribution Protocol";
           }
           enum "local" {
             description "Local system addresses";
           }
           enum "ospf" {
             description "Open Shortest Path First";
           }
           enum "ospf2" {
             description "Open Shortest Path First Version 2";
           }
           enum "ospf3" {
             description "Open Shortest Path First Version 3";
           }
           enum "pim" {
             description "Protocol Independent Multicast";
           }
           enum "mvpn" {
             description "BGP-MVPN Protocol";
           }
           enum "rip" {
             description "Routing Information Protocol";
           }
           enum "ripng" {
             description "Routing Information Protocol for IPv6";
           }
           enum "rsvp" {
             description "Resource Reservation Protocol";
           }
           enum "static" {
             description "Statically defined prefixes";
           }
           enum "arp" {
             description "Prefixes learned via ARP";
           }
           enum "frr" {
             description "Prefixes created by Host (Direct route) Fast reroute";
           }
           enum "mpls" {
             description "Multiprotocol Label Switching";
           }
           enum "ccc" {
             description "Circuit cross-connect";
           }
           enum "msdp" {
             description "Multicast Source Discovery Protocol";
           }
           enum "vpn" {
             description "Layer 3 virtual private network";
           }
           enum "l2vpn" {
             description "Layer 2 virtual private network";
           }
           enum "l2circuit" {
             description "Layer 2 circuit";
           }
           enum "rtarget" {
             description "Local route target VPN membership";
           }
           enum "tunnel" {
             description "Dynamic tunnel";
           }
           enum "flow" {
             description "Locally defined flow route";
           }
           enum "access" {
             description "Access route";
           }
           enum "access-internal" {
             description "Access-internal route";
           }
           enum "anchor" {
             description "Anchor route";
           }
           enum "bgp-static" {
             description "BGP static route";
           }
           enum "vpls" {
             description "Virtual Private LAN Service";
           }
         }
       }
       container evpn-esi-value {
         leaf esi {
           description "Filter evpn routes for a particular ESI, except evpn MAC routes";
           type string;
         }
       }
       container evpn-mac-address {
         leaf mac_address {
           description "Filter evpn mac routes for a particular MAC";
           type mac-addr;
         }
       }
       container evpn-ethernet-tag-id {
         leaf ethernet-tag {
           description "Filter evpn routes for a particular Ethernet Tag ID";
           type uint32;
         }
       }
       container advertising-protocol {
         leaf advertising-protocol-name {
           description "Name of dynamic routing protocol";
           type enumeration {
             enum "bgp" {
               description "Border Gateway Protocol";
             }
             enum "dvmrp" {
               description "Distance Vector Multicast Routing Protocol";
             }
             enum "pim" {
               description "Protocol Independent Multicast";
             }
             enum "rip" {
               description "Routing Information Protocol";
             }
             enum "ripng" {
               description "Routing Information Protocol for IPv6";
             }
             enum "msdp" {
               description "Multicast Source Discovery Protocol";
             }
           }
         }
         leaf neighbor {
           description "IP address of neighbor (local for RIP and RIPng)";
           type ipaddr;
         }
       }
       container receive-protocol {
         leaf receive-protocol-name {
           description "Name of dynamic routing protocol";
           type enumeration {
             enum "bgp" {
               description "Border Gateway Protocol";
             }
             enum "rip" {
               description "Routing Information Protocol";
             }
             enum "ripng" {
               description "Routing Information Protocol for IPv6";
             }
             enum "dvmrp" {
               description "Distance Vector Multicast Routing Protocol";
             }
             enum "pim" {
               description "Protocol Independent Multicast";
             }
             enum "msdp" {
               description "Multicast Source Discovery Protocol";
             }
           }
         }
         leaf peer {
           description "IP address of neighbor";
           type ipaddr;
         }
       }
       leaf rd-prefix {
         description "Route distinguisher with ip prefix (rd:prefix)";
         type string;
       }
       leaf match-prefix {
         description "Regular expression to match formatted prefix";
         type string;
       }
       leaf aspath-regex {
         description "BGP AS path regular expression for entries to match";
         type string;
       }
       leaf-list community {
         description "Identifier for community (can include wildcards)";
         type string;
       }
       leaf no-community {
         description "Show entries with no associated community";
         type empty;
       }
       leaf community-name {
         description "Name of configured community policy to match";
         type string;
       }
       leaf label-switched-path {
         description "Name of LSP tunnel associated with entries";
         type string {
           length "1 .. 64";
         }
       }
       leaf static-label-switched-path {
         description "Name of static LSP tunnel associated with entries";
         type string {
           length "1 .. 64";
         }
       }
       leaf hidden {
         description "Show hidden entries";
         type empty;
       }
       leaf validation-state {
         description "Show entries with a given validation state";
         type enumeration {
           enum "unverified" {
             description "Unverified route validation state";
           }
           enum "unknown" {
             description "Unknown route validation state";
           }
           enum "valid" {
             description "Valid route validation state";
           }
           enum "invalid" {
             description "Invalid route validation state";
           }
         }
       }
       leaf te-link-local-node-ip {
         description "Local node's IPv4 address in the traffic-engineering link";
         type string;
       }
       leaf te-link-local-node-iso {
         description "Local node's ISO circuit ID in the traffic-engineering link";
         type string {
           junos:posix-pattern "^([[:xdigit:]]{1,4}[.]){3}[[:xdigit:]]{1,2}$";
           junos:pattern-message "Address must be of the form aaaa.bbbb.cccc.dd";
         }
       }
       leaf te-link-remote-node-ip {
         description "Remote node's IPv4 address in the traffic-engineering link";
         type string;
       }
       leaf te-link-remote-node-iso {
         description "Remote node's ISO circuit ID in the traffic-engineering link";
         type string {
           junos:posix-pattern "^([[:xdigit:]]{1,4}[.]){3}[[:xdigit:]]{1,2}$";
           junos:pattern-message "Address must be of the form aaaa.bbbb.cccc.dd";
         }
       }
       leaf te-link-local-ip {
         description "Local IPv4 address of the traffic-engineering link";
         type ipaddr;
       }
       leaf te-link-remote-ip {
         description "Remote IPv4 address of the traffic-engineering link";
         type ipaddr;
       }
       leaf te-node-ip {
         description "IPv4 address of the traffic-engineering node";
         type string;
       }
       leaf te-node-iso {
         description "ISO circuit ID of the traffic-engineering node";
         type string {
           junos:posix-pattern "^([[:xdigit:]]{1,4}[.]){3}[[:xdigit:]]{1,2}$";
           junos:pattern-message "Address must be of the form aaaa.bbbb.cccc.dd";
         }
       }
       leaf output-queue {
         description "BGP output-queue for advertising protocol";
         type enumeration {
           enum "priority-1" {
             description "BGP output queue priority 1";
           }
           enum "priority-2" {
             description "BGP output queue priority 2";
           }
           enum "priority-3" {
             description "BGP output queue priority 3";
           }
           enum "priority-4" {
             description "BGP output queue priority 4";
           }
           enum "priority-5" {
             description "BGP output queue priority 5";
           }
           enum "priority-6" {
             description "BGP output queue priority 6";
           }
           enum "priority-7" {
             description "BGP output queue priority 7";
           }
           enum "priority-8" {
             description "BGP output queue priority 8";
           }
           enum "priority-9" {
             description "BGP output queue priority 9";
           }
           enum "priority-10" {
             description "BGP output queue priority 10";
           }
           enum "priority-11" {
             description "BGP output queue priority 11";
           }
           enum "priority-12" {
             description "BGP output queue priority 12";
           }
           enum "priority-13" {
             description "BGP output queue priority 13";
           }
           enum "priority-14" {
             description "BGP output queue priority 14";
           }
           enum "priority-15" {
             description "BGP output queue priority 15";
           }
           enum "priority-16" {
             description "BGP output queue priority 16";
           }
           enum "expedited" {
             description "BGP output queue expedited";
           }
         }
       }
       leaf display-client-data {
         description "Show client details";
         type empty;
       }
     }
     output {
       container route-information {
         leaf as-number {
           type int32;
         }
         leaf router-id {
           type ipaddr;
         }
         leaf maximum-ecmp {
           type int32;
         }
         leaf note-network-services-mode {
           type string;
         }
         container route-table {
           leaf table-name {
             type string;
             description "Unicast routing table";
           }
           leaf destination-count {
             type int32;
             description "Number of destinations in this rib";
           }
           leaf total-route-count {
             type int32;
           }
           leaf active-route-count {
             type int32;
             description "Active routes";
           }
           leaf holddown-route-count {
             type int32;
           }
           leaf hidden-route-count {
             type int32;
           }
           leaf restart-state {
             type string;
           }
           leaf prefix-max {
             type int32;
           }
           leaf prefix-threshold {
             type int32;
           }
           leaf prefix-label {
             type string;
           }
           leaf route-max {
             type int32;
           }
           leaf route-threshold {
             type int32;
           }
           leaf route-limit-label {
             type string;
           }
           container protocols {
             leaf protocol-name {
               type string;
             }
             leaf protocol-route-count {
               type int32;
               description "Total protocol routes";
             }
           }
           container rt {
             container terse {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container terse-mpls-fwd {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief-mpls-fwd {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-brief {
               leaf rt-destination {
                 type string;
               }
               leaf rt-prefix-length {
                 type int32;
               }
               container rt-entry {
                 leaf active-tag {
                   type string;
                   description "Visual indication of active state of this route entry";
                 }
                 leaf med {
                   type int32;
                   description "Multiple exit discriminator";
                 }
                 leaf local-preference {
                   type int32;
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container detail {
               leaf rt-destination {
                 type string;
               }
               leaf rt-prefix-length {
                 type int32;
               }
               leaf rt-entry-count {
                 type int32;
                 description "Number of route entries in this route";
               }
               leaf rt-announced-count {
                 type int32;
                 description "Number of announced route entries";
               }
               leaf rt-state {
                 type string;
                 description "State of this route";
               }
               leaf tsi {
                 type string;
                 description "Task-specific information";
               }
               container rt-entry {
                 leaf nh-type {
                   type string;
                   description "Special next hop: Reject, Blackhole, Receive, Multicast, Local, or Unused";
                 }
                 leaf nh-index {
                   type uint32;
                   description "Next-hop index";
                 }
                 leaf nh-address {
                   type int32;
                   description "Address of next hop";
                 }
                 leaf nh-reference-count {
                   type int32;
                   description "Number of references to this next hop";
                 }
                 leaf ext-int-intf-index {
                   type int32;
                   description "Interface index of equal-external-internal multipath";
                 }
                 leaf nh-flood-overflow {
                   type empty;
                   description "Flood nexthop exceeds maximum branches";
                 }
                 leaf client-data {
                   type string;
                   description "Route server client details";
                 }
                 leaf route-distinguisher {
                   type string;
                 }
                 leaf validation-state {
                   type string;
                 }
                 leaf pmsi {
                   type string;
                   description "P-multicast service interface";
                 }
                 leaf connector {
                   type string;
                 }
                 leaf color {
                   type int32;
                 }
                 leaf color2 {
                   type int32;
                 }
                 leaf rt-isis-level {
                   type int32;
                 }
                 leaf rt-isis-downbit {
                   type int32;
                 }
                 leaf rt-entry-state {
                   type string;
                   description "State of this route entry";
                 }
                 leaf rt-entry-pim-state {
                   type string;
                   description "PIM state of this route entry";
                 }
                 leaf inactive-reason {
                   type string;
                   description "HFRR profile Inactive reason (if any)";
                 }
                 leaf local-as {
                   type int32;
                   description "Local AS number";
                 }
                 leaf peer-as {
                   type int32;
                   description "Peer AS number";
                 }
                 leaf learned-from {
                   type ipaddr;
                   description "Peer address from which this route was learned";
                 }
                 leaf age {
                   type string;
                 }
                 leaf metric {
                   type int32;
                 }
                 leaf metric2 {
                   type int32;
                 }
                 leaf med-plus-igp {
                   type int32;
                 }
                 leaf rt-tag {
                   type int32;
                 }
                 leaf rt-tag2 {
                   type int32;
                 }
                 leaf rt-aigp {
                   type uint64;
                 }
                 leaf rt-resolving-aigp {
                   type uint64;
                 }
                 leaf rt-orr {
                   type uint32;
                 }
                 leaf rt-ospf-area {
                   type string;
                 }
                 leaf task-name {
                   type string;
                   description "Name of this task";
                 }
                 leaf announce-bits {
                   type int32;
                 }
                 leaf announce-tasks {
                   type string;
                 }
                 leaf as-path {
                   type string;
                 }
                 leaf bgp-rt-flag {
                   type string;
                   description "BGP route flag";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf remote-site {
                   type int32;
                   description "Remote site id";
                 }
                 leaf l2vpn-mesh-group {
                   type string;
                 }
                 leaf vc-label {
                   type int32;
                   description "VC label";
                 }
                 leaf context-id {
                   type ipaddr;
                   description "Context Identifier";
                 }
                 leaf route-control-word {
                   type string;
                   description "Control Word";
                 }
                 leaf mtu {
                   type int32;
                   description "MTU along an interface";
                 }
                 leaf cell-bundle-size {
                   type int32;
                   description "Cell bundle size";
                 }
                 leaf vlan-id {
                   type int32;
                 }
                 leaf flow-label-transmit {
                   type int32;
                 }
                 leaf flow-label-receive {
                   type int32;
                 }
                 leaf tdm-payload-size {
                   type int32;
                 }
                 leaf tdm-bitrate {
                   type int32;
                 }
                 leaf pw-status-code {
                   type int32;
                 }
                 leaf cac-bandwidth-failure {
                   type empty;
                   description "Call admission control failure due to insufficient bandwidth";
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf local-preference {
                   type int32;
                 }
                 leaf peer-id {
                   type ipaddr;
                 }
                 leaf path-id {
                   type string;
                 }
                 leaf gateway {
                   type string;
                   description "Sourcing gateway";
                 }
                 leaf rtrib-primary {
                   type string;
                   description "Primary routing table";
                 }
                 leaf rtrib-secondary {
                   type string;
                   description "Secondary routing table";
                 }
                 leaf indirect-nh-count {
                   type int32;
                   description "Number of indirect next hops";
                 }
                 leaf composite-nh-count {
                   type int32;
                   description "Number of composite next hops";
                 }
                 leaf helper-nhid {
                   type uint32;
                   description "Helper nexthop index";
                 }
                 leaf helper-refcount {
                   type int32;
                   description "Reference count of those needing helper route";
                 }
                 leaf backup-pe-group-name {
                   type string;
                   description "Name of the backup PE group";
                 }
                 leaf designated-forwarder {
                   type string;
                   description "Indicates if we are the designated forwarder for this route";
                 }
                 leaf rt-entry-opaque-data {
                   type string;
                   description "Opaque data associated with the route entry";
                 }
                 leaf rt-stats-id-grp-single-line {
                   type string;
                   description "Stats-id-group associated with the route entry";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf evpn-isid {
                   type int32;
                   description "ISID";
                 }
                 leaf rt-evpn-esi {
                   type string;
                   description "ESI";
                 }
                 leaf rt-evpn-bmac {
                   type string;
                   description "BMAC";
                 }
                 leaf active-tag {
                   type string;
                   description "Visual indication of active state of this route entry";
                 }
                 leaf protocol-name {
                   type string;
                 }
                 leaf preference {
                   type int32;
                   description "Preference for the route";
                 }
                 leaf preference2 {
                   type int32;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf snpa-count {
                     type int32;
                     description "Number of SNPAs in this route";
                   }
                   leaf snpa-length {
                     type int32;
                     description "Total length of the SNPAs, in bytes";
                   }
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                   container multicast-member-map-data {
                     description "Multicast member map";
                     leaf multicast-root-hash {
                       type int32;
                     }
                     leaf multicast-core-hash {
                       type int32;
                     }
                     leaf multicast-edge-hash {
                       type int32;
                     }
                     leaf multicast-member-map {
                       type string;
                     }
                   }
                   container layer3-multicast-data {
                     description "Layer3 multicast core key";
                     leaf layer3-multicast-corekey {
                       type int32;
                     }
                   }
                   container multicast-vsg-corekey-data {
                     description "Vsg multicast core key";
                     leaf multicast-vsg-corekey-key {
                       type int32;
                     }
                     leaf multicast-vsg-corekey-len {
                       type int32;
                     }
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container rtd-flow-dep {
                   leaf flow-dep-state {
                     type string;
                   }
                   leaf flow-origin {
                     type ipaddr;
                     description "Originator of the flow information";
                   }
                   leaf flow-next-as {
                     type uint32;
                     description "Neighbor AS of the flow information";
                   }
                   container flow-ucast-rt {
                     description "Unicast route used for resolution";
                   }
                 }
                 container communities {
                   leaf community {
                     type string;
                     description "Basic community";
                   }
                   leaf extended-community {
                     type string;
                     description "Extended community";
                   }
                 }
                 container attrset {
                 }
                 container route-flap-damping {
                   leaf last-merit {
                     type int32;
                     description "Last merit value";
                   }
                   leaf merit {
                     type int32;
                     description "Current merit value";
                   }
                   leaf damping-parameters {
                     type string;
                   }
                   leaf default-damping-parameters {
                     type empty;
                     description "Default damping parameters used";
                   }
                   leaf last-update {
                     type string;
                   }
                   leaf first-update {
                     type string;
                   }
                   leaf route-flap-count {
                     type int32;
                     description "Number of times this route has flapped";
                   }
                   leaf suppressed {
                     type empty;
                     description "This route is suppressed";
                   }
                   leaf reuse-time {
                     type string;
                     description "Time until this route is reusable";
                   }
                   leaf reuse-preference {
                     type int32;
                     description "Preference to use when this route is reused";
                   }
                   leaf expire-time {
                     type string;
                     description "Time when this damping entry expires";
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                   leaf aggregate-flags {
                     type string;
                     description "Flags on this aggregate route entry";
                   }
                   leaf aggregate-depth {
                     type int32;
                     description "Depth of this aggregate";
                   }
                   leaf aggregate-active {
                     type empty;
                     description "Present if this aggregate is active";
                   }
                   leaf contributing-route-count {
                     type int32;
                     description "Number of contributing routes in this aggregate";
                   }
                   container aggregate-as-path {
                     leaf as-path {
                       type string;
                     }
                     leaf reference-count {
                       type int32;
                     }
                   }
                   container aggregated-route {
                     leaf destination-prefix {
                       type string;
                       description "Destination prefix and mask";
                     }
                     leaf protocol-name {
                       type string;
                     }
                   }
                 }
                 container nhh {
                   leaf nh-type {
                     type string;
                     description "Special next hop: Reject, Blackhole, Receive, Multicast, Local, or Unused";
                   }
                   leaf nh-index {
                     type uint32;
                     description "Next-hop index";
                   }
                   leaf nh-address {
                     type int32;
                     description "Address of next hop";
                   }
                   leaf nh-reference-count {
                     type int32;
                     description "Number of references to this next hop";
                   }
                   leaf ext-int-intf-index {
                     type int32;
                     description "Interface index of equal-external-internal multipath";
                   }
                   leaf nh-flood-overflow {
                     type empty;
                     description "Flood nexthop exceeds maximum branches";
                   }
                 }
                 container nh {
                   description "Next-hop gateway information";
                   leaf nh-string {
                     type string;
                   }
                   leaf elnh-address {
                     type int32;
                     description "Address of Element Next-hop";
                   }
                   leaf to {
                     type string;
                     description "Neighbor address to which to send (next-hop address)";
                   }
                   leaf via {
                     type string;
                     description "Reachable via a local interface";
                   }
                   leaf localized-table {
                     type string;
                     description "Name of localized table";
                   }
                   leaf weight {
                     type int32;
                     description "Next-hop weight";
                   }
                   leaf balance {
                     type int32;
                     description "Next-hop balance";
                   }
                   leaf uflags {
                     type int32;
                     description "Next-hop uflags";
                   }
                   leaf filter {
                     type string;
                     description "Next-hop firewall filter";
                   }
                   leaf selected-next-hop {
                     type empty;
                     description "Present if this next hop is selected";
                   }
                   leaf session {
                     type int32;
                     description "Session ID Associated with this NH";
                   }
                   leaf statistics-id-group-terse {
                     type string;
                     description "Statistics ID Group Associated with this NH";
                   }
                   leaf ext-int-type {
                     type string;
                     description "Next-hop type of equal-external-internal multipath";
                   }
                   leaf fc {
                     type int32;
                     description "Forwarding-class";
                   }
                   leaf lsp-name {
                     type string;
                     description "Tunneled into an RSVP LSP";
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf label-element {
                     type string;
                     description "Pointer to the tag label element";
                   }
                   leaf label-element-parent {
                     type string;
                     description "Pointer to the tag label element parent";
                   }
                   leaf label-element-refcount {
                     type string;
                     description "Number of references to the tag label element";
                   }
                   leaf label-element-childcount {
                     type string;
                     description "Number of child references to the tag label element";
                   }
                   leaf label-element-lspid {
                     type string;
                     description "LSP ID of the tag label element";
                   }
                   leaf nh-table-receive {
                     type string;
                     description "Destination is a local address";
                   }
                   leaf nh-table {
                     type string;
                     description "Indirect pointing to another table";
                   }
                   leaf nh-localized-ifl {
                     type string;
                     description "Indirect pointing to a localized ifl";
                   }
                   leaf nh-local-interface {
                     type string;
                     description "Destination is a local interface";
                   }
                   leaf nh-service {
                     type string;
                     description "Next-hop service";
                   }
                   leaf nh-service-pkt-dist {
                     type string;
                     description "Multi services packet distribution type";
                   }
                   leaf nh-service-app-data {
                     type string;
                     description "Multi services application specific data";
                   }
                   leaf nh-private-comp {
                     type string;
                     description "Private Composite Next-hop";
                   }
                   leaf nh-index {
                     type uint32;
                     description "Next-hop index";
                   }
                   leaf nh-address {
                     type int32;
                     description "Address of next hop";
                   }
                 }
                 container protocol-nh {
                   description "Protocol next hop";
                   leaf to {
                     type string;
                     description "Neighbor address to which to send (next-hop address)";
                   }
                   leaf metric {
                     type int32;
                   }
                   leaf aigp {
                     type string;
                     description "AIGP";
                   }
                   leaf balance {
                     type int32;
                     description "Next-hop balance";
                   }
                   leaf flags {
                     type string;
                     description "Enabled trace flags";
                   }
                   leaf res-path-inode-flags {
                     type string;
                   }
                   leaf res-path-flags {
                     type string;
                   }
                   leaf res-path-fnh-link {
                     type string;
                   }
                   leaf res-path-inh-link {
                     type string;
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf composite-nh {
                     type string;
                   }
                   leaf vpnlabel-nh {
                     type string;
                   }
                   leaf indirect-nh {
                     type string;
                   }
                   leaf ext-int-type {
                     type string;
                     description "Next-hop type of equal-external-internal multipath";
                   }
                   leaf forwarding-nh-count {
                     type int32;
                     description "Number of indirect path forwarding next hops";
                   }
                   leaf nh-type {
                     type string;
                     description "Special next hop: Reject, Blackhole, Receive, Multicast, Local, or Unused";
                   }
                   container eth-header-rewrite {
                     description "Ethernet header rewrite information";
                     leaf eth-header-rewrite-smac {
                       type string;
                       description "Source MAC address";
                     }
                     leaf eth-header-rewrite-dmac {
                       type string;
                       description "Destination MAC address";
                     }
                     leaf eth-header-rewrite-tpid {
                       type int32;
                       description "Ethernet header TPID";
                     }
                     leaf eth-header-rewrite-tci {
                       type int32;
                       description "Ethernet header TCI";
                     }
                     leaf eth-header-rewrite-vlan-id {
                       type int32;
                       description "Ethernet header VLAN ID";
                     }
                     leaf eth-header-rewrite-ethertype {
                       type int32;
                       description "Ethernet header ethertype";
                     }
                   }
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-detail {
               leaf rt-destination {
                 type string;
               }
               leaf rt-prefix-length {
                 type int32;
               }
               leaf rt-entry-count {
                 type int32;
                 description "Number of route entries in this route";
               }
               leaf rt-announced-count {
                 type int32;
                 description "Number of announced route entries";
               }
               container rt-entry {
                 leaf bgp-group-name {
                   type string;
                 }
                 leaf bgp-rt-flag {
                   type string;
                   description "BGP route flag";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf l2vpn-mesh-group {
                   type string;
                 }
                 leaf route-distinguisher {
                   type string;
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf bgp-no-label-reason {
                   type string;
                 }
                 leaf bgp-metric-flags {
                   type string;
                   description "BGP metrics flags";
                 }
                 leaf med {
                   type int32;
                   description "Multiple exit discriminator";
                 }
                 leaf local-preference {
                   type int32;
                 }
                 leaf bgp-output-queue-class {
                   type string;
                   description "BGP output queue class";
                 }
                 leaf as-path {
                   type string;
                 }
                 leaf pmsi {
                   type string;
                   description "P-multicast service interface";
                 }
                 leaf cluster-id {
                   type string;
                 }
                 leaf originator {
                   type string;
                 }
                 leaf connector {
                   type string;
                 }
                 leaf path-id {
                   type string;
                 }
                 leaf bgp-aigp {
                   type string;
                   description "Accumulated IGP Metric";
                 }
                 leaf bgp-elc {
                   type empty;
                   description "Entropy label capable";
                 }
                 leaf bgp-elc-nh-valid {
                   type string;
                   description "Whether next hop field matches route next hop";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf active-tag {
                   type string;
                   description "Visual indication of active state of this route entry";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                   leaf attrset-as {
                     type int32;
                     description "Originator AS";
                   }
                   leaf med {
                     type int32;
                     description "Multiple exit discriminator";
                   }
                   leaf local-preference {
                     type int32;
                   }
                   leaf as-path {
                     type string;
                   }
                   leaf pmsi {
                     type string;
                     description "P-multicast service interface";
                   }
                   leaf cluster-id {
                     type string;
                   }
                   leaf originator {
                     type string;
                   }
                   leaf connector {
                     type string;
                   }
                   container communities {
                     leaf community {
                       type string;
                       description "Basic community";
                     }
                     leaf extended-community {
                       type string;
                       description "Extended community";
                     }
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                   leaf to {
                     type string;
                     description "Neighbor address to which to send (next-hop address)";
                   }
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
               container communities {
                 leaf community {
                   type string;
                   description "Basic community";
                 }
                 leaf extended-community {
                   type string;
                   description "Extended community";
                 }
               }
             }
           }
         }
         container rt-martians {
           container route-filter {
             description "Entries in martian table";
             leaf address {
               type ipaddr;
             }
             leaf flags {
               type string;
               description "Enabled trace flags";
             }
             leaf extended-information {
               type string;
             }
             leaf match-count {
               type uint64;
             }
           }
         }
         container rt-ribgroup {
           leaf rt-ribgroup-name {
             type string;
             description "Rib-group name";
           }
           leaf rt-ribgroup-address {
             type string;
             description "Rib-group address";
           }
           leaf rt-ribgroup-address-family {
             type string;
             description "Rib-group address family";
           }
           leaf rt-ribgroup-flags {
             type string;
             description "Rib-group flags";
           }
           leaf rt-ribgroup-refcount {
             type uint32;
             description "Rib-group refcount";
           }
           leaf rt-ribgroup-export-name {
             type string;
             description "Export RIB name";
           }
           leaf rt-ribgroup-import-name {
             type string;
             description "Import RIB name";
           }
           leaf rt-ribgroup-import-policy-name {
             type string;
             description "Import policy name";
           }
           leaf rt-ribgroup-import-secondary-name {
             type string;
             description "Import secondary RIB name";
           }
           leaf rt-ribgroup-union-head-name {
             type string;
             description "Rib-group union head name";
           }
           leaf rt-ribgroup-union-child-name {
             type string;
             description "Rib-group union child name";
           }
         }
         container rt-test-policy-prefix {
           leaf rt-policy-name {
             type string;
           }
           leaf rt-destination {
             type string;
           }
           leaf rt-prefix-length {
             type int32;
           }
           container rt-test-policy-term {
             leaf rt-policy-term-name {
               type string;
             }
             leaf rt-policy-term-result {
               type string;
             }
             leaf rt-policy-term-action {
               type string;
             }
           }
         }
         container rt-test-policy {
           leaf rt-policy-name {
             type string;
           }
           leaf rt-route-accepted {
             type int32;
           }
           leaf rt-route-rejected {
             type int32;
           }
         }
       }
     }
   }
   rpc get-forwarding-table-information {
     description "Show entries in all forwarding tables";
     input {
       leaf level {
         type enumeration {
           enum "detail" {
             description "Display all routes";
           }
           enum "extensive" {
             description "Display extensive information about routes";
           }
         }
       }
       leaf multicast {
         description "Display multicast routes";
         type empty;
       }
       leaf family {
         description "Name of family";
         type enumeration {
           enum "inet" {
             description "IP version 4 (IPv4)";
           }
           enum "inet6" {
             description "IP version 6 (IPv6)";
           }
           enum "unix" {
             description "UNIX";
           }
           enum "iso" {
             description "International Standards Organization protocol";
           }
           enum "tnp" {
             description "Trivial Network Protocol";
           }
           enum "mpls" {
             description "Multiprotocol Label Switching";
           }
           enum "vpls" {
             description "Virtual private LAN service";
           }
           enum "bridge" {
             description "Bridge (Layer 2 switching)";
           }
           enum "evpn" {
             description "Ethernet Virtual Private LAN services";
           }
           enum "vlan-classification" {
             description "VLAN classification table";
           }
           enum "ethernet-switching" {
             description "Switch forwarding table";
           }
           enum "fibre-channel" {
             description "Fibre channel forwarding table";
           }
           enum "fmembers" {
             description "Fibre channel membership table";
           }
           enum "fabric-multicast" {
             description "Fabric multicast routing table";
           }
           enum "fabric-replication" {
             description "Fabric replication routing table";
           }
           enum "mcsnoop-inet" {
             description "Multicast Snooping INET";
           }
           enum "mcsnoop-inet6" {
             description "Multicast Snooping INET6";
           }
           enum "satellite-vpls" {
             description "Satellite VPLS";
           }
           enum "satellite-inet" {
             description "Multicast Satellite INET";
           }
           enum "satellite-inet6" {
             description "Multicast Satellite INET6";
           }
         }
       }
       leaf vpn {
         description "Name of VPN instance";
         type string;
       }
       leaf table {
         description "Name of routing table";
         type string;
       }
       leaf interface-name {
         description "Interface name";
         type string;
       }
       leaf vlan {
         description "VLAN name";
         type string;
       }
       leaf bridge-domain {
         description "Name of bridging domain";
         type string;
       }
       leaf summary {
         description "Display count of routes instead of details";
         type empty;
       }
       leaf matching {
         description "IP prefix and length for entries to match";
         type string;
       }
       leaf destination {
         description "Destination prefix";
         type string;
       }
       leaf learning-vlan-id {
         description "Learning VLAN";
         type string;
       }
       leaf label {
         description "Label for entries to match";
         type uint32;
       }
       leaf ccc {
         description "Circuit cross-connect interface name for entries to match";
         type interface-name;
       }
       leaf all {
         description "Display all routing forwarding-tables";
         type empty;
       }
     }
     output {
       container forwarding-table-information {
         container route-table {
           description "Denotes a routing table";
           leaf logical-system-name {
             type string;
             description "Name of this logical system";
           }
           leaf table-name {
             type string;
             description "Name of this routing table";
           }
           leaf route-table-deleted {
             type empty;
             description "Whether this routing table has been deleted";
           }
           leaf pbbn-table-name {
             type string;
             description "Name of corresponding PBBN routing table";
           }
           leaf pbbn-route-table-deleted {
             type empty;
             description "Whether corresponding PBBN routing table has been deleted";
           }
           leaf bd-name {
             type string;
             description "Name of this bridging domain";
           }
           leaf bridge-table-deleted {
             type empty;
             description "Whether this bridge table has been deleted";
           }
           leaf address-family {
             type string;
             description "Address family for this routing table";
           }
           leaf address-family-number {
             type string;
             description "If the address family name is unknown, print the number";
           }
           leaf enabled-protocols {
             type string;
             description "Protocols enabled for this routing table";
           }
           container rt-entry {
             description "Routing table entry for a destination";
             container brief {
               description "Routing table entry for a destination";
               leaf rt-destination {
                 type string;
                 description "Destination address";
               }
               leaf destination-type {
                 type string;
                 description "Destination type for this entry";
               }
               leaf route-reference-count {
                 type int32;
                 description "Reference count for this destination entry";
               }
               container nh {
                 description "Next hop for this routing table entry";
                 leaf to {
                   type string;
                   description "Next-hop address for this entry";
                 }
                 leaf nh-type {
                   type string;
                   description "Next-hop type";
                 }
                 leaf nh-index {
                   type int32;
                   description "Index in next-hop table";
                 }
                 leaf nh-reference-count {
                   type int32;
                   description "Next-hop reference count";
                 }
                 leaf via {
                   type string;
                   description "Network interface name";
                 }
                 leaf nh-composite-num-nhs {
                   type int32;
                   description "Number of next hops in a composite next hop";
                 }
                 leaf nh-composite-nh-index {
                   type int32;
                   description "Index of next hops in a composite next hop";
                 }
                 leaf nh-composite-function {
                   type string;
                   description "Composition function for next hops in a composite next hop";
                 }
                 leaf nh-composite-num-derived-nhs {
                   type int32;
                   description "Number of derived next hops for a composite next hop";
                 }
                 leaf nh-composite-derived-nh-index {
                   type int32;
                   description "Index of derived next hops in a composite next hop";
                 }
               }
             }
             container extensive-new {
               description "Routing table entry for a destination";
               leaf rt-destination {
                 type string;
                 description "Destination address";
               }
               leaf learn-vlan {
                 type uint32;
                 description "VLAN ID in the routing instance in which the MAC address was learned";
               }
               leaf destination-type {
                 type string;
                 description "Destination type for this entry";
               }
               leaf route-reference-count {
                 type int32;
                 description "Reference count for this destination entry";
               }
               leaf route-interface-index {
                 type int32;
                 description "Interface referenced by this route";
               }
               leaf multicast-rpf-nh-index {
                 type int32;
                 description "Multicast rpf nh index for this route";
               }
               leaf route-p2mp-index {
                 type int32;
                 description "P2mp nexthop index";
               }
               leaf ifl-generation {
                 type uint32;
                 description "Creation time of the IFL when this MAC was learned";
               }
               leaf epoch {
                 type uint32;
                 description "Time when this MAC was learned";
               }
               leaf flood-token {
                 type uint32;
                 description "Layer2 flood token associated with this route entry";
               }
               leaf mac-sequence-number {
                 type uint32;
                 description "Sequence number assigned to this MAC";
               }
               leaf learn-mask {
                 type uint32;
                 description "Mask of PFEs where this MAC was learned";
               }
               leaf l2al-rtflags {
                 type string;
                 description "Route flags associated with MAC routes";
               }
               leaf route-flags {
                 type string;
                 description "Flags associated with this route entry";
               }
               leaf vlan-index {
                 type uint32;
                 description "VLAN index";
               }
               leaf vlan-flags {
                 type uint32;
                 description "VLAN flags";
               }
               leaf statistics-group-id {
                 type uint32;
                 description "Stats ID Group ID";
               }
               container nh {
                 description "Next hop for this routing table entry";
                 leaf to {
                   type string;
                   description "Next-hop address for this entry";
                 }
                 leaf nh-type {
                   type string;
                   description "Next-hop type";
                 }
                 leaf nh-index {
                   type int32;
                   description "Index in next-hop table";
                 }
                 leaf nh-reference-count {
                   type int32;
                   description "Next-hop reference count";
                 }
                 leaf nh-lb-label {
                   type string;
                   description "Next-hop tag load balancing label";
                 }
                 leaf nh-cfi-index {
                   type int32;
                   description "Next-hop core-facing-interface index";
                 }
                 leaf nh-key-flags {
                   type int32;
                   description "Next-hop key flags";
                 }
                 leaf subnh-index {
                   type int32;
                   description "Index of subnh in a nexthop";
                 }
                 leaf via {
                   type string;
                   description "Network interface name";
                 }
                 leaf nh-weight {
                   type int32;
                   description "Next-hop weight";
                 }
                 leaf nh-balance {
                   type int32;
                   description "Next-hop balance";
                 }
                 leaf nh-uflags {
                   type int32;
                   description "Next-hop uflags";
                 }
                 leaf nh-le-beb-mac {
                   type mac-addr;
                   description "The remote BEB MAC learned on bridge-domain of type PBN";
                 }
                 leaf nh-composite-num-nhs {
                   type int32;
                   description "Number of next hops in a composite next hop";
                 }
                 leaf nh-composite-nh-index {
                   type int32;
                   description "Index of next hops in a composite next hop";
                 }
                 leaf nh-composite-function {
                   type string;
                   description "Composition function for next hops in a composite next hop";
                 }
                 leaf nh-composite-num-derived-nhs {
                   type int32;
                   description "Number of derived next hops for a composite next hop";
                 }
                 leaf nh-composite-derived-nh-index {
                   type int32;
                   description "Index of derived next hops in a composite next hop";
                 }
               }
               container rpf-information {
                 description "Reverse-path forwarding check for this route";
                 leaf via {
                   type string;
                   description "Network interface name";
                 }
               }
               container vpls-mac-source-address-statistics {
                 description "MAC source address statistics";
                 leaf packet-count {
                   type uint64;
                   description "Packet count";
                 }
                 leaf byte-count {
                   type uint64;
                   description "Byte count";
                 }
               }
               container vpls-mac-destination-address-statistics {
                 description "MAC destination address statistics";
                 leaf packet-count {
                   type uint64;
                   description "Packet count";
                 }
                 leaf byte-count {
                   type uint64;
                   description "Byte count";
                 }
               }
               container bridge-mac-source-address-statistics {
                 description "MAC source address statistics";
                 leaf packet-count {
                   type uint64;
                   description "Packet count";
                 }
                 leaf byte-count {
                   type uint64;
                   description "Byte count";
                 }
               }
               container bridge-mac-destination-address-statistics {
                 description "MAC destination address statistics";
                 leaf packet-count {
                   type uint64;
                   description "Packet count";
                 }
                 leaf byte-count {
                   type uint64;
                   description "Byte count";
                 }
               }
             }
             container extensive {
               description "Routing table entry for a destination";
               leaf rt-destination {
                 type string;
                 description "Destination address";
               }
               leaf destination-type {
                 type string;
                 description "Destination type for this entry";
               }
               leaf route-reference-count {
                 type int32;
                 description "Reference count for this destination entry";
               }
               leaf route-interface-index {
                 type int32;
                 description "Interface referenced by this route";
               }
               leaf multicast-rpf-nh-index {
                 type int32;
                 description "Multicast rpf nh index for this route";
               }
               leaf route-p2mp-index {
                 type int32;
                 description "P2mp nexthop index";
               }
               leaf route-flags {
                 type string;
                 description "Flags associated with this route entry";
               }
               leaf snmp-idx {
                 type uint32;
                 description "KRT: IFD SNMP index";
               }
               leaf statistics-group-id {
                 type uint32;
                 description "Stats ID Group ID";
               }
               container nh {
                 description "Next hop for this routing table entry";
                 leaf to {
                   type string;
                   description "Next-hop address for this entry";
                 }
                 leaf nh-type {
                   type string;
                   description "Next-hop type";
                 }
                 leaf nh-index {
                   type int32;
                   description "Index in next-hop table";
                 }
                 leaf nh-reference-count {
                   type int32;
                   description "Next-hop reference count";
                 }
                 leaf nh-lb-label {
                   type string;
                   description "Next-hop tag load balancing label";
                 }
                 leaf nh-cfi-index {
                   type int32;
                   description "Next-hop core-facing-interface index";
                 }
                 leaf nh-key-flags {
                   type int32;
                   description "Next-hop key flags";
                 }
                 leaf subnh-index {
                   type int32;
                   description "Index of subnh in a nexthop";
                 }
                 leaf via {
                   type string;
                   description "Network interface name";
                 }
                 leaf nh-weight {
                   type int32;
                   description "Next-hop weight";
                 }
                 leaf nh-balance {
                   type int32;
                   description "Next-hop balance";
                 }
                 leaf nh-uflags {
                   type int32;
                   description "Next-hop uflags";
                 }
                 leaf nh-le-beb-mac {
                   type mac-addr;
                   description "The remote BEB MAC learned on bridge-domain of type PBN";
                 }
                 leaf alt-fwdnh-index {
                   type int32;
                   description "Alternate forward Index in next-hop table";
                 }
                 leaf nh-l3-interface {
                   type string;
                   description "Next-hop L3 interface";
                 }
                 leaf nh-composite-num-nhs {
                   type int32;
                   description "Number of next hops in a composite next hop";
                 }
                 leaf nh-composite-nh-index {
                   type int32;
                   description "Index of next hops in a composite next hop";
                 }
                 leaf nh-composite-function {
                   type string;
                   description "Composition function for next hops in a composite next hop";
                 }
                 leaf nh-composite-num-derived-nhs {
                   type int32;
                   description "Number of derived next hops for a composite next hop";
                 }
                 leaf nh-composite-derived-nh-index {
                   type int32;
                   description "Index of derived next hops in a composite next hop";
                 }
                 container nh-l2-interface {
                 }
               }
               container rpf-information {
                 description "Reverse-path forwarding check for this route";
                 leaf via {
                   type string;
                   description "Network interface name";
                 }
               }
               container vpls-mac-source-address-statistics {
                 description "MAC source address statistics";
                 leaf packet-count {
                   type uint64;
                   description "Packet count";
                 }
                 leaf byte-count {
                   type uint64;
                   description "Byte count";
                 }
               }
               container vpls-mac-destination-address-statistics {
                 description "MAC destination address statistics";
                 leaf packet-count {
                   type uint64;
                   description "Packet count";
                 }
                 leaf byte-count {
                   type uint64;
                   description "Byte count";
                 }
               }
               container bridge-mac-source-address-statistics {
                 description "MAC source address statistics";
                 leaf packet-count {
                   type uint64;
                   description "Packet count";
                 }
                 leaf byte-count {
                   type uint64;
                   description "Byte count";
                 }
               }
               container bridge-mac-destination-address-statistics {
                 description "MAC destination address statistics";
                 leaf packet-count {
                   type uint64;
                   description "Packet count";
                 }
                 leaf byte-count {
                   type uint64;
                   description "Byte count";
                 }
               }
             }
           }
           container route-table-summary {
             description "Routing table summary";
             leaf route-table-type {
               type string;
               description "Type for this routing table";
             }
             leaf route-count {
               type int32;
               description "Number of routes in this routing table";
             }
           }
         }
       }
     }
   }
   rpc get-instance-information {
     description "Show routing instances information";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
       leaf verbosity_level {
         default "brief";
         type enumeration {
           enum "summary" {
             description "Display summary output";
           }
           enum "brief" {
             description "Display brief output (default)";
           }
           enum "detail" {
             description "Display detailed output";
           }
           enum "extensive" {
             description "Display extensive output";
           }
         }
       }
       leaf instance-name {
         description "Particular instance name";
         type string;
       }
     }
     output {
       container instance-information {
         container terse {
           description "Operational and configuration information for routing instances";
           container instance-core {
             leaf instance-name {
               type string;
             }
             leaf instance-type {
               type string;
             }
             container instance-rib {
               leaf irib-name {
                 type string;
               }
               leaf irib-active-count {
                 type int32;
               }
               leaf irib-holddown-count {
                 type int32;
               }
               leaf irib-hidden-count {
                 type int32;
               }
             }
             container instance-localize {
             }
           }
         }
         container detail {
           description "Operational and configuration information for routing instances";
           container instance-core {
             leaf instance-name {
               type string;
             }
             leaf instance-description {
               type string;
             }
             leaf router-id {
               type ipaddr;
             }
             leaf instance-type {
               type string;
             }
             leaf instance-state {
               type string;
             }
             leaf instance-restart-state {
               type string;
             }
             leaf instance-pathsel-timeout {
               type int32;
             }
             container instance-rib {
               leaf irib-name {
                 type string;
               }
               leaf irib-route-count {
                 type int32;
               }
               leaf irib-active-count {
                 type int32;
               }
               leaf irib-holddown-count {
                 type int32;
               }
               leaf irib-hidden-count {
                 type int32;
               }
               leaf irib-restart-state {
                 type string;
               }
             }
             container instance-interface {
               leaf interface-name {
                 type string;
                 description "Name of interface";
               }
             }
             container instance-localize {
               container instance-localize-scope {
                 leaf localize-scope {
                   type string;
                 }
               }
               container instance-localize-interface {
                 leaf interface-name {
                   type string;
                   description "Name of interface";
                 }
                 leaf address-family {
                   type string;
                 }
                 leaf nexthop-index {
                   type int32;
                 }
               }
             }
             container instance-vrf {
               leaf route-distinguisher {
                 type string;
               }
               leaf vrf-import {
                 type string;
               }
               leaf vrf-export {
                 type string;
               }
               leaf vrf-import-target {
                 type string;
               }
               leaf vrf-export-target {
                 type string;
               }
               leaf vrf-label-allocation {
                 type string;
               }
               leaf vrf-label-substitution {
                 type string;
               }
               leaf fast-reroute-priority {
                 type string;
               }
               leaf vrf-edge-protection-context-id {
                 type ipaddr;
               }
             }
             container instance-vpls-meshgroup {
               leaf meshgroup-name {
                 type string;
               }
               leaf route-distinguisher {
                 type string;
               }
               leaf meshgroup-vrf-import {
                 type string;
               }
               leaf meshgroup-vrf-export {
                 type string;
               }
               leaf meshgroup-vrf-import-target {
                 type string;
               }
               leaf meshgroup-vrf-export-target {
                 type string;
               }
             }
           }
         }
       }
     }
   }
   rpc get-operational-routing-instance-information {
     description "Show operational routing instances";
     output {
       container operational-routing-instance-information {
         leaf instance-name {
           type string;
         }
       }
     }
   }
   rpc get-localize-routing-instance-information {
     description "Show instances localization mapping";
   }
   rpc get-route-resolution-information {
     description "Show next-hop resolution database";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf prefix {
         description "IP prefix/length of destination";
         type string;
       }
       leaf table {
         description "Name of resolving table";
         type string;
       }
       leaf index {
         description "Index of resolution tree";
         type uint32;
       }
     }
     output {
       container route-resolution-information {
         container route-resolution-tree {
           leaf tree-index {
             type int32;
             description "Index of the resolution tree";
           }
           leaf nodes {
             type int32;
             description "Number of resolution nodes in the tree";
           }
           leaf tree-reference-count {
             type int32;
             description "Reference count on the tree";
           }
           leaf tree-policy {
             type string;
             description "Import policy on the tree";
           }
           container node {
             leaf node-prefix {
               type string;
             }
             leaf node-prefix-length {
               type int32;
             }
             leaf originating-rib {
               type string;
               description "Routing table from which this route was learned";
             }
             leaf metric {
               type int32;
             }
             leaf node-path-count {
               type int32;
               description "Number of paths for this node";
             }
             leaf forwarding-nh-count {
               type int32;
               description "Number of indirect path forwarding next hops";
             }
             leaf nh-subtype {
               type string;
               description "Specified nexthop subtype";
             }
             leaf indirect-nh-count {
               type int32;
               description "Number of indirect next hops";
             }
             leaf composite-nh-count {
               type int32;
               description "Number of composite next hops";
             }
             container protocol-nh {
               description "Protocol next hop";
               leaf to {
                 type string;
                 description "Neighbor address to which to send (next-hop address)";
               }
               leaf aigp {
                 type string;
                 description "AIGP";
               }
               leaf balance {
                 type int32;
                 description "Next-hop balance";
               }
               leaf flags {
                 type string;
                 description "Enabled trace flags";
               }
               leaf res-path-inode-flags {
                 type string;
               }
               leaf res-path-flags {
                 type string;
               }
               leaf res-path-fnh-link {
                 type string;
               }
               leaf res-path-inh-link {
                 type string;
               }
               leaf mpls-label {
                 type string;
                 description "Label of MPLS packet";
               }
               leaf label-ttl-action {
                 type string;
                 description "TTL action associated with labels";
               }
               leaf load-balance-label {
                 type string;
                 description "Load balance action associated with labels";
               }
               leaf composite-nh {
                 type string;
               }
               leaf vpnlabel-nh {
                 type string;
               }
               leaf indirect-nh {
                 type string;
               }
               leaf ext-int-type {
                 type string;
                 description "Next-hop type of equal-external-internal multipath";
               }
               leaf nh-type {
                 type string;
                 description "Special next hop: Reject, Blackhole, Receive, Multicast, Local, or Unused";
               }
               container nh {
                 description "Next-hop gateway information";
                 leaf nh-string {
                   type string;
                 }
                 leaf elnh-address {
                   type int32;
                   description "Address of Element Next-hop";
                 }
                 leaf via {
                   type string;
                   description "Reachable via a local interface";
                 }
                 leaf localized-table {
                   type string;
                   description "Name of localized table";
                 }
                 leaf weight {
                   type int32;
                   description "Next-hop weight";
                 }
                 leaf uflags {
                   type int32;
                   description "Next-hop uflags";
                 }
                 leaf filter {
                   type string;
                   description "Next-hop firewall filter";
                 }
                 leaf selected-next-hop {
                   type empty;
                   description "Present if this next hop is selected";
                 }
                 leaf session {
                   type int32;
                   description "Session ID Associated with this NH";
                 }
                 leaf statistics-id-group-terse {
                   type string;
                   description "Statistics ID Group Associated with this NH";
                 }
                 leaf fc {
                   type int32;
                   description "Forwarding-class";
                 }
                 leaf lsp-name {
                   type string;
                   description "Tunneled into an RSVP LSP";
                 }
                 leaf label-element {
                   type string;
                   description "Pointer to the tag label element";
                 }
                 leaf label-element-parent {
                   type string;
                   description "Pointer to the tag label element parent";
                 }
                 leaf label-element-refcount {
                   type string;
                   description "Number of references to the tag label element";
                 }
                 leaf label-element-childcount {
                   type string;
                   description "Number of child references to the tag label element";
                 }
                 leaf label-element-lspid {
                   type string;
                   description "LSP ID of the tag label element";
                 }
                 leaf nh-table-receive {
                   type string;
                   description "Destination is a local address";
                 }
                 leaf nh-table {
                   type string;
                   description "Indirect pointing to another table";
                 }
                 leaf nh-localized-ifl {
                   type string;
                   description "Indirect pointing to a localized ifl";
                 }
                 leaf nh-local-interface {
                   type string;
                   description "Destination is a local interface";
                 }
                 leaf nh-service {
                   type string;
                   description "Next-hop service";
                 }
                 leaf nh-service-pkt-dist {
                   type string;
                   description "Multi services packet distribution type";
                 }
                 leaf nh-service-app-data {
                   type string;
                   description "Multi services application specific data";
                 }
                 leaf nh-private-comp {
                   type string;
                   description "Private Composite Next-hop";
                 }
                 leaf nh-index {
                   type uint32;
                   description "Next-hop index";
                 }
                 leaf nh-address {
                   type int32;
                   description "Address of next hop";
                 }
               }
             }
           }
         }
       }
     }
   }
   rpc get-route-resolution-summary {
     description "Show summary of tree";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container route-resolution-information {
         container route-resolution-tree {
           leaf tree-index {
             type int32;
             description "Index of the resolution tree";
           }
           leaf nodes {
             type int32;
             description "Number of resolution nodes in the tree";
           }
           leaf tree-reference-count {
             type int32;
             description "Reference count on the tree";
           }
           leaf tree-policy {
             type string;
             description "Import policy on the tree";
           }
           container node {
             leaf node-prefix {
               type string;
             }
             leaf node-prefix-length {
               type int32;
             }
             leaf originating-rib {
               type string;
               description "Routing table from which this route was learned";
             }
             leaf metric {
               type int32;
             }
             leaf node-path-count {
               type int32;
               description "Number of paths for this node";
             }
             leaf forwarding-nh-count {
               type int32;
               description "Number of indirect path forwarding next hops";
             }
             leaf nh-subtype {
               type string;
               description "Specified nexthop subtype";
             }
             leaf indirect-nh-count {
               type int32;
               description "Number of indirect next hops";
             }
             leaf composite-nh-count {
               type int32;
               description "Number of composite next hops";
             }
             container protocol-nh {
               description "Protocol next hop";
               leaf to {
                 type string;
                 description "Neighbor address to which to send (next-hop address)";
               }
               leaf aigp {
                 type string;
                 description "AIGP";
               }
               leaf balance {
                 type int32;
                 description "Next-hop balance";
               }
               leaf flags {
                 type string;
                 description "Enabled trace flags";
               }
               leaf res-path-inode-flags {
                 type string;
               }
               leaf res-path-flags {
                 type string;
               }
               leaf res-path-fnh-link {
                 type string;
               }
               leaf res-path-inh-link {
                 type string;
               }
               leaf mpls-label {
                 type string;
                 description "Label of MPLS packet";
               }
               leaf label-ttl-action {
                 type string;
                 description "TTL action associated with labels";
               }
               leaf load-balance-label {
                 type string;
                 description "Load balance action associated with labels";
               }
               leaf composite-nh {
                 type string;
               }
               leaf vpnlabel-nh {
                 type string;
               }
               leaf indirect-nh {
                 type string;
               }
               leaf ext-int-type {
                 type string;
                 description "Next-hop type of equal-external-internal multipath";
               }
               leaf nh-type {
                 type string;
                 description "Special next hop: Reject, Blackhole, Receive, Multicast, Local, or Unused";
               }
               container nh {
                 description "Next-hop gateway information";
                 leaf nh-string {
                   type string;
                 }
                 leaf elnh-address {
                   type int32;
                   description "Address of Element Next-hop";
                 }
                 leaf via {
                   type string;
                   description "Reachable via a local interface";
                 }
                 leaf localized-table {
                   type string;
                   description "Name of localized table";
                 }
                 leaf weight {
                   type int32;
                   description "Next-hop weight";
                 }
                 leaf uflags {
                   type int32;
                   description "Next-hop uflags";
                 }
                 leaf filter {
                   type string;
                   description "Next-hop firewall filter";
                 }
                 leaf selected-next-hop {
                   type empty;
                   description "Present if this next hop is selected";
                 }
                 leaf session {
                   type int32;
                   description "Session ID Associated with this NH";
                 }
                 leaf statistics-id-group-terse {
                   type string;
                   description "Statistics ID Group Associated with this NH";
                 }
                 leaf fc {
                   type int32;
                   description "Forwarding-class";
                 }
                 leaf lsp-name {
                   type string;
                   description "Tunneled into an RSVP LSP";
                 }
                 leaf label-element {
                   type string;
                   description "Pointer to the tag label element";
                 }
                 leaf label-element-parent {
                   type string;
                   description "Pointer to the tag label element parent";
                 }
                 leaf label-element-refcount {
                   type string;
                   description "Number of references to the tag label element";
                 }
                 leaf label-element-childcount {
                   type string;
                   description "Number of child references to the tag label element";
                 }
                 leaf label-element-lspid {
                   type string;
                   description "LSP ID of the tag label element";
                 }
                 leaf nh-table-receive {
                   type string;
                   description "Destination is a local address";
                 }
                 leaf nh-table {
                   type string;
                   description "Indirect pointing to another table";
                 }
                 leaf nh-localized-ifl {
                   type string;
                   description "Indirect pointing to a localized ifl";
                 }
                 leaf nh-local-interface {
                   type string;
                   description "Destination is a local interface";
                 }
                 leaf nh-service {
                   type string;
                   description "Next-hop service";
                 }
                 leaf nh-service-pkt-dist {
                   type string;
                   description "Multi services packet distribution type";
                 }
                 leaf nh-service-app-data {
                   type string;
                   description "Multi services application specific data";
                 }
                 leaf nh-private-comp {
                   type string;
                   description "Private Composite Next-hop";
                 }
                 leaf nh-index {
                   type uint32;
                   description "Next-hop index";
                 }
                 leaf nh-address {
                   type int32;
                   description "Address of next hop";
                 }
               }
             }
           }
         }
       }
     }
   }
   rpc get-route-summary-information {
     description "Show routing table statistics";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
       leaf table {
         description "Name of routing table";
         type string;
       }
     }
     output {
       container route-summary-information {
         leaf as-number {
           type int32;
         }
         leaf router-id {
           type ipaddr;
         }
         leaf maximum-ecmp {
           type int32;
         }
         leaf note-network-services-mode {
           type string;
         }
         container route-table {
           leaf table-name {
             type string;
             description "Unicast routing table";
           }
           leaf destination-count {
             type int32;
             description "Number of destinations in this rib";
           }
           leaf total-route-count {
             type int32;
           }
           leaf active-route-count {
             type int32;
             description "Active routes";
           }
           leaf holddown-route-count {
             type int32;
           }
           leaf hidden-route-count {
             type int32;
           }
           leaf restart-state {
             type string;
           }
           leaf prefix-max {
             type int32;
           }
           leaf prefix-threshold {
             type int32;
           }
           leaf prefix-label {
             type string;
           }
           leaf route-max {
             type int32;
           }
           leaf route-threshold {
             type int32;
           }
           leaf route-limit-label {
             type string;
           }
           container protocols {
             leaf protocol-name {
               type string;
             }
             leaf protocol-route-count {
               type int32;
               description "Total protocol routes";
             }
           }
           container rt {
             container terse {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container terse-mpls-fwd {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief-mpls-fwd {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-brief {
               leaf rt-destination {
                 type string;
               }
               leaf rt-prefix-length {
                 type int32;
               }
               container rt-entry {
                 leaf active-tag {
                   type string;
                   description "Visual indication of active state of this route entry";
                 }
                 leaf med {
                   type int32;
                   description "Multiple exit discriminator";
                 }
                 leaf local-preference {
                   type int32;
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container detail {
               leaf rt-destination {
                 type string;
               }
               leaf rt-prefix-length {
                 type int32;
               }
               leaf rt-entry-count {
                 type int32;
                 description "Number of route entries in this route";
               }
               leaf rt-announced-count {
                 type int32;
                 description "Number of announced route entries";
               }
               leaf rt-state {
                 type string;
                 description "State of this route";
               }
               leaf tsi {
                 type string;
                 description "Task-specific information";
               }
               container rt-entry {
                 leaf nh-type {
                   type string;
                   description "Special next hop: Reject, Blackhole, Receive, Multicast, Local, or Unused";
                 }
                 leaf nh-index {
                   type uint32;
                   description "Next-hop index";
                 }
                 leaf nh-address {
                   type int32;
                   description "Address of next hop";
                 }
                 leaf nh-reference-count {
                   type int32;
                   description "Number of references to this next hop";
                 }
                 leaf ext-int-intf-index {
                   type int32;
                   description "Interface index of equal-external-internal multipath";
                 }
                 leaf nh-flood-overflow {
                   type empty;
                   description "Flood nexthop exceeds maximum branches";
                 }
                 leaf client-data {
                   type string;
                   description "Route server client details";
                 }
                 leaf route-distinguisher {
                   type string;
                 }
                 leaf validation-state {
                   type string;
                 }
                 leaf pmsi {
                   type string;
                   description "P-multicast service interface";
                 }
                 leaf connector {
                   type string;
                 }
                 leaf color {
                   type int32;
                 }
                 leaf color2 {
                   type int32;
                 }
                 leaf rt-isis-level {
                   type int32;
                 }
                 leaf rt-isis-downbit {
                   type int32;
                 }
                 leaf rt-entry-state {
                   type string;
                   description "State of this route entry";
                 }
                 leaf rt-entry-pim-state {
                   type string;
                   description "PIM state of this route entry";
                 }
                 leaf inactive-reason {
                   type string;
                   description "HFRR profile Inactive reason (if any)";
                 }
                 leaf local-as {
                   type int32;
                   description "Local AS number";
                 }
                 leaf peer-as {
                   type int32;
                   description "Peer AS number";
                 }
                 leaf learned-from {
                   type ipaddr;
                   description "Peer address from which this route was learned";
                 }
                 leaf age {
                   type string;
                 }
                 leaf metric {
                   type int32;
                 }
                 leaf metric2 {
                   type int32;
                 }
                 leaf med-plus-igp {
                   type int32;
                 }
                 leaf rt-tag {
                   type int32;
                 }
                 leaf rt-tag2 {
                   type int32;
                 }
                 leaf rt-aigp {
                   type uint64;
                 }
                 leaf rt-resolving-aigp {
                   type uint64;
                 }
                 leaf rt-orr {
                   type uint32;
                 }
                 leaf rt-ospf-area {
                   type string;
                 }
                 leaf task-name {
                   type string;
                   description "Name of this task";
                 }
                 leaf announce-bits {
                   type int32;
                 }
                 leaf announce-tasks {
                   type string;
                 }
                 leaf as-path {
                   type string;
                 }
                 leaf bgp-rt-flag {
                   type string;
                   description "BGP route flag";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf remote-site {
                   type int32;
                   description "Remote site id";
                 }
                 leaf l2vpn-mesh-group {
                   type string;
                 }
                 leaf vc-label {
                   type int32;
                   description "VC label";
                 }
                 leaf context-id {
                   type ipaddr;
                   description "Context Identifier";
                 }
                 leaf route-control-word {
                   type string;
                   description "Control Word";
                 }
                 leaf mtu {
                   type int32;
                   description "MTU along an interface";
                 }
                 leaf cell-bundle-size {
                   type int32;
                   description "Cell bundle size";
                 }
                 leaf vlan-id {
                   type int32;
                 }
                 leaf flow-label-transmit {
                   type int32;
                 }
                 leaf flow-label-receive {
                   type int32;
                 }
                 leaf tdm-payload-size {
                   type int32;
                 }
                 leaf tdm-bitrate {
                   type int32;
                 }
                 leaf pw-status-code {
                   type int32;
                 }
                 leaf cac-bandwidth-failure {
                   type empty;
                   description "Call admission control failure due to insufficient bandwidth";
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf local-preference {
                   type int32;
                 }
                 leaf peer-id {
                   type ipaddr;
                 }
                 leaf path-id {
                   type string;
                 }
                 leaf gateway {
                   type string;
                   description "Sourcing gateway";
                 }
                 leaf rtrib-primary {
                   type string;
                   description "Primary routing table";
                 }
                 leaf rtrib-secondary {
                   type string;
                   description "Secondary routing table";
                 }
                 leaf indirect-nh-count {
                   type int32;
                   description "Number of indirect next hops";
                 }
                 leaf composite-nh-count {
                   type int32;
                   description "Number of composite next hops";
                 }
                 leaf helper-nhid {
                   type uint32;
                   description "Helper nexthop index";
                 }
                 leaf helper-refcount {
                   type int32;
                   description "Reference count of those needing helper route";
                 }
                 leaf backup-pe-group-name {
                   type string;
                   description "Name of the backup PE group";
                 }
                 leaf designated-forwarder {
                   type string;
                   description "Indicates if we are the designated forwarder for this route";
                 }
                 leaf rt-entry-opaque-data {
                   type string;
                   description "Opaque data associated with the route entry";
                 }
                 leaf rt-stats-id-grp-single-line {
                   type string;
                   description "Stats-id-group associated with the route entry";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf evpn-isid {
                   type int32;
                   description "ISID";
                 }
                 leaf rt-evpn-esi {
                   type string;
                   description "ESI";
                 }
                 leaf rt-evpn-bmac {
                   type string;
                   description "BMAC";
                 }
                 leaf active-tag {
                   type string;
                   description "Visual indication of active state of this route entry";
                 }
                 leaf protocol-name {
                   type string;
                 }
                 leaf preference {
                   type int32;
                   description "Preference for the route";
                 }
                 leaf preference2 {
                   type int32;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf snpa-count {
                     type int32;
                     description "Number of SNPAs in this route";
                   }
                   leaf snpa-length {
                     type int32;
                     description "Total length of the SNPAs, in bytes";
                   }
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                   container multicast-member-map-data {
                     description "Multicast member map";
                     leaf multicast-root-hash {
                       type int32;
                     }
                     leaf multicast-core-hash {
                       type int32;
                     }
                     leaf multicast-edge-hash {
                       type int32;
                     }
                     leaf multicast-member-map {
                       type string;
                     }
                   }
                   container layer3-multicast-data {
                     description "Layer3 multicast core key";
                     leaf layer3-multicast-corekey {
                       type int32;
                     }
                   }
                   container multicast-vsg-corekey-data {
                     description "Vsg multicast core key";
                     leaf multicast-vsg-corekey-key {
                       type int32;
                     }
                     leaf multicast-vsg-corekey-len {
                       type int32;
                     }
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container rtd-flow-dep {
                   leaf flow-dep-state {
                     type string;
                   }
                   leaf flow-origin {
                     type ipaddr;
                     description "Originator of the flow information";
                   }
                   leaf flow-next-as {
                     type uint32;
                     description "Neighbor AS of the flow information";
                   }
                   container flow-ucast-rt {
                     description "Unicast route used for resolution";
                   }
                 }
                 container communities {
                   leaf community {
                     type string;
                     description "Basic community";
                   }
                   leaf extended-community {
                     type string;
                     description "Extended community";
                   }
                 }
                 container attrset {
                 }
                 container route-flap-damping {
                   leaf last-merit {
                     type int32;
                     description "Last merit value";
                   }
                   leaf merit {
                     type int32;
                     description "Current merit value";
                   }
                   leaf damping-parameters {
                     type string;
                   }
                   leaf default-damping-parameters {
                     type empty;
                     description "Default damping parameters used";
                   }
                   leaf last-update {
                     type string;
                   }
                   leaf first-update {
                     type string;
                   }
                   leaf route-flap-count {
                     type int32;
                     description "Number of times this route has flapped";
                   }
                   leaf suppressed {
                     type empty;
                     description "This route is suppressed";
                   }
                   leaf reuse-time {
                     type string;
                     description "Time until this route is reusable";
                   }
                   leaf reuse-preference {
                     type int32;
                     description "Preference to use when this route is reused";
                   }
                   leaf expire-time {
                     type string;
                     description "Time when this damping entry expires";
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                   leaf aggregate-flags {
                     type string;
                     description "Flags on this aggregate route entry";
                   }
                   leaf aggregate-depth {
                     type int32;
                     description "Depth of this aggregate";
                   }
                   leaf aggregate-active {
                     type empty;
                     description "Present if this aggregate is active";
                   }
                   leaf contributing-route-count {
                     type int32;
                     description "Number of contributing routes in this aggregate";
                   }
                   container aggregate-as-path {
                     leaf as-path {
                       type string;
                     }
                     leaf reference-count {
                       type int32;
                     }
                   }
                   container aggregated-route {
                     leaf destination-prefix {
                       type string;
                       description "Destination prefix and mask";
                     }
                     leaf protocol-name {
                       type string;
                     }
                   }
                 }
                 container nhh {
                   leaf nh-type {
                     type string;
                     description "Special next hop: Reject, Blackhole, Receive, Multicast, Local, or Unused";
                   }
                   leaf nh-index {
                     type uint32;
                     description "Next-hop index";
                   }
                   leaf nh-address {
                     type int32;
                     description "Address of next hop";
                   }
                   leaf nh-reference-count {
                     type int32;
                     description "Number of references to this next hop";
                   }
                   leaf ext-int-intf-index {
                     type int32;
                     description "Interface index of equal-external-internal multipath";
                   }
                   leaf nh-flood-overflow {
                     type empty;
                     description "Flood nexthop exceeds maximum branches";
                   }
                 }
                 container nh {
                   description "Next-hop gateway information";
                   leaf nh-string {
                     type string;
                   }
                   leaf elnh-address {
                     type int32;
                     description "Address of Element Next-hop";
                   }
                   leaf to {
                     type string;
                     description "Neighbor address to which to send (next-hop address)";
                   }
                   leaf via {
                     type string;
                     description "Reachable via a local interface";
                   }
                   leaf localized-table {
                     type string;
                     description "Name of localized table";
                   }
                   leaf weight {
                     type int32;
                     description "Next-hop weight";
                   }
                   leaf balance {
                     type int32;
                     description "Next-hop balance";
                   }
                   leaf uflags {
                     type int32;
                     description "Next-hop uflags";
                   }
                   leaf filter {
                     type string;
                     description "Next-hop firewall filter";
                   }
                   leaf selected-next-hop {
                     type empty;
                     description "Present if this next hop is selected";
                   }
                   leaf session {
                     type int32;
                     description "Session ID Associated with this NH";
                   }
                   leaf statistics-id-group-terse {
                     type string;
                     description "Statistics ID Group Associated with this NH";
                   }
                   leaf ext-int-type {
                     type string;
                     description "Next-hop type of equal-external-internal multipath";
                   }
                   leaf fc {
                     type int32;
                     description "Forwarding-class";
                   }
                   leaf lsp-name {
                     type string;
                     description "Tunneled into an RSVP LSP";
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf label-element {
                     type string;
                     description "Pointer to the tag label element";
                   }
                   leaf label-element-parent {
                     type string;
                     description "Pointer to the tag label element parent";
                   }
                   leaf label-element-refcount {
                     type string;
                     description "Number of references to the tag label element";
                   }
                   leaf label-element-childcount {
                     type string;
                     description "Number of child references to the tag label element";
                   }
                   leaf label-element-lspid {
                     type string;
                     description "LSP ID of the tag label element";
                   }
                   leaf nh-table-receive {
                     type string;
                     description "Destination is a local address";
                   }
                   leaf nh-table {
                     type string;
                     description "Indirect pointing to another table";
                   }
                   leaf nh-localized-ifl {
                     type string;
                     description "Indirect pointing to a localized ifl";
                   }
                   leaf nh-local-interface {
                     type string;
                     description "Destination is a local interface";
                   }
                   leaf nh-service {
                     type string;
                     description "Next-hop service";
                   }
                   leaf nh-service-pkt-dist {
                     type string;
                     description "Multi services packet distribution type";
                   }
                   leaf nh-service-app-data {
                     type string;
                     description "Multi services application specific data";
                   }
                   leaf nh-private-comp {
                     type string;
                     description "Private Composite Next-hop";
                   }
                   leaf nh-index {
                     type uint32;
                     description "Next-hop index";
                   }
                   leaf nh-address {
                     type int32;
                     description "Address of next hop";
                   }
                 }
                 container protocol-nh {
                   description "Protocol next hop";
                   leaf to {
                     type string;
                     description "Neighbor address to which to send (next-hop address)";
                   }
                   leaf metric {
                     type int32;
                   }
                   leaf aigp {
                     type string;
                     description "AIGP";
                   }
                   leaf balance {
                     type int32;
                     description "Next-hop balance";
                   }
                   leaf flags {
                     type string;
                     description "Enabled trace flags";
                   }
                   leaf res-path-inode-flags {
                     type string;
                   }
                   leaf res-path-flags {
                     type string;
                   }
                   leaf res-path-fnh-link {
                     type string;
                   }
                   leaf res-path-inh-link {
                     type string;
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf composite-nh {
                     type string;
                   }
                   leaf vpnlabel-nh {
                     type string;
                   }
                   leaf indirect-nh {
                     type string;
                   }
                   leaf ext-int-type {
                     type string;
                     description "Next-hop type of equal-external-internal multipath";
                   }
                   leaf forwarding-nh-count {
                     type int32;
                     description "Number of indirect path forwarding next hops";
                   }
                   leaf nh-type {
                     type string;
                     description "Special next hop: Reject, Blackhole, Receive, Multicast, Local, or Unused";
                   }
                   container eth-header-rewrite {
                     description "Ethernet header rewrite information";
                     leaf eth-header-rewrite-smac {
                       type string;
                       description "Source MAC address";
                     }
                     leaf eth-header-rewrite-dmac {
                       type string;
                       description "Destination MAC address";
                     }
                     leaf eth-header-rewrite-tpid {
                       type int32;
                       description "Ethernet header TPID";
                     }
                     leaf eth-header-rewrite-tci {
                       type int32;
                       description "Ethernet header TCI";
                     }
                     leaf eth-header-rewrite-vlan-id {
                       type int32;
                       description "Ethernet header VLAN ID";
                     }
                     leaf eth-header-rewrite-ethertype {
                       type int32;
                       description "Ethernet header ethertype";
                     }
                   }
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-detail {
               leaf rt-destination {
                 type string;
               }
               leaf rt-prefix-length {
                 type int32;
               }
               leaf rt-entry-count {
                 type int32;
                 description "Number of route entries in this route";
               }
               leaf rt-announced-count {
                 type int32;
                 description "Number of announced route entries";
               }
               container rt-entry {
                 leaf bgp-group-name {
                   type string;
                 }
                 leaf bgp-rt-flag {
                   type string;
                   description "BGP route flag";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf l2vpn-mesh-group {
                   type string;
                 }
                 leaf route-distinguisher {
                   type string;
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf bgp-no-label-reason {
                   type string;
                 }
                 leaf bgp-metric-flags {
                   type string;
                   description "BGP metrics flags";
                 }
                 leaf med {
                   type int32;
                   description "Multiple exit discriminator";
                 }
                 leaf local-preference {
                   type int32;
                 }
                 leaf bgp-output-queue-class {
                   type string;
                   description "BGP output queue class";
                 }
                 leaf as-path {
                   type string;
                 }
                 leaf pmsi {
                   type string;
                   description "P-multicast service interface";
                 }
                 leaf cluster-id {
                   type string;
                 }
                 leaf originator {
                   type string;
                 }
                 leaf connector {
                   type string;
                 }
                 leaf path-id {
                   type string;
                 }
                 leaf bgp-aigp {
                   type string;
                   description "Accumulated IGP Metric";
                 }
                 leaf bgp-elc {
                   type empty;
                   description "Entropy label capable";
                 }
                 leaf bgp-elc-nh-valid {
                   type string;
                   description "Whether next hop field matches route next hop";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf active-tag {
                   type string;
                   description "Visual indication of active state of this route entry";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                   leaf attrset-as {
                     type int32;
                     description "Originator AS";
                   }
                   leaf med {
                     type int32;
                     description "Multiple exit discriminator";
                   }
                   leaf local-preference {
                     type int32;
                   }
                   leaf as-path {
                     type string;
                   }
                   leaf pmsi {
                     type string;
                     description "P-multicast service interface";
                   }
                   leaf cluster-id {
                     type string;
                   }
                   leaf originator {
                     type string;
                   }
                   leaf connector {
                     type string;
                   }
                   container communities {
                     leaf community {
                       type string;
                       description "Basic community";
                     }
                     leaf extended-community {
                       type string;
                       description "Extended community";
                     }
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                   leaf to {
                     type string;
                     description "Neighbor address to which to send (next-hop address)";
                   }
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
               container communities {
                 leaf community {
                   type string;
                   description "Basic community";
                 }
                 leaf extended-community {
                   type string;
                   description "Extended community";
                 }
               }
             }
           }
         }
       }
     }
   }
   rpc get-route-martians {
     description "Show martian networks";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
       leaf table {
         description "Name of routing table";
         type string;
       }
     }
     output {
       container route-information {
         leaf as-number {
           type int32;
         }
         leaf router-id {
           type ipaddr;
         }
         leaf maximum-ecmp {
           type int32;
         }
         leaf note-network-services-mode {
           type string;
         }
         container route-table {
           leaf table-name {
             type string;
             description "Unicast routing table";
           }
           leaf destination-count {
             type int32;
             description "Number of destinations in this rib";
           }
           leaf total-route-count {
             type int32;
           }
           leaf active-route-count {
             type int32;
             description "Active routes";
           }
           leaf holddown-route-count {
             type int32;
           }
           leaf hidden-route-count {
             type int32;
           }
           leaf restart-state {
             type string;
           }
           leaf prefix-max {
             type int32;
           }
           leaf prefix-threshold {
             type int32;
           }
           leaf prefix-label {
             type string;
           }
           leaf route-max {
             type int32;
           }
           leaf route-threshold {
             type int32;
           }
           leaf route-limit-label {
             type string;
           }
           container protocols {
             leaf protocol-name {
               type string;
             }
             leaf protocol-route-count {
               type int32;
               description "Total protocol routes";
             }
           }
           container rt {
             container terse {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container terse-mpls-fwd {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief-mpls-fwd {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-brief {
               leaf rt-destination {
                 type string;
               }
               leaf rt-prefix-length {
                 type int32;
               }
               container rt-entry {
                 leaf active-tag {
                   type string;
                   description "Visual indication of active state of this route entry";
                 }
                 leaf med {
                   type int32;
                   description "Multiple exit discriminator";
                 }
                 leaf local-preference {
                   type int32;
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container detail {
               leaf rt-destination {
                 type string;
               }
               leaf rt-prefix-length {
                 type int32;
               }
               leaf rt-entry-count {
                 type int32;
                 description "Number of route entries in this route";
               }
               leaf rt-announced-count {
                 type int32;
                 description "Number of announced route entries";
               }
               leaf rt-state {
                 type string;
                 description "State of this route";
               }
               leaf tsi {
                 type string;
                 description "Task-specific information";
               }
               container rt-entry {
                 leaf nh-type {
                   type string;
                   description "Special next hop: Reject, Blackhole, Receive, Multicast, Local, or Unused";
                 }
                 leaf nh-index {
                   type uint32;
                   description "Next-hop index";
                 }
                 leaf nh-address {
                   type int32;
                   description "Address of next hop";
                 }
                 leaf nh-reference-count {
                   type int32;
                   description "Number of references to this next hop";
                 }
                 leaf ext-int-intf-index {
                   type int32;
                   description "Interface index of equal-external-internal multipath";
                 }
                 leaf nh-flood-overflow {
                   type empty;
                   description "Flood nexthop exceeds maximum branches";
                 }
                 leaf client-data {
                   type string;
                   description "Route server client details";
                 }
                 leaf route-distinguisher {
                   type string;
                 }
                 leaf validation-state {
                   type string;
                 }
                 leaf pmsi {
                   type string;
                   description "P-multicast service interface";
                 }
                 leaf connector {
                   type string;
                 }
                 leaf color {
                   type int32;
                 }
                 leaf color2 {
                   type int32;
                 }
                 leaf rt-isis-level {
                   type int32;
                 }
                 leaf rt-isis-downbit {
                   type int32;
                 }
                 leaf rt-entry-state {
                   type string;
                   description "State of this route entry";
                 }
                 leaf rt-entry-pim-state {
                   type string;
                   description "PIM state of this route entry";
                 }
                 leaf inactive-reason {
                   type string;
                   description "HFRR profile Inactive reason (if any)";
                 }
                 leaf local-as {
                   type int32;
                   description "Local AS number";
                 }
                 leaf peer-as {
                   type int32;
                   description "Peer AS number";
                 }
                 leaf learned-from {
                   type ipaddr;
                   description "Peer address from which this route was learned";
                 }
                 leaf age {
                   type string;
                 }
                 leaf metric {
                   type int32;
                 }
                 leaf metric2 {
                   type int32;
                 }
                 leaf med-plus-igp {
                   type int32;
                 }
                 leaf rt-tag {
                   type int32;
                 }
                 leaf rt-tag2 {
                   type int32;
                 }
                 leaf rt-aigp {
                   type uint64;
                 }
                 leaf rt-resolving-aigp {
                   type uint64;
                 }
                 leaf rt-orr {
                   type uint32;
                 }
                 leaf rt-ospf-area {
                   type string;
                 }
                 leaf task-name {
                   type string;
                   description "Name of this task";
                 }
                 leaf announce-bits {
                   type int32;
                 }
                 leaf announce-tasks {
                   type string;
                 }
                 leaf as-path {
                   type string;
                 }
                 leaf bgp-rt-flag {
                   type string;
                   description "BGP route flag";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf remote-site {
                   type int32;
                   description "Remote site id";
                 }
                 leaf l2vpn-mesh-group {
                   type string;
                 }
                 leaf vc-label {
                   type int32;
                   description "VC label";
                 }
                 leaf context-id {
                   type ipaddr;
                   description "Context Identifier";
                 }
                 leaf route-control-word {
                   type string;
                   description "Control Word";
                 }
                 leaf mtu {
                   type int32;
                   description "MTU along an interface";
                 }
                 leaf cell-bundle-size {
                   type int32;
                   description "Cell bundle size";
                 }
                 leaf vlan-id {
                   type int32;
                 }
                 leaf flow-label-transmit {
                   type int32;
                 }
                 leaf flow-label-receive {
                   type int32;
                 }
                 leaf tdm-payload-size {
                   type int32;
                 }
                 leaf tdm-bitrate {
                   type int32;
                 }
                 leaf pw-status-code {
                   type int32;
                 }
                 leaf cac-bandwidth-failure {
                   type empty;
                   description "Call admission control failure due to insufficient bandwidth";
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf local-preference {
                   type int32;
                 }
                 leaf peer-id {
                   type ipaddr;
                 }
                 leaf path-id {
                   type string;
                 }
                 leaf gateway {
                   type string;
                   description "Sourcing gateway";
                 }
                 leaf rtrib-primary {
                   type string;
                   description "Primary routing table";
                 }
                 leaf rtrib-secondary {
                   type string;
                   description "Secondary routing table";
                 }
                 leaf indirect-nh-count {
                   type int32;
                   description "Number of indirect next hops";
                 }
                 leaf composite-nh-count {
                   type int32;
                   description "Number of composite next hops";
                 }
                 leaf helper-nhid {
                   type uint32;
                   description "Helper nexthop index";
                 }
                 leaf helper-refcount {
                   type int32;
                   description "Reference count of those needing helper route";
                 }
                 leaf backup-pe-group-name {
                   type string;
                   description "Name of the backup PE group";
                 }
                 leaf designated-forwarder {
                   type string;
                   description "Indicates if we are the designated forwarder for this route";
                 }
                 leaf rt-entry-opaque-data {
                   type string;
                   description "Opaque data associated with the route entry";
                 }
                 leaf rt-stats-id-grp-single-line {
                   type string;
                   description "Stats-id-group associated with the route entry";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf evpn-isid {
                   type int32;
                   description "ISID";
                 }
                 leaf rt-evpn-esi {
                   type string;
                   description "ESI";
                 }
                 leaf rt-evpn-bmac {
                   type string;
                   description "BMAC";
                 }
                 leaf active-tag {
                   type string;
                   description "Visual indication of active state of this route entry";
                 }
                 leaf protocol-name {
                   type string;
                 }
                 leaf preference {
                   type int32;
                   description "Preference for the route";
                 }
                 leaf preference2 {
                   type int32;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf snpa-count {
                     type int32;
                     description "Number of SNPAs in this route";
                   }
                   leaf snpa-length {
                     type int32;
                     description "Total length of the SNPAs, in bytes";
                   }
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                   container multicast-member-map-data {
                     description "Multicast member map";
                     leaf multicast-root-hash {
                       type int32;
                     }
                     leaf multicast-core-hash {
                       type int32;
                     }
                     leaf multicast-edge-hash {
                       type int32;
                     }
                     leaf multicast-member-map {
                       type string;
                     }
                   }
                   container layer3-multicast-data {
                     description "Layer3 multicast core key";
                     leaf layer3-multicast-corekey {
                       type int32;
                     }
                   }
                   container multicast-vsg-corekey-data {
                     description "Vsg multicast core key";
                     leaf multicast-vsg-corekey-key {
                       type int32;
                     }
                     leaf multicast-vsg-corekey-len {
                       type int32;
                     }
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container rtd-flow-dep {
                   leaf flow-dep-state {
                     type string;
                   }
                   leaf flow-origin {
                     type ipaddr;
                     description "Originator of the flow information";
                   }
                   leaf flow-next-as {
                     type uint32;
                     description "Neighbor AS of the flow information";
                   }
                   container flow-ucast-rt {
                     description "Unicast route used for resolution";
                   }
                 }
                 container communities {
                   leaf community {
                     type string;
                     description "Basic community";
                   }
                   leaf extended-community {
                     type string;
                     description "Extended community";
                   }
                 }
                 container attrset {
                 }
                 container route-flap-damping {
                   leaf last-merit {
                     type int32;
                     description "Last merit value";
                   }
                   leaf merit {
                     type int32;
                     description "Current merit value";
                   }
                   leaf damping-parameters {
                     type string;
                   }
                   leaf default-damping-parameters {
                     type empty;
                     description "Default damping parameters used";
                   }
                   leaf last-update {
                     type string;
                   }
                   leaf first-update {
                     type string;
                   }
                   leaf route-flap-count {
                     type int32;
                     description "Number of times this route has flapped";
                   }
                   leaf suppressed {
                     type empty;
                     description "This route is suppressed";
                   }
                   leaf reuse-time {
                     type string;
                     description "Time until this route is reusable";
                   }
                   leaf reuse-preference {
                     type int32;
                     description "Preference to use when this route is reused";
                   }
                   leaf expire-time {
                     type string;
                     description "Time when this damping entry expires";
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                   leaf aggregate-flags {
                     type string;
                     description "Flags on this aggregate route entry";
                   }
                   leaf aggregate-depth {
                     type int32;
                     description "Depth of this aggregate";
                   }
                   leaf aggregate-active {
                     type empty;
                     description "Present if this aggregate is active";
                   }
                   leaf contributing-route-count {
                     type int32;
                     description "Number of contributing routes in this aggregate";
                   }
                   container aggregate-as-path {
                     leaf as-path {
                       type string;
                     }
                     leaf reference-count {
                       type int32;
                     }
                   }
                   container aggregated-route {
                     leaf destination-prefix {
                       type string;
                       description "Destination prefix and mask";
                     }
                     leaf protocol-name {
                       type string;
                     }
                   }
                 }
                 container nhh {
                   leaf nh-type {
                     type string;
                     description "Special next hop: Reject, Blackhole, Receive, Multicast, Local, or Unused";
                   }
                   leaf nh-index {
                     type uint32;
                     description "Next-hop index";
                   }
                   leaf nh-address {
                     type int32;
                     description "Address of next hop";
                   }
                   leaf nh-reference-count {
                     type int32;
                     description "Number of references to this next hop";
                   }
                   leaf ext-int-intf-index {
                     type int32;
                     description "Interface index of equal-external-internal multipath";
                   }
                   leaf nh-flood-overflow {
                     type empty;
                     description "Flood nexthop exceeds maximum branches";
                   }
                 }
                 container nh {
                   description "Next-hop gateway information";
                   leaf nh-string {
                     type string;
                   }
                   leaf elnh-address {
                     type int32;
                     description "Address of Element Next-hop";
                   }
                   leaf to {
                     type string;
                     description "Neighbor address to which to send (next-hop address)";
                   }
                   leaf via {
                     type string;
                     description "Reachable via a local interface";
                   }
                   leaf localized-table {
                     type string;
                     description "Name of localized table";
                   }
                   leaf weight {
                     type int32;
                     description "Next-hop weight";
                   }
                   leaf balance {
                     type int32;
                     description "Next-hop balance";
                   }
                   leaf uflags {
                     type int32;
                     description "Next-hop uflags";
                   }
                   leaf filter {
                     type string;
                     description "Next-hop firewall filter";
                   }
                   leaf selected-next-hop {
                     type empty;
                     description "Present if this next hop is selected";
                   }
                   leaf session {
                     type int32;
                     description "Session ID Associated with this NH";
                   }
                   leaf statistics-id-group-terse {
                     type string;
                     description "Statistics ID Group Associated with this NH";
                   }
                   leaf ext-int-type {
                     type string;
                     description "Next-hop type of equal-external-internal multipath";
                   }
                   leaf fc {
                     type int32;
                     description "Forwarding-class";
                   }
                   leaf lsp-name {
                     type string;
                     description "Tunneled into an RSVP LSP";
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf label-element {
                     type string;
                     description "Pointer to the tag label element";
                   }
                   leaf label-element-parent {
                     type string;
                     description "Pointer to the tag label element parent";
                   }
                   leaf label-element-refcount {
                     type string;
                     description "Number of references to the tag label element";
                   }
                   leaf label-element-childcount {
                     type string;
                     description "Number of child references to the tag label element";
                   }
                   leaf label-element-lspid {
                     type string;
                     description "LSP ID of the tag label element";
                   }
                   leaf nh-table-receive {
                     type string;
                     description "Destination is a local address";
                   }
                   leaf nh-table {
                     type string;
                     description "Indirect pointing to another table";
                   }
                   leaf nh-localized-ifl {
                     type string;
                     description "Indirect pointing to a localized ifl";
                   }
                   leaf nh-local-interface {
                     type string;
                     description "Destination is a local interface";
                   }
                   leaf nh-service {
                     type string;
                     description "Next-hop service";
                   }
                   leaf nh-service-pkt-dist {
                     type string;
                     description "Multi services packet distribution type";
                   }
                   leaf nh-service-app-data {
                     type string;
                     description "Multi services application specific data";
                   }
                   leaf nh-private-comp {
                     type string;
                     description "Private Composite Next-hop";
                   }
                   leaf nh-index {
                     type uint32;
                     description "Next-hop index";
                   }
                   leaf nh-address {
                     type int32;
                     description "Address of next hop";
                   }
                 }
                 container protocol-nh {
                   description "Protocol next hop";
                   leaf to {
                     type string;
                     description "Neighbor address to which to send (next-hop address)";
                   }
                   leaf metric {
                     type int32;
                   }
                   leaf aigp {
                     type string;
                     description "AIGP";
                   }
                   leaf balance {
                     type int32;
                     description "Next-hop balance";
                   }
                   leaf flags {
                     type string;
                     description "Enabled trace flags";
                   }
                   leaf res-path-inode-flags {
                     type string;
                   }
                   leaf res-path-flags {
                     type string;
                   }
                   leaf res-path-fnh-link {
                     type string;
                   }
                   leaf res-path-inh-link {
                     type string;
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf composite-nh {
                     type string;
                   }
                   leaf vpnlabel-nh {
                     type string;
                   }
                   leaf indirect-nh {
                     type string;
                   }
                   leaf ext-int-type {
                     type string;
                     description "Next-hop type of equal-external-internal multipath";
                   }
                   leaf forwarding-nh-count {
                     type int32;
                     description "Number of indirect path forwarding next hops";
                   }
                   leaf nh-type {
                     type string;
                     description "Special next hop: Reject, Blackhole, Receive, Multicast, Local, or Unused";
                   }
                   container eth-header-rewrite {
                     description "Ethernet header rewrite information";
                     leaf eth-header-rewrite-smac {
                       type string;
                       description "Source MAC address";
                     }
                     leaf eth-header-rewrite-dmac {
                       type string;
                       description "Destination MAC address";
                     }
                     leaf eth-header-rewrite-tpid {
                       type int32;
                       description "Ethernet header TPID";
                     }
                     leaf eth-header-rewrite-tci {
                       type int32;
                       description "Ethernet header TCI";
                     }
                     leaf eth-header-rewrite-vlan-id {
                       type int32;
                       description "Ethernet header VLAN ID";
                     }
                     leaf eth-header-rewrite-ethertype {
                       type int32;
                       description "Ethernet header ethertype";
                     }
                   }
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-detail {
               leaf rt-destination {
                 type string;
               }
               leaf rt-prefix-length {
                 type int32;
               }
               leaf rt-entry-count {
                 type int32;
                 description "Number of route entries in this route";
               }
               leaf rt-announced-count {
                 type int32;
                 description "Number of announced route entries";
               }
               container rt-entry {
                 leaf bgp-group-name {
                   type string;
                 }
                 leaf bgp-rt-flag {
                   type string;
                   description "BGP route flag";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf l2vpn-mesh-group {
                   type string;
                 }
                 leaf route-distinguisher {
                   type string;
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf bgp-no-label-reason {
                   type string;
                 }
                 leaf bgp-metric-flags {
                   type string;
                   description "BGP metrics flags";
                 }
                 leaf med {
                   type int32;
                   description "Multiple exit discriminator";
                 }
                 leaf local-preference {
                   type int32;
                 }
                 leaf bgp-output-queue-class {
                   type string;
                   description "BGP output queue class";
                 }
                 leaf as-path {
                   type string;
                 }
                 leaf pmsi {
                   type string;
                   description "P-multicast service interface";
                 }
                 leaf cluster-id {
                   type string;
                 }
                 leaf originator {
                   type string;
                 }
                 leaf connector {
                   type string;
                 }
                 leaf path-id {
                   type string;
                 }
                 leaf bgp-aigp {
                   type string;
                   description "Accumulated IGP Metric";
                 }
                 leaf bgp-elc {
                   type empty;
                   description "Entropy label capable";
                 }
                 leaf bgp-elc-nh-valid {
                   type string;
                   description "Whether next hop field matches route next hop";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf active-tag {
                   type string;
                   description "Visual indication of active state of this route entry";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                   leaf attrset-as {
                     type int32;
                     description "Originator AS";
                   }
                   leaf med {
                     type int32;
                     description "Multiple exit discriminator";
                   }
                   leaf local-preference {
                     type int32;
                   }
                   leaf as-path {
                     type string;
                   }
                   leaf pmsi {
                     type string;
                     description "P-multicast service interface";
                   }
                   leaf cluster-id {
                     type string;
                   }
                   leaf originator {
                     type string;
                   }
                   leaf connector {
                     type string;
                   }
                   container communities {
                     leaf community {
                       type string;
                       description "Basic community";
                     }
                     leaf extended-community {
                       type string;
                       description "Extended community";
                     }
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                   leaf to {
                     type string;
                     description "Neighbor address to which to send (next-hop address)";
                   }
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
               container communities {
                 leaf community {
                   type string;
                   description "Basic community";
                 }
                 leaf extended-community {
                   type string;
                   description "Extended community";
                 }
               }
             }
           }
         }
         container rt-martians {
           container route-filter {
             description "Entries in martian table";
             leaf address {
               type ipaddr;
             }
             leaf flags {
               type string;
               description "Enabled trace flags";
             }
             leaf extended-information {
               type string;
             }
             leaf match-count {
               type uint64;
             }
           }
         }
         container rt-ribgroup {
           leaf rt-ribgroup-name {
             type string;
             description "Rib-group name";
           }
           leaf rt-ribgroup-address {
             type string;
             description "Rib-group address";
           }
           leaf rt-ribgroup-address-family {
             type string;
             description "Rib-group address family";
           }
           leaf rt-ribgroup-flags {
             type string;
             description "Rib-group flags";
           }
           leaf rt-ribgroup-refcount {
             type uint32;
             description "Rib-group refcount";
           }
           leaf rt-ribgroup-export-name {
             type string;
             description "Export RIB name";
           }
           leaf rt-ribgroup-import-name {
             type string;
             description "Import RIB name";
           }
           leaf rt-ribgroup-import-policy-name {
             type string;
             description "Import policy name";
           }
           leaf rt-ribgroup-import-secondary-name {
             type string;
             description "Import secondary RIB name";
           }
           leaf rt-ribgroup-union-head-name {
             type string;
             description "Rib-group union head name";
           }
           leaf rt-ribgroup-union-child-name {
             type string;
             description "Rib-group union child name";
           }
         }
         container rt-test-policy-prefix {
           leaf rt-policy-name {
             type string;
           }
           leaf rt-destination {
             type string;
           }
           leaf rt-prefix-length {
             type int32;
           }
           container rt-test-policy-term {
             leaf rt-policy-term-name {
               type string;
             }
             leaf rt-policy-term-result {
               type string;
             }
             leaf rt-policy-term-action {
               type string;
             }
           }
         }
         container rt-test-policy {
           leaf rt-policy-name {
             type string;
           }
           leaf rt-route-accepted {
             type int32;
           }
           leaf rt-route-rejected {
             type int32;
           }
         }
       }
     }
   }
   rpc get-route-cumulative {
     description "Show the cumulative routes in VRF table";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
       leaf vpn-family {
         type enumeration {
           enum "inet.0" {
             description "Display the inet.0 vrf instance";
           }
           enum "inet6.0" {
             description "Display the inet6.0 vrf instance";
           }
         }
         mandatory true;
       }
     }
     output {
       container route-information {
         leaf as-number {
           type int32;
         }
         leaf router-id {
           type ipaddr;
         }
         leaf maximum-ecmp {
           type int32;
         }
         leaf note-network-services-mode {
           type string;
         }
         container route-table {
           leaf table-name {
             type string;
             description "Unicast routing table";
           }
           leaf destination-count {
             type int32;
             description "Number of destinations in this rib";
           }
           leaf total-route-count {
             type int32;
           }
           leaf active-route-count {
             type int32;
             description "Active routes";
           }
           leaf holddown-route-count {
             type int32;
           }
           leaf hidden-route-count {
             type int32;
           }
           leaf restart-state {
             type string;
           }
           leaf prefix-max {
             type int32;
           }
           leaf prefix-threshold {
             type int32;
           }
           leaf prefix-label {
             type string;
           }
           leaf route-max {
             type int32;
           }
           leaf route-threshold {
             type int32;
           }
           leaf route-limit-label {
             type string;
           }
           container protocols {
             leaf protocol-name {
               type string;
             }
             leaf protocol-route-count {
               type int32;
               description "Total protocol routes";
             }
           }
           container rt {
             container terse {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container terse-mpls-fwd {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief-mpls-fwd {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-brief {
               leaf rt-destination {
                 type string;
               }
               leaf rt-prefix-length {
                 type int32;
               }
               container rt-entry {
                 leaf active-tag {
                   type string;
                   description "Visual indication of active state of this route entry";
                 }
                 leaf med {
                   type int32;
                   description "Multiple exit discriminator";
                 }
                 leaf local-preference {
                   type int32;
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container detail {
               leaf rt-destination {
                 type string;
               }
               leaf rt-prefix-length {
                 type int32;
               }
               leaf rt-entry-count {
                 type int32;
                 description "Number of route entries in this route";
               }
               leaf rt-announced-count {
                 type int32;
                 description "Number of announced route entries";
               }
               leaf rt-state {
                 type string;
                 description "State of this route";
               }
               leaf tsi {
                 type string;
                 description "Task-specific information";
               }
               container rt-entry {
                 leaf nh-type {
                   type string;
                   description "Special next hop: Reject, Blackhole, Receive, Multicast, Local, or Unused";
                 }
                 leaf nh-index {
                   type uint32;
                   description "Next-hop index";
                 }
                 leaf nh-address {
                   type int32;
                   description "Address of next hop";
                 }
                 leaf nh-reference-count {
                   type int32;
                   description "Number of references to this next hop";
                 }
                 leaf ext-int-intf-index {
                   type int32;
                   description "Interface index of equal-external-internal multipath";
                 }
                 leaf nh-flood-overflow {
                   type empty;
                   description "Flood nexthop exceeds maximum branches";
                 }
                 leaf client-data {
                   type string;
                   description "Route server client details";
                 }
                 leaf route-distinguisher {
                   type string;
                 }
                 leaf validation-state {
                   type string;
                 }
                 leaf pmsi {
                   type string;
                   description "P-multicast service interface";
                 }
                 leaf connector {
                   type string;
                 }
                 leaf color {
                   type int32;
                 }
                 leaf color2 {
                   type int32;
                 }
                 leaf rt-isis-level {
                   type int32;
                 }
                 leaf rt-isis-downbit {
                   type int32;
                 }
                 leaf rt-entry-state {
                   type string;
                   description "State of this route entry";
                 }
                 leaf rt-entry-pim-state {
                   type string;
                   description "PIM state of this route entry";
                 }
                 leaf inactive-reason {
                   type string;
                   description "HFRR profile Inactive reason (if any)";
                 }
                 leaf local-as {
                   type int32;
                   description "Local AS number";
                 }
                 leaf peer-as {
                   type int32;
                   description "Peer AS number";
                 }
                 leaf learned-from {
                   type ipaddr;
                   description "Peer address from which this route was learned";
                 }
                 leaf age {
                   type string;
                 }
                 leaf metric {
                   type int32;
                 }
                 leaf metric2 {
                   type int32;
                 }
                 leaf med-plus-igp {
                   type int32;
                 }
                 leaf rt-tag {
                   type int32;
                 }
                 leaf rt-tag2 {
                   type int32;
                 }
                 leaf rt-aigp {
                   type uint64;
                 }
                 leaf rt-resolving-aigp {
                   type uint64;
                 }
                 leaf rt-orr {
                   type uint32;
                 }
                 leaf rt-ospf-area {
                   type string;
                 }
                 leaf task-name {
                   type string;
                   description "Name of this task";
                 }
                 leaf announce-bits {
                   type int32;
                 }
                 leaf announce-tasks {
                   type string;
                 }
                 leaf as-path {
                   type string;
                 }
                 leaf bgp-rt-flag {
                   type string;
                   description "BGP route flag";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf remote-site {
                   type int32;
                   description "Remote site id";
                 }
                 leaf l2vpn-mesh-group {
                   type string;
                 }
                 leaf vc-label {
                   type int32;
                   description "VC label";
                 }
                 leaf context-id {
                   type ipaddr;
                   description "Context Identifier";
                 }
                 leaf route-control-word {
                   type string;
                   description "Control Word";
                 }
                 leaf mtu {
                   type int32;
                   description "MTU along an interface";
                 }
                 leaf cell-bundle-size {
                   type int32;
                   description "Cell bundle size";
                 }
                 leaf vlan-id {
                   type int32;
                 }
                 leaf flow-label-transmit {
                   type int32;
                 }
                 leaf flow-label-receive {
                   type int32;
                 }
                 leaf tdm-payload-size {
                   type int32;
                 }
                 leaf tdm-bitrate {
                   type int32;
                 }
                 leaf pw-status-code {
                   type int32;
                 }
                 leaf cac-bandwidth-failure {
                   type empty;
                   description "Call admission control failure due to insufficient bandwidth";
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf local-preference {
                   type int32;
                 }
                 leaf peer-id {
                   type ipaddr;
                 }
                 leaf path-id {
                   type string;
                 }
                 leaf gateway {
                   type string;
                   description "Sourcing gateway";
                 }
                 leaf rtrib-primary {
                   type string;
                   description "Primary routing table";
                 }
                 leaf rtrib-secondary {
                   type string;
                   description "Secondary routing table";
                 }
                 leaf indirect-nh-count {
                   type int32;
                   description "Number of indirect next hops";
                 }
                 leaf composite-nh-count {
                   type int32;
                   description "Number of composite next hops";
                 }
                 leaf helper-nhid {
                   type uint32;
                   description "Helper nexthop index";
                 }
                 leaf helper-refcount {
                   type int32;
                   description "Reference count of those needing helper route";
                 }
                 leaf backup-pe-group-name {
                   type string;
                   description "Name of the backup PE group";
                 }
                 leaf designated-forwarder {
                   type string;
                   description "Indicates if we are the designated forwarder for this route";
                 }
                 leaf rt-entry-opaque-data {
                   type string;
                   description "Opaque data associated with the route entry";
                 }
                 leaf rt-stats-id-grp-single-line {
                   type string;
                   description "Stats-id-group associated with the route entry";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf evpn-isid {
                   type int32;
                   description "ISID";
                 }
                 leaf rt-evpn-esi {
                   type string;
                   description "ESI";
                 }
                 leaf rt-evpn-bmac {
                   type string;
                   description "BMAC";
                 }
                 leaf active-tag {
                   type string;
                   description "Visual indication of active state of this route entry";
                 }
                 leaf protocol-name {
                   type string;
                 }
                 leaf preference {
                   type int32;
                   description "Preference for the route";
                 }
                 leaf preference2 {
                   type int32;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf snpa-count {
                     type int32;
                     description "Number of SNPAs in this route";
                   }
                   leaf snpa-length {
                     type int32;
                     description "Total length of the SNPAs, in bytes";
                   }
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                   container multicast-member-map-data {
                     description "Multicast member map";
                     leaf multicast-root-hash {
                       type int32;
                     }
                     leaf multicast-core-hash {
                       type int32;
                     }
                     leaf multicast-edge-hash {
                       type int32;
                     }
                     leaf multicast-member-map {
                       type string;
                     }
                   }
                   container layer3-multicast-data {
                     description "Layer3 multicast core key";
                     leaf layer3-multicast-corekey {
                       type int32;
                     }
                   }
                   container multicast-vsg-corekey-data {
                     description "Vsg multicast core key";
                     leaf multicast-vsg-corekey-key {
                       type int32;
                     }
                     leaf multicast-vsg-corekey-len {
                       type int32;
                     }
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container rtd-flow-dep {
                   leaf flow-dep-state {
                     type string;
                   }
                   leaf flow-origin {
                     type ipaddr;
                     description "Originator of the flow information";
                   }
                   leaf flow-next-as {
                     type uint32;
                     description "Neighbor AS of the flow information";
                   }
                   container flow-ucast-rt {
                     description "Unicast route used for resolution";
                   }
                 }
                 container communities {
                   leaf community {
                     type string;
                     description "Basic community";
                   }
                   leaf extended-community {
                     type string;
                     description "Extended community";
                   }
                 }
                 container attrset {
                 }
                 container route-flap-damping {
                   leaf last-merit {
                     type int32;
                     description "Last merit value";
                   }
                   leaf merit {
                     type int32;
                     description "Current merit value";
                   }
                   leaf damping-parameters {
                     type string;
                   }
                   leaf default-damping-parameters {
                     type empty;
                     description "Default damping parameters used";
                   }
                   leaf last-update {
                     type string;
                   }
                   leaf first-update {
                     type string;
                   }
                   leaf route-flap-count {
                     type int32;
                     description "Number of times this route has flapped";
                   }
                   leaf suppressed {
                     type empty;
                     description "This route is suppressed";
                   }
                   leaf reuse-time {
                     type string;
                     description "Time until this route is reusable";
                   }
                   leaf reuse-preference {
                     type int32;
                     description "Preference to use when this route is reused";
                   }
                   leaf expire-time {
                     type string;
                     description "Time when this damping entry expires";
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                   leaf aggregate-flags {
                     type string;
                     description "Flags on this aggregate route entry";
                   }
                   leaf aggregate-depth {
                     type int32;
                     description "Depth of this aggregate";
                   }
                   leaf aggregate-active {
                     type empty;
                     description "Present if this aggregate is active";
                   }
                   leaf contributing-route-count {
                     type int32;
                     description "Number of contributing routes in this aggregate";
                   }
                   container aggregate-as-path {
                     leaf as-path {
                       type string;
                     }
                     leaf reference-count {
                       type int32;
                     }
                   }
                   container aggregated-route {
                     leaf destination-prefix {
                       type string;
                       description "Destination prefix and mask";
                     }
                     leaf protocol-name {
                       type string;
                     }
                   }
                 }
                 container nhh {
                   leaf nh-type {
                     type string;
                     description "Special next hop: Reject, Blackhole, Receive, Multicast, Local, or Unused";
                   }
                   leaf nh-index {
                     type uint32;
                     description "Next-hop index";
                   }
                   leaf nh-address {
                     type int32;
                     description "Address of next hop";
                   }
                   leaf nh-reference-count {
                     type int32;
                     description "Number of references to this next hop";
                   }
                   leaf ext-int-intf-index {
                     type int32;
                     description "Interface index of equal-external-internal multipath";
                   }
                   leaf nh-flood-overflow {
                     type empty;
                     description "Flood nexthop exceeds maximum branches";
                   }
                 }
                 container nh {
                   description "Next-hop gateway information";
                   leaf nh-string {
                     type string;
                   }
                   leaf elnh-address {
                     type int32;
                     description "Address of Element Next-hop";
                   }
                   leaf to {
                     type string;
                     description "Neighbor address to which to send (next-hop address)";
                   }
                   leaf via {
                     type string;
                     description "Reachable via a local interface";
                   }
                   leaf localized-table {
                     type string;
                     description "Name of localized table";
                   }
                   leaf weight {
                     type int32;
                     description "Next-hop weight";
                   }
                   leaf balance {
                     type int32;
                     description "Next-hop balance";
                   }
                   leaf uflags {
                     type int32;
                     description "Next-hop uflags";
                   }
                   leaf filter {
                     type string;
                     description "Next-hop firewall filter";
                   }
                   leaf selected-next-hop {
                     type empty;
                     description "Present if this next hop is selected";
                   }
                   leaf session {
                     type int32;
                     description "Session ID Associated with this NH";
                   }
                   leaf statistics-id-group-terse {
                     type string;
                     description "Statistics ID Group Associated with this NH";
                   }
                   leaf ext-int-type {
                     type string;
                     description "Next-hop type of equal-external-internal multipath";
                   }
                   leaf fc {
                     type int32;
                     description "Forwarding-class";
                   }
                   leaf lsp-name {
                     type string;
                     description "Tunneled into an RSVP LSP";
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf label-element {
                     type string;
                     description "Pointer to the tag label element";
                   }
                   leaf label-element-parent {
                     type string;
                     description "Pointer to the tag label element parent";
                   }
                   leaf label-element-refcount {
                     type string;
                     description "Number of references to the tag label element";
                   }
                   leaf label-element-childcount {
                     type string;
                     description "Number of child references to the tag label element";
                   }
                   leaf label-element-lspid {
                     type string;
                     description "LSP ID of the tag label element";
                   }
                   leaf nh-table-receive {
                     type string;
                     description "Destination is a local address";
                   }
                   leaf nh-table {
                     type string;
                     description "Indirect pointing to another table";
                   }
                   leaf nh-localized-ifl {
                     type string;
                     description "Indirect pointing to a localized ifl";
                   }
                   leaf nh-local-interface {
                     type string;
                     description "Destination is a local interface";
                   }
                   leaf nh-service {
                     type string;
                     description "Next-hop service";
                   }
                   leaf nh-service-pkt-dist {
                     type string;
                     description "Multi services packet distribution type";
                   }
                   leaf nh-service-app-data {
                     type string;
                     description "Multi services application specific data";
                   }
                   leaf nh-private-comp {
                     type string;
                     description "Private Composite Next-hop";
                   }
                   leaf nh-index {
                     type uint32;
                     description "Next-hop index";
                   }
                   leaf nh-address {
                     type int32;
                     description "Address of next hop";
                   }
                 }
                 container protocol-nh {
                   description "Protocol next hop";
                   leaf to {
                     type string;
                     description "Neighbor address to which to send (next-hop address)";
                   }
                   leaf metric {
                     type int32;
                   }
                   leaf aigp {
                     type string;
                     description "AIGP";
                   }
                   leaf balance {
                     type int32;
                     description "Next-hop balance";
                   }
                   leaf flags {
                     type string;
                     description "Enabled trace flags";
                   }
                   leaf res-path-inode-flags {
                     type string;
                   }
                   leaf res-path-flags {
                     type string;
                   }
                   leaf res-path-fnh-link {
                     type string;
                   }
                   leaf res-path-inh-link {
                     type string;
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf composite-nh {
                     type string;
                   }
                   leaf vpnlabel-nh {
                     type string;
                   }
                   leaf indirect-nh {
                     type string;
                   }
                   leaf ext-int-type {
                     type string;
                     description "Next-hop type of equal-external-internal multipath";
                   }
                   leaf forwarding-nh-count {
                     type int32;
                     description "Number of indirect path forwarding next hops";
                   }
                   leaf nh-type {
                     type string;
                     description "Special next hop: Reject, Blackhole, Receive, Multicast, Local, or Unused";
                   }
                   container eth-header-rewrite {
                     description "Ethernet header rewrite information";
                     leaf eth-header-rewrite-smac {
                       type string;
                       description "Source MAC address";
                     }
                     leaf eth-header-rewrite-dmac {
                       type string;
                       description "Destination MAC address";
                     }
                     leaf eth-header-rewrite-tpid {
                       type int32;
                       description "Ethernet header TPID";
                     }
                     leaf eth-header-rewrite-tci {
                       type int32;
                       description "Ethernet header TCI";
                     }
                     leaf eth-header-rewrite-vlan-id {
                       type int32;
                       description "Ethernet header VLAN ID";
                     }
                     leaf eth-header-rewrite-ethertype {
                       type int32;
                       description "Ethernet header ethertype";
                     }
                   }
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-detail {
               leaf rt-destination {
                 type string;
               }
               leaf rt-prefix-length {
                 type int32;
               }
               leaf rt-entry-count {
                 type int32;
                 description "Number of route entries in this route";
               }
               leaf rt-announced-count {
                 type int32;
                 description "Number of announced route entries";
               }
               container rt-entry {
                 leaf bgp-group-name {
                   type string;
                 }
                 leaf bgp-rt-flag {
                   type string;
                   description "BGP route flag";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf l2vpn-mesh-group {
                   type string;
                 }
                 leaf route-distinguisher {
                   type string;
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf bgp-no-label-reason {
                   type string;
                 }
                 leaf bgp-metric-flags {
                   type string;
                   description "BGP metrics flags";
                 }
                 leaf med {
                   type int32;
                   description "Multiple exit discriminator";
                 }
                 leaf local-preference {
                   type int32;
                 }
                 leaf bgp-output-queue-class {
                   type string;
                   description "BGP output queue class";
                 }
                 leaf as-path {
                   type string;
                 }
                 leaf pmsi {
                   type string;
                   description "P-multicast service interface";
                 }
                 leaf cluster-id {
                   type string;
                 }
                 leaf originator {
                   type string;
                 }
                 leaf connector {
                   type string;
                 }
                 leaf path-id {
                   type string;
                 }
                 leaf bgp-aigp {
                   type string;
                   description "Accumulated IGP Metric";
                 }
                 leaf bgp-elc {
                   type empty;
                   description "Entropy label capable";
                 }
                 leaf bgp-elc-nh-valid {
                   type string;
                   description "Whether next hop field matches route next hop";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf active-tag {
                   type string;
                   description "Visual indication of active state of this route entry";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                   leaf attrset-as {
                     type int32;
                     description "Originator AS";
                   }
                   leaf med {
                     type int32;
                     description "Multiple exit discriminator";
                   }
                   leaf local-preference {
                     type int32;
                   }
                   leaf as-path {
                     type string;
                   }
                   leaf pmsi {
                     type string;
                     description "P-multicast service interface";
                   }
                   leaf cluster-id {
                     type string;
                   }
                   leaf originator {
                     type string;
                   }
                   leaf connector {
                     type string;
                   }
                   container communities {
                     leaf community {
                       type string;
                       description "Basic community";
                     }
                     leaf extended-community {
                       type string;
                       description "Extended community";
                     }
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                   leaf to {
                     type string;
                     description "Neighbor address to which to send (next-hop address)";
                   }
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
               container communities {
                 leaf community {
                   type string;
                   description "Basic community";
                 }
                 leaf extended-community {
                   type string;
                   description "Extended community";
                 }
               }
             }
           }
         }
         container rt-martians {
           container route-filter {
             description "Entries in martian table";
             leaf address {
               type ipaddr;
             }
             leaf flags {
               type string;
               description "Enabled trace flags";
             }
             leaf extended-information {
               type string;
             }
             leaf match-count {
               type uint64;
             }
           }
         }
         container rt-ribgroup {
           leaf rt-ribgroup-name {
             type string;
             description "Rib-group name";
           }
           leaf rt-ribgroup-address {
             type string;
             description "Rib-group address";
           }
           leaf rt-ribgroup-address-family {
             type string;
             description "Rib-group address family";
           }
           leaf rt-ribgroup-flags {
             type string;
             description "Rib-group flags";
           }
           leaf rt-ribgroup-refcount {
             type uint32;
             description "Rib-group refcount";
           }
           leaf rt-ribgroup-export-name {
             type string;
             description "Export RIB name";
           }
           leaf rt-ribgroup-import-name {
             type string;
             description "Import RIB name";
           }
           leaf rt-ribgroup-import-policy-name {
             type string;
             description "Import policy name";
           }
           leaf rt-ribgroup-import-secondary-name {
             type string;
             description "Import secondary RIB name";
           }
           leaf rt-ribgroup-union-head-name {
             type string;
             description "Rib-group union head name";
           }
           leaf rt-ribgroup-union-child-name {
             type string;
             description "Rib-group union child name";
           }
         }
         container rt-test-policy-prefix {
           leaf rt-policy-name {
             type string;
           }
           leaf rt-destination {
             type string;
           }
           leaf rt-prefix-length {
             type int32;
           }
           container rt-test-policy-term {
             leaf rt-policy-term-name {
               type string;
             }
             leaf rt-policy-term-result {
               type string;
             }
             leaf rt-policy-term-action {
               type string;
             }
           }
         }
         container rt-test-policy {
           leaf rt-policy-name {
             type string;
           }
           leaf rt-route-accepted {
             type int32;
           }
           leaf rt-route-rejected {
             type int32;
           }
         }
       }
     }
   }
   rpc get-route-rib-groups {
     description "Show group of routing tables";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
     }
     output {
       container route-information {
         leaf as-number {
           type int32;
         }
         leaf router-id {
           type ipaddr;
         }
         leaf maximum-ecmp {
           type int32;
         }
         leaf note-network-services-mode {
           type string;
         }
         container route-table {
           leaf table-name {
             type string;
             description "Unicast routing table";
           }
           leaf destination-count {
             type int32;
             description "Number of destinations in this rib";
           }
           leaf total-route-count {
             type int32;
           }
           leaf active-route-count {
             type int32;
             description "Active routes";
           }
           leaf holddown-route-count {
             type int32;
           }
           leaf hidden-route-count {
             type int32;
           }
           leaf restart-state {
             type string;
           }
           leaf prefix-max {
             type int32;
           }
           leaf prefix-threshold {
             type int32;
           }
           leaf prefix-label {
             type string;
           }
           leaf route-max {
             type int32;
           }
           leaf route-threshold {
             type int32;
           }
           leaf route-limit-label {
             type string;
           }
           container protocols {
             leaf protocol-name {
               type string;
             }
             leaf protocol-route-count {
               type int32;
               description "Total protocol routes";
             }
           }
           container rt {
             container terse {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container terse-mpls-fwd {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief-mpls-fwd {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-brief {
               leaf rt-destination {
                 type string;
               }
               leaf rt-prefix-length {
                 type int32;
               }
               container rt-entry {
                 leaf active-tag {
                   type string;
                   description "Visual indication of active state of this route entry";
                 }
                 leaf med {
                   type int32;
                   description "Multiple exit discriminator";
                 }
                 leaf local-preference {
                   type int32;
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container detail {
               leaf rt-destination {
                 type string;
               }
               leaf rt-prefix-length {
                 type int32;
               }
               leaf rt-entry-count {
                 type int32;
                 description "Number of route entries in this route";
               }
               leaf rt-announced-count {
                 type int32;
                 description "Number of announced route entries";
               }
               leaf rt-state {
                 type string;
                 description "State of this route";
               }
               leaf tsi {
                 type string;
                 description "Task-specific information";
               }
               container rt-entry {
                 leaf nh-type {
                   type string;
                   description "Special next hop: Reject, Blackhole, Receive, Multicast, Local, or Unused";
                 }
                 leaf nh-index {
                   type uint32;
                   description "Next-hop index";
                 }
                 leaf nh-address {
                   type int32;
                   description "Address of next hop";
                 }
                 leaf nh-reference-count {
                   type int32;
                   description "Number of references to this next hop";
                 }
                 leaf ext-int-intf-index {
                   type int32;
                   description "Interface index of equal-external-internal multipath";
                 }
                 leaf nh-flood-overflow {
                   type empty;
                   description "Flood nexthop exceeds maximum branches";
                 }
                 leaf client-data {
                   type string;
                   description "Route server client details";
                 }
                 leaf route-distinguisher {
                   type string;
                 }
                 leaf validation-state {
                   type string;
                 }
                 leaf pmsi {
                   type string;
                   description "P-multicast service interface";
                 }
                 leaf connector {
                   type string;
                 }
                 leaf color {
                   type int32;
                 }
                 leaf color2 {
                   type int32;
                 }
                 leaf rt-isis-level {
                   type int32;
                 }
                 leaf rt-isis-downbit {
                   type int32;
                 }
                 leaf rt-entry-state {
                   type string;
                   description "State of this route entry";
                 }
                 leaf rt-entry-pim-state {
                   type string;
                   description "PIM state of this route entry";
                 }
                 leaf inactive-reason {
                   type string;
                   description "HFRR profile Inactive reason (if any)";
                 }
                 leaf local-as {
                   type int32;
                   description "Local AS number";
                 }
                 leaf peer-as {
                   type int32;
                   description "Peer AS number";
                 }
                 leaf learned-from {
                   type ipaddr;
                   description "Peer address from which this route was learned";
                 }
                 leaf age {
                   type string;
                 }
                 leaf metric {
                   type int32;
                 }
                 leaf metric2 {
                   type int32;
                 }
                 leaf med-plus-igp {
                   type int32;
                 }
                 leaf rt-tag {
                   type int32;
                 }
                 leaf rt-tag2 {
                   type int32;
                 }
                 leaf rt-aigp {
                   type uint64;
                 }
                 leaf rt-resolving-aigp {
                   type uint64;
                 }
                 leaf rt-orr {
                   type uint32;
                 }
                 leaf rt-ospf-area {
                   type string;
                 }
                 leaf task-name {
                   type string;
                   description "Name of this task";
                 }
                 leaf announce-bits {
                   type int32;
                 }
                 leaf announce-tasks {
                   type string;
                 }
                 leaf as-path {
                   type string;
                 }
                 leaf bgp-rt-flag {
                   type string;
                   description "BGP route flag";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf remote-site {
                   type int32;
                   description "Remote site id";
                 }
                 leaf l2vpn-mesh-group {
                   type string;
                 }
                 leaf vc-label {
                   type int32;
                   description "VC label";
                 }
                 leaf context-id {
                   type ipaddr;
                   description "Context Identifier";
                 }
                 leaf route-control-word {
                   type string;
                   description "Control Word";
                 }
                 leaf mtu {
                   type int32;
                   description "MTU along an interface";
                 }
                 leaf cell-bundle-size {
                   type int32;
                   description "Cell bundle size";
                 }
                 leaf vlan-id {
                   type int32;
                 }
                 leaf flow-label-transmit {
                   type int32;
                 }
                 leaf flow-label-receive {
                   type int32;
                 }
                 leaf tdm-payload-size {
                   type int32;
                 }
                 leaf tdm-bitrate {
                   type int32;
                 }
                 leaf pw-status-code {
                   type int32;
                 }
                 leaf cac-bandwidth-failure {
                   type empty;
                   description "Call admission control failure due to insufficient bandwidth";
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf local-preference {
                   type int32;
                 }
                 leaf peer-id {
                   type ipaddr;
                 }
                 leaf path-id {
                   type string;
                 }
                 leaf gateway {
                   type string;
                   description "Sourcing gateway";
                 }
                 leaf rtrib-primary {
                   type string;
                   description "Primary routing table";
                 }
                 leaf rtrib-secondary {
                   type string;
                   description "Secondary routing table";
                 }
                 leaf indirect-nh-count {
                   type int32;
                   description "Number of indirect next hops";
                 }
                 leaf composite-nh-count {
                   type int32;
                   description "Number of composite next hops";
                 }
                 leaf helper-nhid {
                   type uint32;
                   description "Helper nexthop index";
                 }
                 leaf helper-refcount {
                   type int32;
                   description "Reference count of those needing helper route";
                 }
                 leaf backup-pe-group-name {
                   type string;
                   description "Name of the backup PE group";
                 }
                 leaf designated-forwarder {
                   type string;
                   description "Indicates if we are the designated forwarder for this route";
                 }
                 leaf rt-entry-opaque-data {
                   type string;
                   description "Opaque data associated with the route entry";
                 }
                 leaf rt-stats-id-grp-single-line {
                   type string;
                   description "Stats-id-group associated with the route entry";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf evpn-isid {
                   type int32;
                   description "ISID";
                 }
                 leaf rt-evpn-esi {
                   type string;
                   description "ESI";
                 }
                 leaf rt-evpn-bmac {
                   type string;
                   description "BMAC";
                 }
                 leaf active-tag {
                   type string;
                   description "Visual indication of active state of this route entry";
                 }
                 leaf protocol-name {
                   type string;
                 }
                 leaf preference {
                   type int32;
                   description "Preference for the route";
                 }
                 leaf preference2 {
                   type int32;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf snpa-count {
                     type int32;
                     description "Number of SNPAs in this route";
                   }
                   leaf snpa-length {
                     type int32;
                     description "Total length of the SNPAs, in bytes";
                   }
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                   container multicast-member-map-data {
                     description "Multicast member map";
                     leaf multicast-root-hash {
                       type int32;
                     }
                     leaf multicast-core-hash {
                       type int32;
                     }
                     leaf multicast-edge-hash {
                       type int32;
                     }
                     leaf multicast-member-map {
                       type string;
                     }
                   }
                   container layer3-multicast-data {
                     description "Layer3 multicast core key";
                     leaf layer3-multicast-corekey {
                       type int32;
                     }
                   }
                   container multicast-vsg-corekey-data {
                     description "Vsg multicast core key";
                     leaf multicast-vsg-corekey-key {
                       type int32;
                     }
                     leaf multicast-vsg-corekey-len {
                       type int32;
                     }
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container rtd-flow-dep {
                   leaf flow-dep-state {
                     type string;
                   }
                   leaf flow-origin {
                     type ipaddr;
                     description "Originator of the flow information";
                   }
                   leaf flow-next-as {
                     type uint32;
                     description "Neighbor AS of the flow information";
                   }
                   container flow-ucast-rt {
                     description "Unicast route used for resolution";
                   }
                 }
                 container communities {
                   leaf community {
                     type string;
                     description "Basic community";
                   }
                   leaf extended-community {
                     type string;
                     description "Extended community";
                   }
                 }
                 container attrset {
                 }
                 container route-flap-damping {
                   leaf last-merit {
                     type int32;
                     description "Last merit value";
                   }
                   leaf merit {
                     type int32;
                     description "Current merit value";
                   }
                   leaf damping-parameters {
                     type string;
                   }
                   leaf default-damping-parameters {
                     type empty;
                     description "Default damping parameters used";
                   }
                   leaf last-update {
                     type string;
                   }
                   leaf first-update {
                     type string;
                   }
                   leaf route-flap-count {
                     type int32;
                     description "Number of times this route has flapped";
                   }
                   leaf suppressed {
                     type empty;
                     description "This route is suppressed";
                   }
                   leaf reuse-time {
                     type string;
                     description "Time until this route is reusable";
                   }
                   leaf reuse-preference {
                     type int32;
                     description "Preference to use when this route is reused";
                   }
                   leaf expire-time {
                     type string;
                     description "Time when this damping entry expires";
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                   leaf aggregate-flags {
                     type string;
                     description "Flags on this aggregate route entry";
                   }
                   leaf aggregate-depth {
                     type int32;
                     description "Depth of this aggregate";
                   }
                   leaf aggregate-active {
                     type empty;
                     description "Present if this aggregate is active";
                   }
                   leaf contributing-route-count {
                     type int32;
                     description "Number of contributing routes in this aggregate";
                   }
                   container aggregate-as-path {
                     leaf as-path {
                       type string;
                     }
                     leaf reference-count {
                       type int32;
                     }
                   }
                   container aggregated-route {
                     leaf destination-prefix {
                       type string;
                       description "Destination prefix and mask";
                     }
                     leaf protocol-name {
                       type string;
                     }
                   }
                 }
                 container nhh {
                   leaf nh-type {
                     type string;
                     description "Special next hop: Reject, Blackhole, Receive, Multicast, Local, or Unused";
                   }
                   leaf nh-index {
                     type uint32;
                     description "Next-hop index";
                   }
                   leaf nh-address {
                     type int32;
                     description "Address of next hop";
                   }
                   leaf nh-reference-count {
                     type int32;
                     description "Number of references to this next hop";
                   }
                   leaf ext-int-intf-index {
                     type int32;
                     description "Interface index of equal-external-internal multipath";
                   }
                   leaf nh-flood-overflow {
                     type empty;
                     description "Flood nexthop exceeds maximum branches";
                   }
                 }
                 container nh {
                   description "Next-hop gateway information";
                   leaf nh-string {
                     type string;
                   }
                   leaf elnh-address {
                     type int32;
                     description "Address of Element Next-hop";
                   }
                   leaf to {
                     type string;
                     description "Neighbor address to which to send (next-hop address)";
                   }
                   leaf via {
                     type string;
                     description "Reachable via a local interface";
                   }
                   leaf localized-table {
                     type string;
                     description "Name of localized table";
                   }
                   leaf weight {
                     type int32;
                     description "Next-hop weight";
                   }
                   leaf balance {
                     type int32;
                     description "Next-hop balance";
                   }
                   leaf uflags {
                     type int32;
                     description "Next-hop uflags";
                   }
                   leaf filter {
                     type string;
                     description "Next-hop firewall filter";
                   }
                   leaf selected-next-hop {
                     type empty;
                     description "Present if this next hop is selected";
                   }
                   leaf session {
                     type int32;
                     description "Session ID Associated with this NH";
                   }
                   leaf statistics-id-group-terse {
                     type string;
                     description "Statistics ID Group Associated with this NH";
                   }
                   leaf ext-int-type {
                     type string;
                     description "Next-hop type of equal-external-internal multipath";
                   }
                   leaf fc {
                     type int32;
                     description "Forwarding-class";
                   }
                   leaf lsp-name {
                     type string;
                     description "Tunneled into an RSVP LSP";
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf label-element {
                     type string;
                     description "Pointer to the tag label element";
                   }
                   leaf label-element-parent {
                     type string;
                     description "Pointer to the tag label element parent";
                   }
                   leaf label-element-refcount {
                     type string;
                     description "Number of references to the tag label element";
                   }
                   leaf label-element-childcount {
                     type string;
                     description "Number of child references to the tag label element";
                   }
                   leaf label-element-lspid {
                     type string;
                     description "LSP ID of the tag label element";
                   }
                   leaf nh-table-receive {
                     type string;
                     description "Destination is a local address";
                   }
                   leaf nh-table {
                     type string;
                     description "Indirect pointing to another table";
                   }
                   leaf nh-localized-ifl {
                     type string;
                     description "Indirect pointing to a localized ifl";
                   }
                   leaf nh-local-interface {
                     type string;
                     description "Destination is a local interface";
                   }
                   leaf nh-service {
                     type string;
                     description "Next-hop service";
                   }
                   leaf nh-service-pkt-dist {
                     type string;
                     description "Multi services packet distribution type";
                   }
                   leaf nh-service-app-data {
                     type string;
                     description "Multi services application specific data";
                   }
                   leaf nh-private-comp {
                     type string;
                     description "Private Composite Next-hop";
                   }
                   leaf nh-index {
                     type uint32;
                     description "Next-hop index";
                   }
                   leaf nh-address {
                     type int32;
                     description "Address of next hop";
                   }
                 }
                 container protocol-nh {
                   description "Protocol next hop";
                   leaf to {
                     type string;
                     description "Neighbor address to which to send (next-hop address)";
                   }
                   leaf metric {
                     type int32;
                   }
                   leaf aigp {
                     type string;
                     description "AIGP";
                   }
                   leaf balance {
                     type int32;
                     description "Next-hop balance";
                   }
                   leaf flags {
                     type string;
                     description "Enabled trace flags";
                   }
                   leaf res-path-inode-flags {
                     type string;
                   }
                   leaf res-path-flags {
                     type string;
                   }
                   leaf res-path-fnh-link {
                     type string;
                   }
                   leaf res-path-inh-link {
                     type string;
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf composite-nh {
                     type string;
                   }
                   leaf vpnlabel-nh {
                     type string;
                   }
                   leaf indirect-nh {
                     type string;
                   }
                   leaf ext-int-type {
                     type string;
                     description "Next-hop type of equal-external-internal multipath";
                   }
                   leaf forwarding-nh-count {
                     type int32;
                     description "Number of indirect path forwarding next hops";
                   }
                   leaf nh-type {
                     type string;
                     description "Special next hop: Reject, Blackhole, Receive, Multicast, Local, or Unused";
                   }
                   container eth-header-rewrite {
                     description "Ethernet header rewrite information";
                     leaf eth-header-rewrite-smac {
                       type string;
                       description "Source MAC address";
                     }
                     leaf eth-header-rewrite-dmac {
                       type string;
                       description "Destination MAC address";
                     }
                     leaf eth-header-rewrite-tpid {
                       type int32;
                       description "Ethernet header TPID";
                     }
                     leaf eth-header-rewrite-tci {
                       type int32;
                       description "Ethernet header TCI";
                     }
                     leaf eth-header-rewrite-vlan-id {
                       type int32;
                       description "Ethernet header VLAN ID";
                     }
                     leaf eth-header-rewrite-ethertype {
                       type int32;
                       description "Ethernet header ethertype";
                     }
                   }
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-detail {
               leaf rt-destination {
                 type string;
               }
               leaf rt-prefix-length {
                 type int32;
               }
               leaf rt-entry-count {
                 type int32;
                 description "Number of route entries in this route";
               }
               leaf rt-announced-count {
                 type int32;
                 description "Number of announced route entries";
               }
               container rt-entry {
                 leaf bgp-group-name {
                   type string;
                 }
                 leaf bgp-rt-flag {
                   type string;
                   description "BGP route flag";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf l2vpn-mesh-group {
                   type string;
                 }
                 leaf route-distinguisher {
                   type string;
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf bgp-no-label-reason {
                   type string;
                 }
                 leaf bgp-metric-flags {
                   type string;
                   description "BGP metrics flags";
                 }
                 leaf med {
                   type int32;
                   description "Multiple exit discriminator";
                 }
                 leaf local-preference {
                   type int32;
                 }
                 leaf bgp-output-queue-class {
                   type string;
                   description "BGP output queue class";
                 }
                 leaf as-path {
                   type string;
                 }
                 leaf pmsi {
                   type string;
                   description "P-multicast service interface";
                 }
                 leaf cluster-id {
                   type string;
                 }
                 leaf originator {
                   type string;
                 }
                 leaf connector {
                   type string;
                 }
                 leaf path-id {
                   type string;
                 }
                 leaf bgp-aigp {
                   type string;
                   description "Accumulated IGP Metric";
                 }
                 leaf bgp-elc {
                   type empty;
                   description "Entropy label capable";
                 }
                 leaf bgp-elc-nh-valid {
                   type string;
                   description "Whether next hop field matches route next hop";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf active-tag {
                   type string;
                   description "Visual indication of active state of this route entry";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                   leaf attrset-as {
                     type int32;
                     description "Originator AS";
                   }
                   leaf med {
                     type int32;
                     description "Multiple exit discriminator";
                   }
                   leaf local-preference {
                     type int32;
                   }
                   leaf as-path {
                     type string;
                   }
                   leaf pmsi {
                     type string;
                     description "P-multicast service interface";
                   }
                   leaf cluster-id {
                     type string;
                   }
                   leaf originator {
                     type string;
                   }
                   leaf connector {
                     type string;
                   }
                   container communities {
                     leaf community {
                       type string;
                       description "Basic community";
                     }
                     leaf extended-community {
                       type string;
                       description "Extended community";
                     }
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                   leaf to {
                     type string;
                     description "Neighbor address to which to send (next-hop address)";
                   }
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
               container communities {
                 leaf community {
                   type string;
                   description "Basic community";
                 }
                 leaf extended-community {
                   type string;
                   description "Extended community";
                 }
               }
             }
           }
         }
         container rt-martians {
           container route-filter {
             description "Entries in martian table";
             leaf address {
               type ipaddr;
             }
             leaf flags {
               type string;
               description "Enabled trace flags";
             }
             leaf extended-information {
               type string;
             }
             leaf match-count {
               type uint64;
             }
           }
         }
         container rt-ribgroup {
           leaf rt-ribgroup-name {
             type string;
             description "Rib-group name";
           }
           leaf rt-ribgroup-address {
             type string;
             description "Rib-group address";
           }
           leaf rt-ribgroup-address-family {
             type string;
             description "Rib-group address family";
           }
           leaf rt-ribgroup-flags {
             type string;
             description "Rib-group flags";
           }
           leaf rt-ribgroup-refcount {
             type uint32;
             description "Rib-group refcount";
           }
           leaf rt-ribgroup-export-name {
             type string;
             description "Export RIB name";
           }
           leaf rt-ribgroup-import-name {
             type string;
             description "Import RIB name";
           }
           leaf rt-ribgroup-import-policy-name {
             type string;
             description "Import policy name";
           }
           leaf rt-ribgroup-import-secondary-name {
             type string;
             description "Import secondary RIB name";
           }
           leaf rt-ribgroup-union-head-name {
             type string;
             description "Rib-group union head name";
           }
           leaf rt-ribgroup-union-child-name {
             type string;
             description "Rib-group union child name";
           }
         }
         container rt-test-policy-prefix {
           leaf rt-policy-name {
             type string;
           }
           leaf rt-destination {
             type string;
           }
           leaf rt-prefix-length {
             type int32;
           }
           container rt-test-policy-term {
             leaf rt-policy-term-name {
               type string;
             }
             leaf rt-policy-term-result {
               type string;
             }
             leaf rt-policy-term-action {
               type string;
             }
           }
         }
         container rt-test-policy {
           leaf rt-policy-name {
             type string;
           }
           leaf rt-route-accepted {
             type int32;
           }
           leaf rt-route-rejected {
             type int32;
           }
         }
       }
     }
   }
   rpc get-route-snooping-information {
     description "Show routes for multicast snooping";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf destination {
         description "IP address and optional prefix length of destination";
         type ipprefix-optional;
       }
       leaf all {
         description "Show all entries, including hidden entries";
         type empty;
       }
       leaf level {
         type enumeration {
           enum "terse" {
             description "Display terse output";
           }
           enum "brief" {
             description "Display brief output";
           }
           enum "detail" {
             description "Display detailed output";
           }
           enum "extensive" {
             description "Display extensive output";
           }
         }
       }
       leaf match {
         type enumeration {
           enum "best" {
             description "Show longest matching route";
           }
           enum "exact" {
             description "Show routes that match exactly";
           }
           enum "range" {
             description "Show all entries in prefix range";
           }
         }
       }
       leaf table {
         description "Name of routing table";
         type string;
       }
     }
     output {
       container route-information {
         leaf as-number {
           type int32;
         }
         leaf router-id {
           type ipaddr;
         }
         leaf maximum-ecmp {
           type int32;
         }
         leaf note-network-services-mode {
           type string;
         }
         container route-table {
           leaf table-name {
             type string;
             description "Unicast routing table";
           }
           leaf destination-count {
             type int32;
             description "Number of destinations in this rib";
           }
           leaf total-route-count {
             type int32;
           }
           leaf active-route-count {
             type int32;
             description "Active routes";
           }
           leaf holddown-route-count {
             type int32;
           }
           leaf hidden-route-count {
             type int32;
           }
           leaf restart-state {
             type string;
           }
           leaf prefix-max {
             type int32;
           }
           leaf prefix-threshold {
             type int32;
           }
           leaf prefix-label {
             type string;
           }
           leaf route-max {
             type int32;
           }
           leaf route-threshold {
             type int32;
           }
           leaf route-limit-label {
             type string;
           }
           container protocols {
             leaf protocol-name {
               type string;
             }
             leaf protocol-route-count {
               type int32;
               description "Total protocol routes";
             }
           }
           container rt {
             container terse {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container terse-mpls-fwd {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief-mpls-fwd {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-brief {
               leaf rt-destination {
                 type string;
               }
               leaf rt-prefix-length {
                 type int32;
               }
               container rt-entry {
                 leaf active-tag {
                   type string;
                   description "Visual indication of active state of this route entry";
                 }
                 leaf med {
                   type int32;
                   description "Multiple exit discriminator";
                 }
                 leaf local-preference {
                   type int32;
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container detail {
               leaf rt-destination {
                 type string;
               }
               leaf rt-prefix-length {
                 type int32;
               }
               leaf rt-entry-count {
                 type int32;
                 description "Number of route entries in this route";
               }
               leaf rt-announced-count {
                 type int32;
                 description "Number of announced route entries";
               }
               leaf rt-state {
                 type string;
                 description "State of this route";
               }
               leaf tsi {
                 type string;
                 description "Task-specific information";
               }
               container rt-entry {
                 leaf nh-type {
                   type string;
                   description "Special next hop: Reject, Blackhole, Receive, Multicast, Local, or Unused";
                 }
                 leaf nh-index {
                   type uint32;
                   description "Next-hop index";
                 }
                 leaf nh-address {
                   type int32;
                   description "Address of next hop";
                 }
                 leaf nh-reference-count {
                   type int32;
                   description "Number of references to this next hop";
                 }
                 leaf ext-int-intf-index {
                   type int32;
                   description "Interface index of equal-external-internal multipath";
                 }
                 leaf nh-flood-overflow {
                   type empty;
                   description "Flood nexthop exceeds maximum branches";
                 }
                 leaf client-data {
                   type string;
                   description "Route server client details";
                 }
                 leaf route-distinguisher {
                   type string;
                 }
                 leaf validation-state {
                   type string;
                 }
                 leaf pmsi {
                   type string;
                   description "P-multicast service interface";
                 }
                 leaf connector {
                   type string;
                 }
                 leaf color {
                   type int32;
                 }
                 leaf color2 {
                   type int32;
                 }
                 leaf rt-isis-level {
                   type int32;
                 }
                 leaf rt-isis-downbit {
                   type int32;
                 }
                 leaf rt-entry-state {
                   type string;
                   description "State of this route entry";
                 }
                 leaf rt-entry-pim-state {
                   type string;
                   description "PIM state of this route entry";
                 }
                 leaf inactive-reason {
                   type string;
                   description "HFRR profile Inactive reason (if any)";
                 }
                 leaf local-as {
                   type int32;
                   description "Local AS number";
                 }
                 leaf peer-as {
                   type int32;
                   description "Peer AS number";
                 }
                 leaf learned-from {
                   type ipaddr;
                   description "Peer address from which this route was learned";
                 }
                 leaf age {
                   type string;
                 }
                 leaf metric {
                   type int32;
                 }
                 leaf metric2 {
                   type int32;
                 }
                 leaf med-plus-igp {
                   type int32;
                 }
                 leaf rt-tag {
                   type int32;
                 }
                 leaf rt-tag2 {
                   type int32;
                 }
                 leaf rt-aigp {
                   type uint64;
                 }
                 leaf rt-resolving-aigp {
                   type uint64;
                 }
                 leaf rt-orr {
                   type uint32;
                 }
                 leaf rt-ospf-area {
                   type string;
                 }
                 leaf task-name {
                   type string;
                   description "Name of this task";
                 }
                 leaf announce-bits {
                   type int32;
                 }
                 leaf announce-tasks {
                   type string;
                 }
                 leaf as-path {
                   type string;
                 }
                 leaf bgp-rt-flag {
                   type string;
                   description "BGP route flag";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf remote-site {
                   type int32;
                   description "Remote site id";
                 }
                 leaf l2vpn-mesh-group {
                   type string;
                 }
                 leaf vc-label {
                   type int32;
                   description "VC label";
                 }
                 leaf context-id {
                   type ipaddr;
                   description "Context Identifier";
                 }
                 leaf route-control-word {
                   type string;
                   description "Control Word";
                 }
                 leaf mtu {
                   type int32;
                   description "MTU along an interface";
                 }
                 leaf cell-bundle-size {
                   type int32;
                   description "Cell bundle size";
                 }
                 leaf vlan-id {
                   type int32;
                 }
                 leaf flow-label-transmit {
                   type int32;
                 }
                 leaf flow-label-receive {
                   type int32;
                 }
                 leaf tdm-payload-size {
                   type int32;
                 }
                 leaf tdm-bitrate {
                   type int32;
                 }
                 leaf pw-status-code {
                   type int32;
                 }
                 leaf cac-bandwidth-failure {
                   type empty;
                   description "Call admission control failure due to insufficient bandwidth";
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf local-preference {
                   type int32;
                 }
                 leaf peer-id {
                   type ipaddr;
                 }
                 leaf path-id {
                   type string;
                 }
                 leaf gateway {
                   type string;
                   description "Sourcing gateway";
                 }
                 leaf rtrib-primary {
                   type string;
                   description "Primary routing table";
                 }
                 leaf rtrib-secondary {
                   type string;
                   description "Secondary routing table";
                 }
                 leaf indirect-nh-count {
                   type int32;
                   description "Number of indirect next hops";
                 }
                 leaf composite-nh-count {
                   type int32;
                   description "Number of composite next hops";
                 }
                 leaf helper-nhid {
                   type uint32;
                   description "Helper nexthop index";
                 }
                 leaf helper-refcount {
                   type int32;
                   description "Reference count of those needing helper route";
                 }
                 leaf backup-pe-group-name {
                   type string;
                   description "Name of the backup PE group";
                 }
                 leaf designated-forwarder {
                   type string;
                   description "Indicates if we are the designated forwarder for this route";
                 }
                 leaf rt-entry-opaque-data {
                   type string;
                   description "Opaque data associated with the route entry";
                 }
                 leaf rt-stats-id-grp-single-line {
                   type string;
                   description "Stats-id-group associated with the route entry";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf evpn-isid {
                   type int32;
                   description "ISID";
                 }
                 leaf rt-evpn-esi {
                   type string;
                   description "ESI";
                 }
                 leaf rt-evpn-bmac {
                   type string;
                   description "BMAC";
                 }
                 leaf active-tag {
                   type string;
                   description "Visual indication of active state of this route entry";
                 }
                 leaf protocol-name {
                   type string;
                 }
                 leaf preference {
                   type int32;
                   description "Preference for the route";
                 }
                 leaf preference2 {
                   type int32;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf snpa-count {
                     type int32;
                     description "Number of SNPAs in this route";
                   }
                   leaf snpa-length {
                     type int32;
                     description "Total length of the SNPAs, in bytes";
                   }
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                   container multicast-member-map-data {
                     description "Multicast member map";
                     leaf multicast-root-hash {
                       type int32;
                     }
                     leaf multicast-core-hash {
                       type int32;
                     }
                     leaf multicast-edge-hash {
                       type int32;
                     }
                     leaf multicast-member-map {
                       type string;
                     }
                   }
                   container layer3-multicast-data {
                     description "Layer3 multicast core key";
                     leaf layer3-multicast-corekey {
                       type int32;
                     }
                   }
                   container multicast-vsg-corekey-data {
                     description "Vsg multicast core key";
                     leaf multicast-vsg-corekey-key {
                       type int32;
                     }
                     leaf multicast-vsg-corekey-len {
                       type int32;
                     }
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container rtd-flow-dep {
                   leaf flow-dep-state {
                     type string;
                   }
                   leaf flow-origin {
                     type ipaddr;
                     description "Originator of the flow information";
                   }
                   leaf flow-next-as {
                     type uint32;
                     description "Neighbor AS of the flow information";
                   }
                   container flow-ucast-rt {
                     description "Unicast route used for resolution";
                   }
                 }
                 container communities {
                   leaf community {
                     type string;
                     description "Basic community";
                   }
                   leaf extended-community {
                     type string;
                     description "Extended community";
                   }
                 }
                 container attrset {
                 }
                 container route-flap-damping {
                   leaf last-merit {
                     type int32;
                     description "Last merit value";
                   }
                   leaf merit {
                     type int32;
                     description "Current merit value";
                   }
                   leaf damping-parameters {
                     type string;
                   }
                   leaf default-damping-parameters {
                     type empty;
                     description "Default damping parameters used";
                   }
                   leaf last-update {
                     type string;
                   }
                   leaf first-update {
                     type string;
                   }
                   leaf route-flap-count {
                     type int32;
                     description "Number of times this route has flapped";
                   }
                   leaf suppressed {
                     type empty;
                     description "This route is suppressed";
                   }
                   leaf reuse-time {
                     type string;
                     description "Time until this route is reusable";
                   }
                   leaf reuse-preference {
                     type int32;
                     description "Preference to use when this route is reused";
                   }
                   leaf expire-time {
                     type string;
                     description "Time when this damping entry expires";
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                   leaf aggregate-flags {
                     type string;
                     description "Flags on this aggregate route entry";
                   }
                   leaf aggregate-depth {
                     type int32;
                     description "Depth of this aggregate";
                   }
                   leaf aggregate-active {
                     type empty;
                     description "Present if this aggregate is active";
                   }
                   leaf contributing-route-count {
                     type int32;
                     description "Number of contributing routes in this aggregate";
                   }
                   container aggregate-as-path {
                     leaf as-path {
                       type string;
                     }
                     leaf reference-count {
                       type int32;
                     }
                   }
                   container aggregated-route {
                     leaf destination-prefix {
                       type string;
                       description "Destination prefix and mask";
                     }
                     leaf protocol-name {
                       type string;
                     }
                   }
                 }
                 container nhh {
                   leaf nh-type {
                     type string;
                     description "Special next hop: Reject, Blackhole, Receive, Multicast, Local, or Unused";
                   }
                   leaf nh-index {
                     type uint32;
                     description "Next-hop index";
                   }
                   leaf nh-address {
                     type int32;
                     description "Address of next hop";
                   }
                   leaf nh-reference-count {
                     type int32;
                     description "Number of references to this next hop";
                   }
                   leaf ext-int-intf-index {
                     type int32;
                     description "Interface index of equal-external-internal multipath";
                   }
                   leaf nh-flood-overflow {
                     type empty;
                     description "Flood nexthop exceeds maximum branches";
                   }
                 }
                 container nh {
                   description "Next-hop gateway information";
                   leaf nh-string {
                     type string;
                   }
                   leaf elnh-address {
                     type int32;
                     description "Address of Element Next-hop";
                   }
                   leaf to {
                     type string;
                     description "Neighbor address to which to send (next-hop address)";
                   }
                   leaf via {
                     type string;
                     description "Reachable via a local interface";
                   }
                   leaf localized-table {
                     type string;
                     description "Name of localized table";
                   }
                   leaf weight {
                     type int32;
                     description "Next-hop weight";
                   }
                   leaf balance {
                     type int32;
                     description "Next-hop balance";
                   }
                   leaf uflags {
                     type int32;
                     description "Next-hop uflags";
                   }
                   leaf filter {
                     type string;
                     description "Next-hop firewall filter";
                   }
                   leaf selected-next-hop {
                     type empty;
                     description "Present if this next hop is selected";
                   }
                   leaf session {
                     type int32;
                     description "Session ID Associated with this NH";
                   }
                   leaf statistics-id-group-terse {
                     type string;
                     description "Statistics ID Group Associated with this NH";
                   }
                   leaf ext-int-type {
                     type string;
                     description "Next-hop type of equal-external-internal multipath";
                   }
                   leaf fc {
                     type int32;
                     description "Forwarding-class";
                   }
                   leaf lsp-name {
                     type string;
                     description "Tunneled into an RSVP LSP";
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf label-element {
                     type string;
                     description "Pointer to the tag label element";
                   }
                   leaf label-element-parent {
                     type string;
                     description "Pointer to the tag label element parent";
                   }
                   leaf label-element-refcount {
                     type string;
                     description "Number of references to the tag label element";
                   }
                   leaf label-element-childcount {
                     type string;
                     description "Number of child references to the tag label element";
                   }
                   leaf label-element-lspid {
                     type string;
                     description "LSP ID of the tag label element";
                   }
                   leaf nh-table-receive {
                     type string;
                     description "Destination is a local address";
                   }
                   leaf nh-table {
                     type string;
                     description "Indirect pointing to another table";
                   }
                   leaf nh-localized-ifl {
                     type string;
                     description "Indirect pointing to a localized ifl";
                   }
                   leaf nh-local-interface {
                     type string;
                     description "Destination is a local interface";
                   }
                   leaf nh-service {
                     type string;
                     description "Next-hop service";
                   }
                   leaf nh-service-pkt-dist {
                     type string;
                     description "Multi services packet distribution type";
                   }
                   leaf nh-service-app-data {
                     type string;
                     description "Multi services application specific data";
                   }
                   leaf nh-private-comp {
                     type string;
                     description "Private Composite Next-hop";
                   }
                   leaf nh-index {
                     type uint32;
                     description "Next-hop index";
                   }
                   leaf nh-address {
                     type int32;
                     description "Address of next hop";
                   }
                 }
                 container protocol-nh {
                   description "Protocol next hop";
                   leaf to {
                     type string;
                     description "Neighbor address to which to send (next-hop address)";
                   }
                   leaf metric {
                     type int32;
                   }
                   leaf aigp {
                     type string;
                     description "AIGP";
                   }
                   leaf balance {
                     type int32;
                     description "Next-hop balance";
                   }
                   leaf flags {
                     type string;
                     description "Enabled trace flags";
                   }
                   leaf res-path-inode-flags {
                     type string;
                   }
                   leaf res-path-flags {
                     type string;
                   }
                   leaf res-path-fnh-link {
                     type string;
                   }
                   leaf res-path-inh-link {
                     type string;
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf composite-nh {
                     type string;
                   }
                   leaf vpnlabel-nh {
                     type string;
                   }
                   leaf indirect-nh {
                     type string;
                   }
                   leaf ext-int-type {
                     type string;
                     description "Next-hop type of equal-external-internal multipath";
                   }
                   leaf forwarding-nh-count {
                     type int32;
                     description "Number of indirect path forwarding next hops";
                   }
                   leaf nh-type {
                     type string;
                     description "Special next hop: Reject, Blackhole, Receive, Multicast, Local, or Unused";
                   }
                   container eth-header-rewrite {
                     description "Ethernet header rewrite information";
                     leaf eth-header-rewrite-smac {
                       type string;
                       description "Source MAC address";
                     }
                     leaf eth-header-rewrite-dmac {
                       type string;
                       description "Destination MAC address";
                     }
                     leaf eth-header-rewrite-tpid {
                       type int32;
                       description "Ethernet header TPID";
                     }
                     leaf eth-header-rewrite-tci {
                       type int32;
                       description "Ethernet header TCI";
                     }
                     leaf eth-header-rewrite-vlan-id {
                       type int32;
                       description "Ethernet header VLAN ID";
                     }
                     leaf eth-header-rewrite-ethertype {
                       type int32;
                       description "Ethernet header ethertype";
                     }
                   }
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-detail {
               leaf rt-destination {
                 type string;
               }
               leaf rt-prefix-length {
                 type int32;
               }
               leaf rt-entry-count {
                 type int32;
                 description "Number of route entries in this route";
               }
               leaf rt-announced-count {
                 type int32;
                 description "Number of announced route entries";
               }
               container rt-entry {
                 leaf bgp-group-name {
                   type string;
                 }
                 leaf bgp-rt-flag {
                   type string;
                   description "BGP route flag";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf l2vpn-mesh-group {
                   type string;
                 }
                 leaf route-distinguisher {
                   type string;
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf bgp-no-label-reason {
                   type string;
                 }
                 leaf bgp-metric-flags {
                   type string;
                   description "BGP metrics flags";
                 }
                 leaf med {
                   type int32;
                   description "Multiple exit discriminator";
                 }
                 leaf local-preference {
                   type int32;
                 }
                 leaf bgp-output-queue-class {
                   type string;
                   description "BGP output queue class";
                 }
                 leaf as-path {
                   type string;
                 }
                 leaf pmsi {
                   type string;
                   description "P-multicast service interface";
                 }
                 leaf cluster-id {
                   type string;
                 }
                 leaf originator {
                   type string;
                 }
                 leaf connector {
                   type string;
                 }
                 leaf path-id {
                   type string;
                 }
                 leaf bgp-aigp {
                   type string;
                   description "Accumulated IGP Metric";
                 }
                 leaf bgp-elc {
                   type empty;
                   description "Entropy label capable";
                 }
                 leaf bgp-elc-nh-valid {
                   type string;
                   description "Whether next hop field matches route next hop";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf active-tag {
                   type string;
                   description "Visual indication of active state of this route entry";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                   leaf attrset-as {
                     type int32;
                     description "Originator AS";
                   }
                   leaf med {
                     type int32;
                     description "Multiple exit discriminator";
                   }
                   leaf local-preference {
                     type int32;
                   }
                   leaf as-path {
                     type string;
                   }
                   leaf pmsi {
                     type string;
                     description "P-multicast service interface";
                   }
                   leaf cluster-id {
                     type string;
                   }
                   leaf originator {
                     type string;
                   }
                   leaf connector {
                     type string;
                   }
                   container communities {
                     leaf community {
                       type string;
                       description "Basic community";
                     }
                     leaf extended-community {
                       type string;
                       description "Extended community";
                     }
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                   leaf to {
                     type string;
                     description "Neighbor address to which to send (next-hop address)";
                   }
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
               container communities {
                 leaf community {
                   type string;
                   description "Basic community";
                 }
                 leaf extended-community {
                   type string;
                   description "Extended community";
                 }
               }
             }
           }
         }
         container rt-martians {
           container route-filter {
             description "Entries in martian table";
             leaf address {
               type ipaddr;
             }
             leaf flags {
               type string;
               description "Enabled trace flags";
             }
             leaf extended-information {
               type string;
             }
             leaf match-count {
               type uint64;
             }
           }
         }
         container rt-ribgroup {
           leaf rt-ribgroup-name {
             type string;
             description "Rib-group name";
           }
           leaf rt-ribgroup-address {
             type string;
             description "Rib-group address";
           }
           leaf rt-ribgroup-address-family {
             type string;
             description "Rib-group address family";
           }
           leaf rt-ribgroup-flags {
             type string;
             description "Rib-group flags";
           }
           leaf rt-ribgroup-refcount {
             type uint32;
             description "Rib-group refcount";
           }
           leaf rt-ribgroup-export-name {
             type string;
             description "Export RIB name";
           }
           leaf rt-ribgroup-import-name {
             type string;
             description "Import RIB name";
           }
           leaf rt-ribgroup-import-policy-name {
             type string;
             description "Import policy name";
           }
           leaf rt-ribgroup-import-secondary-name {
             type string;
             description "Import secondary RIB name";
           }
           leaf rt-ribgroup-union-head-name {
             type string;
             description "Rib-group union head name";
           }
           leaf rt-ribgroup-union-child-name {
             type string;
             description "Rib-group union child name";
           }
         }
         container rt-test-policy-prefix {
           leaf rt-policy-name {
             type string;
           }
           leaf rt-destination {
             type string;
           }
           leaf rt-prefix-length {
             type int32;
           }
           container rt-test-policy-term {
             leaf rt-policy-term-name {
               type string;
             }
             leaf rt-policy-term-result {
               type string;
             }
             leaf rt-policy-term-action {
               type string;
             }
           }
         }
         container rt-test-policy {
           leaf rt-policy-name {
             type string;
           }
           leaf rt-route-accepted {
             type int32;
           }
           leaf rt-route-rejected {
             type int32;
           }
         }
       }
     }
   }
   rpc get-route-snooping-summary {
     description "Show routing table statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container route-summary-information {
         leaf as-number {
           type int32;
         }
         leaf router-id {
           type ipaddr;
         }
         leaf maximum-ecmp {
           type int32;
         }
         leaf note-network-services-mode {
           type string;
         }
         container route-table {
           leaf table-name {
             type string;
             description "Unicast routing table";
           }
           leaf destination-count {
             type int32;
             description "Number of destinations in this rib";
           }
           leaf total-route-count {
             type int32;
           }
           leaf active-route-count {
             type int32;
             description "Active routes";
           }
           leaf holddown-route-count {
             type int32;
           }
           leaf hidden-route-count {
             type int32;
           }
           leaf restart-state {
             type string;
           }
           leaf prefix-max {
             type int32;
           }
           leaf prefix-threshold {
             type int32;
           }
           leaf prefix-label {
             type string;
           }
           leaf route-max {
             type int32;
           }
           leaf route-threshold {
             type int32;
           }
           leaf route-limit-label {
             type string;
           }
           container protocols {
             leaf protocol-name {
               type string;
             }
             leaf protocol-route-count {
               type int32;
               description "Total protocol routes";
             }
           }
           container rt {
             container terse {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container terse-mpls-fwd {
               leaf rt-destination {
                 type string;
               }
               leaf rt-prefix-length {
                 type int32;
               }
               container rt-entry {
                 leaf active-tag {
                   type string;
                   description "Visual indication of active state of this route entry";
                 }
                 leaf validation-state {
                   type string;
                 }
                 leaf protocol-name {
                   type string;
                 }
                 leaf preference {
                   type int32;
                   description "Preference for the route";
                 }
                 leaf metric {
                   type int32;
                 }
                 leaf metric2 {
                   type int32;
                 }
                 leaf nh-type {
                   type string;
                   description "Special next hop: Reject, Blackhole, Receive, Multicast, Local, or Unused";
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container brief-mpls-fwd {
               leaf rt-destination {
                 type string;
               }
               leaf rt-prefix-length {
                 type int32;
               }
               container rt-entry {
                 leaf active-tag {
                   type string;
                   description "Visual indication of active state of this route entry";
                 }
                 leaf protocol-name {
                   type string;
                 }
                 leaf preference {
                   type int32;
                   description "Preference for the route";
                 }
                 leaf preference2 {
                   type int32;
                 }
                 leaf age {
                   type string;
                 }
                 leaf metric {
                   type int32;
                 }
                 leaf med {
                   type int32;
                   description "Multiple exit discriminator";
                 }
                 leaf local-preference {
                   type int32;
                 }
                 leaf metric2 {
                   type int32;
                 }
                 leaf rt-tag {
                   type int32;
                 }
                 leaf rt-tag2 {
                   type int32;
                 }
                 leaf learned-from {
                   type ipaddr;
                   description "Peer address from which this route was learned";
                 }
                 leaf peer-as {
                   type int32;
                   description "Peer AS number";
                 }
                 leaf evpn-remote-mes {
                   type ipaddr;
                   description "Remote PE";
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf rt-evpn-esi {
                   type string;
                   description "ESI";
                 }
                 leaf evpn-isid {
                   type int32;
                   description "ISID";
                 }
                 leaf rt-evpn-bmac {
                   type string;
                   description "BMAC";
                 }
                 leaf as-path {
                   type string;
                 }
                 leaf validation-state {
                   type string;
                 }
                 leaf nh-type {
                   type string;
                   description "Special next hop: Reject, Blackhole, Receive, Multicast, Local, or Unused";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-brief {
               leaf rt-destination {
                 type string;
               }
               leaf rt-prefix-length {
                 type int32;
               }
               container rt-entry {
                 leaf active-tag {
                   type string;
                   description "Visual indication of active state of this route entry";
                 }
                 leaf med {
                   type int32;
                   description "Multiple exit discriminator";
                 }
                 leaf local-preference {
                   type int32;
                 }
                 leaf as-path {
                   type string;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container detail {
               leaf rt-destination {
                 type string;
               }
               leaf rt-prefix-length {
                 type int32;
               }
               leaf rt-entry-count {
                 type int32;
                 description "Number of route entries in this route";
               }
               leaf rt-announced-count {
                 type int32;
                 description "Number of announced route entries";
               }
               leaf rt-state {
                 type string;
                 description "State of this route";
               }
               leaf tsi {
                 type string;
                 description "Task-specific information";
               }
               container rt-entry {
                 leaf nh-type {
                   type string;
                   description "Special next hop: Reject, Blackhole, Receive, Multicast, Local, or Unused";
                 }
                 leaf nh-index {
                   type uint32;
                   description "Next-hop index";
                 }
                 leaf nh-address {
                   type int32;
                   description "Address of next hop";
                 }
                 leaf nh-reference-count {
                   type int32;
                   description "Number of references to this next hop";
                 }
                 leaf ext-int-intf-index {
                   type int32;
                   description "Interface index of equal-external-internal multipath";
                 }
                 leaf nh-flood-overflow {
                   type empty;
                   description "Flood nexthop exceeds maximum branches";
                 }
                 leaf client-data {
                   type string;
                   description "Route server client details";
                 }
                 leaf route-distinguisher {
                   type string;
                 }
                 leaf validation-state {
                   type string;
                 }
                 leaf pmsi {
                   type string;
                   description "P-multicast service interface";
                 }
                 leaf connector {
                   type string;
                 }
                 leaf color {
                   type int32;
                 }
                 leaf color2 {
                   type int32;
                 }
                 leaf rt-isis-level {
                   type int32;
                 }
                 leaf rt-isis-downbit {
                   type int32;
                 }
                 leaf rt-entry-state {
                   type string;
                   description "State of this route entry";
                 }
                 leaf rt-entry-pim-state {
                   type string;
                   description "PIM state of this route entry";
                 }
                 leaf inactive-reason {
                   type string;
                   description "HFRR profile Inactive reason (if any)";
                 }
                 leaf local-as {
                   type int32;
                   description "Local AS number";
                 }
                 leaf peer-as {
                   type int32;
                   description "Peer AS number";
                 }
                 leaf learned-from {
                   type ipaddr;
                   description "Peer address from which this route was learned";
                 }
                 leaf age {
                   type string;
                 }
                 leaf metric {
                   type int32;
                 }
                 leaf metric2 {
                   type int32;
                 }
                 leaf med-plus-igp {
                   type int32;
                 }
                 leaf rt-tag {
                   type int32;
                 }
                 leaf rt-tag2 {
                   type int32;
                 }
                 leaf rt-aigp {
                   type uint64;
                 }
                 leaf rt-resolving-aigp {
                   type uint64;
                 }
                 leaf rt-orr {
                   type uint32;
                 }
                 leaf rt-ospf-area {
                   type string;
                 }
                 leaf task-name {
                   type string;
                   description "Name of this task";
                 }
                 leaf announce-bits {
                   type int32;
                 }
                 leaf announce-tasks {
                   type string;
                 }
                 leaf as-path {
                   type string;
                 }
                 leaf bgp-rt-flag {
                   type string;
                   description "BGP route flag";
                 }
                 leaf bgp-rtarget-type {
                   type string;
                   description "BGP RT-Constrain route type";
                 }
                 leaf bgp-rtarget-generation {
                   type uint32;
                   description "BGP RT-Constrain generation";
                 }
                 leaf bgp-rtarget-for {
                   type string;
                   description "BGP RT-Constrain member";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf remote-site {
                   type int32;
                   description "Remote site id";
                 }
                 leaf l2vpn-mesh-group {
                   type string;
                 }
                 leaf vc-label {
                   type int32;
                   description "VC label";
                 }
                 leaf context-id {
                   type ipaddr;
                   description "Context Identifier";
                 }
                 leaf route-control-word {
                   type string;
                   description "Control Word";
                 }
                 leaf mtu {
                   type int32;
                   description "MTU along an interface";
                 }
                 leaf cell-bundle-size {
                   type int32;
                   description "Cell bundle size";
                 }
                 leaf vlan-id {
                   type int32;
                 }
                 leaf flow-label-transmit {
                   type int32;
                 }
                 leaf flow-label-receive {
                   type int32;
                 }
                 leaf tdm-payload-size {
                   type int32;
                 }
                 leaf tdm-bitrate {
                   type int32;
                 }
                 leaf pw-status-code {
                   type int32;
                 }
                 leaf cac-bandwidth-failure {
                   type empty;
                   description "Call admission control failure due to insufficient bandwidth";
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf local-preference {
                   type int32;
                 }
                 leaf peer-id {
                   type ipaddr;
                 }
                 leaf path-id {
                   type string;
                 }
                 leaf gateway {
                   type string;
                   description "Sourcing gateway";
                 }
                 leaf rtrib-primary {
                   type string;
                   description "Primary routing table";
                 }
                 leaf rtrib-secondary {
                   type string;
                   description "Secondary routing table";
                 }
                 leaf indirect-nh-count {
                   type int32;
                   description "Number of indirect next hops";
                 }
                 leaf composite-nh-count {
                   type int32;
                   description "Number of composite next hops";
                 }
                 leaf helper-nhid {
                   type uint32;
                   description "Helper nexthop index";
                 }
                 leaf helper-refcount {
                   type int32;
                   description "Reference count of those needing helper route";
                 }
                 leaf backup-pe-group-name {
                   type string;
                   description "Name of the backup PE group";
                 }
                 leaf designated-forwarder {
                   type string;
                   description "Indicates if we are the designated forwarder for this route";
                 }
                 leaf rt-entry-opaque-data {
                   type string;
                   description "Opaque data associated with the route entry";
                 }
                 leaf rt-stats-id-grp-single-line {
                   type string;
                   description "Stats-id-group associated with the route entry";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf evpn-routing-instance-name {
                   type string;
                   description "Routing Instance";
                 }
                 leaf evpn-tag-rt-type {
                   type string;
                   description "Route Type";
                 }
                 leaf evpn-vlan-id {
                   type int32;
                   description "VLAN-ID";
                 }
                 leaf evpn-isid {
                   type int32;
                   description "ISID";
                 }
                 leaf rt-evpn-esi {
                   type string;
                   description "ESI";
                 }
                 leaf rt-evpn-bmac {
                   type string;
                   description "BMAC";
                 }
                 leaf active-tag {
                   type string;
                   description "Visual indication of active state of this route entry";
                 }
                 leaf protocol-name {
                   type string;
                 }
                 leaf preference {
                   type int32;
                   description "Preference for the route";
                 }
                 leaf preference2 {
                   type int32;
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf snpa-count {
                     type int32;
                     description "Number of SNPAs in this route";
                   }
                   leaf snpa-length {
                     type int32;
                     description "Total length of the SNPAs, in bytes";
                   }
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                   container multicast-member-map-data {
                     description "Multicast member map";
                     leaf multicast-root-hash {
                       type int32;
                     }
                     leaf multicast-core-hash {
                       type int32;
                     }
                     leaf multicast-edge-hash {
                       type int32;
                     }
                     leaf multicast-member-map {
                       type string;
                     }
                   }
                   container layer3-multicast-data {
                     description "Layer3 multicast core key";
                     leaf layer3-multicast-corekey {
                       type int32;
                     }
                   }
                   container multicast-vsg-corekey-data {
                     description "Vsg multicast core key";
                     leaf multicast-vsg-corekey-key {
                       type int32;
                     }
                     leaf multicast-vsg-corekey-len {
                       type int32;
                     }
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container rtd-flow-dep {
                   leaf flow-dep-state {
                     type string;
                   }
                   leaf flow-origin {
                     type ipaddr;
                     description "Originator of the flow information";
                   }
                   leaf flow-next-as {
                     type uint32;
                     description "Neighbor AS of the flow information";
                   }
                   container flow-ucast-rt {
                     description "Unicast route used for resolution";
                   }
                 }
                 container communities {
                   leaf community {
                     type string;
                     description "Basic community";
                   }
                   leaf extended-community {
                     type string;
                     description "Extended community";
                   }
                 }
                 container attrset {
                 }
                 container route-flap-damping {
                   leaf last-merit {
                     type int32;
                     description "Last merit value";
                   }
                   leaf merit {
                     type int32;
                     description "Current merit value";
                   }
                   leaf damping-parameters {
                     type string;
                   }
                   leaf default-damping-parameters {
                     type empty;
                     description "Default damping parameters used";
                   }
                   leaf last-update {
                     type string;
                   }
                   leaf first-update {
                     type string;
                   }
                   leaf route-flap-count {
                     type int32;
                     description "Number of times this route has flapped";
                   }
                   leaf suppressed {
                     type empty;
                     description "This route is suppressed";
                   }
                   leaf reuse-time {
                     type string;
                     description "Time until this route is reusable";
                   }
                   leaf reuse-preference {
                     type int32;
                     description "Preference to use when this route is reused";
                   }
                   leaf expire-time {
                     type string;
                     description "Time when this damping entry expires";
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                   leaf aggregate-flags {
                     type string;
                     description "Flags on this aggregate route entry";
                   }
                   leaf aggregate-depth {
                     type int32;
                     description "Depth of this aggregate";
                   }
                   leaf aggregate-active {
                     type empty;
                     description "Present if this aggregate is active";
                   }
                   leaf contributing-route-count {
                     type int32;
                     description "Number of contributing routes in this aggregate";
                   }
                   container aggregate-as-path {
                     leaf as-path {
                       type string;
                     }
                     leaf reference-count {
                       type int32;
                     }
                   }
                   container aggregated-route {
                     leaf destination-prefix {
                       type string;
                       description "Destination prefix and mask";
                     }
                     leaf protocol-name {
                       type string;
                     }
                   }
                 }
                 container nhh {
                   leaf nh-type {
                     type string;
                     description "Special next hop: Reject, Blackhole, Receive, Multicast, Local, or Unused";
                   }
                   leaf nh-index {
                     type uint32;
                     description "Next-hop index";
                   }
                   leaf nh-address {
                     type int32;
                     description "Address of next hop";
                   }
                   leaf nh-reference-count {
                     type int32;
                     description "Number of references to this next hop";
                   }
                   leaf ext-int-intf-index {
                     type int32;
                     description "Interface index of equal-external-internal multipath";
                   }
                   leaf nh-flood-overflow {
                     type empty;
                     description "Flood nexthop exceeds maximum branches";
                   }
                 }
                 container nh {
                   description "Next-hop gateway information";
                   leaf nh-string {
                     type string;
                   }
                   leaf elnh-address {
                     type int32;
                     description "Address of Element Next-hop";
                   }
                   leaf to {
                     type string;
                     description "Neighbor address to which to send (next-hop address)";
                   }
                   leaf via {
                     type string;
                     description "Reachable via a local interface";
                   }
                   leaf localized-table {
                     type string;
                     description "Name of localized table";
                   }
                   leaf weight {
                     type int32;
                     description "Next-hop weight";
                   }
                   leaf balance {
                     type int32;
                     description "Next-hop balance";
                   }
                   leaf uflags {
                     type int32;
                     description "Next-hop uflags";
                   }
                   leaf filter {
                     type string;
                     description "Next-hop firewall filter";
                   }
                   leaf selected-next-hop {
                     type empty;
                     description "Present if this next hop is selected";
                   }
                   leaf session {
                     type int32;
                     description "Session ID Associated with this NH";
                   }
                   leaf statistics-id-group-terse {
                     type string;
                     description "Statistics ID Group Associated with this NH";
                   }
                   leaf ext-int-type {
                     type string;
                     description "Next-hop type of equal-external-internal multipath";
                   }
                   leaf fc {
                     type int32;
                     description "Forwarding-class";
                   }
                   leaf lsp-name {
                     type string;
                     description "Tunneled into an RSVP LSP";
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf label-element {
                     type string;
                     description "Pointer to the tag label element";
                   }
                   leaf label-element-parent {
                     type string;
                     description "Pointer to the tag label element parent";
                   }
                   leaf label-element-refcount {
                     type string;
                     description "Number of references to the tag label element";
                   }
                   leaf label-element-childcount {
                     type string;
                     description "Number of child references to the tag label element";
                   }
                   leaf label-element-lspid {
                     type string;
                     description "LSP ID of the tag label element";
                   }
                   leaf nh-table-receive {
                     type string;
                     description "Destination is a local address";
                   }
                   leaf nh-table {
                     type string;
                     description "Indirect pointing to another table";
                   }
                   leaf nh-localized-ifl {
                     type string;
                     description "Indirect pointing to a localized ifl";
                   }
                   leaf nh-local-interface {
                     type string;
                     description "Destination is a local interface";
                   }
                   leaf nh-service {
                     type string;
                     description "Next-hop service";
                   }
                   leaf nh-service-pkt-dist {
                     type string;
                     description "Multi services packet distribution type";
                   }
                   leaf nh-service-app-data {
                     type string;
                     description "Multi services application specific data";
                   }
                   leaf nh-private-comp {
                     type string;
                     description "Private Composite Next-hop";
                   }
                   leaf nh-index {
                     type uint32;
                     description "Next-hop index";
                   }
                   leaf nh-address {
                     type int32;
                     description "Address of next hop";
                   }
                 }
                 container protocol-nh {
                   description "Protocol next hop";
                   leaf to {
                     type string;
                     description "Neighbor address to which to send (next-hop address)";
                   }
                   leaf metric {
                     type int32;
                   }
                   leaf aigp {
                     type string;
                     description "AIGP";
                   }
                   leaf balance {
                     type int32;
                     description "Next-hop balance";
                   }
                   leaf flags {
                     type string;
                     description "Enabled trace flags";
                   }
                   leaf res-path-inode-flags {
                     type string;
                   }
                   leaf res-path-flags {
                     type string;
                   }
                   leaf res-path-fnh-link {
                     type string;
                   }
                   leaf res-path-inh-link {
                     type string;
                   }
                   leaf mpls-label {
                     type string;
                     description "Label of MPLS packet";
                   }
                   leaf label-ttl-action {
                     type string;
                     description "TTL action associated with labels";
                   }
                   leaf load-balance-label {
                     type string;
                     description "Load balance action associated with labels";
                   }
                   leaf composite-nh {
                     type string;
                   }
                   leaf vpnlabel-nh {
                     type string;
                   }
                   leaf indirect-nh {
                     type string;
                   }
                   leaf ext-int-type {
                     type string;
                     description "Next-hop type of equal-external-internal multipath";
                   }
                   leaf forwarding-nh-count {
                     type int32;
                     description "Number of indirect path forwarding next hops";
                   }
                   leaf nh-type {
                     type string;
                     description "Special next hop: Reject, Blackhole, Receive, Multicast, Local, or Unused";
                   }
                   container eth-header-rewrite {
                     description "Ethernet header rewrite information";
                     leaf eth-header-rewrite-smac {
                       type string;
                       description "Source MAC address";
                     }
                     leaf eth-header-rewrite-dmac {
                       type string;
                       description "Destination MAC address";
                     }
                     leaf eth-header-rewrite-tpid {
                       type int32;
                       description "Ethernet header TPID";
                     }
                     leaf eth-header-rewrite-tci {
                       type int32;
                       description "Ethernet header TCI";
                     }
                     leaf eth-header-rewrite-vlan-id {
                       type int32;
                       description "Ethernet header VLAN ID";
                     }
                     leaf eth-header-rewrite-ethertype {
                       type int32;
                       description "Ethernet header ethertype";
                     }
                   }
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
             }
             container bgp-detail {
               leaf rt-destination {
                 type string;
               }
               leaf rt-prefix-length {
                 type int32;
               }
               leaf rt-entry-count {
                 type int32;
                 description "Number of route entries in this route";
               }
               leaf rt-announced-count {
                 type int32;
                 description "Number of announced route entries";
               }
               container rt-entry {
                 leaf bgp-group-name {
                   type string;
                 }
                 leaf bgp-rt-flag {
                   type string;
                   description "BGP route flag";
                 }
                 leaf label-base {
                   type int32;
                   description "Label base for l2vpn";
                 }
                 leaf label-range {
                   type int32;
                   description "Label range for l2vpn";
                 }
                 leaf l2vpn-status-vector {
                   type string;
                 }
                 leaf label-offset {
                   type int32;
                   description "Label offset for l2vpn";
                 }
                 leaf l2vpn-mesh-group {
                   type string;
                 }
                 leaf route-distinguisher {
                   type string;
                 }
                 leaf vpn-label {
                   type int32;
                   description "VPN label";
                 }
                 leaf route-label {
                   type int32;
                   description "Route label";
                 }
                 leaf route-labels {
                   type string;
                   description "Route label";
                 }
                 leaf mac-route-esi {
                   type string;
                   description "ESI";
                 }
                 leaf bgp-no-label-reason {
                   type string;
                 }
                 leaf bgp-metric-flags {
                   type string;
                   description "BGP metrics flags";
                 }
                 leaf med {
                   type int32;
                   description "Multiple exit discriminator";
                 }
                 leaf local-preference {
                   type int32;
                 }
                 leaf bgp-output-queue-class {
                   type string;
                   description "BGP output queue class";
                 }
                 leaf as-path {
                   type string;
                 }
                 leaf pmsi {
                   type string;
                   description "P-multicast service interface";
                 }
                 leaf cluster-id {
                   type string;
                 }
                 leaf originator {
                   type string;
                 }
                 leaf connector {
                   type string;
                 }
                 leaf path-id {
                   type string;
                 }
                 leaf bgp-aigp {
                   type string;
                   description "Accumulated IGP Metric";
                 }
                 leaf bgp-elc {
                   type empty;
                   description "Entropy label capable";
                 }
                 leaf bgp-elc-nh-valid {
                   type string;
                   description "Whether next hop field matches route next hop";
                 }
                 leaf hidden-reason {
                   type string;
                   description "Protocol's reason for hiding the route";
                 }
                 leaf bgp-bmp-send-flag-start {
                   type string;
                 }
                 leaf bgp-bmp-send-flag-pre {
                   type string;
                 }
                 leaf bgp-bmp-send-flag-post {
                   type string;
                 }
                 leaf bgp-bmp-send-flag-station {
                   type string;
                 }
                 leaf active-tag {
                   type string;
                   description "Visual indication of active state of this route entry";
                 }
                 leaf last-active {
                   type empty;
                   description "This route entry was the last active route entry";
                 }
                 leaf current-active {
                   type empty;
                   description "This route entry is currently active";
                 }
                 leaf deleted {
                   type empty;
                 }
                 leaf nh-kernel-id {
                   type int32;
                   description "Table Id for this next hop";
                 }
                 container route-data-dcf {
                   leaf rt-mac-addr {
                     type mac-addr;
                     description "Mac address associated with the route";
                   }
                   container snpa {
                     container pfe-port-snpa {
                       description "PFE Port SNPA";
                       leaf pfe-id {
                         type int32;
                       }
                       leaf port-id {
                         type int32;
                       }
                     }
                     container network-element-port-snpa {
                       description "Network Element Port SNPA";
                       leaf port-id {
                         type int32;
                       }
                     }
                     container mstp-root-snpa {
                       description "Multiple Spanning Tree Protocol Root SNPA";
                       leaf mstp-root-id {
                         type int32;
                       }
                     }
                     container gateway-snpa {
                       description "Gateway SNPA";
                       leaf gateway-addr {
                         type ipaddr;
                       }
                     }
                     container layer2-domain-port-snpa {
                       description "Layer-2 Domain Port SNPA";
                       leaf port-id {
                         type int32;
                       }
                     }
                     container replication-block-snpa {
                       description "Replication Block SNPA";
                       leaf replication-block-id {
                         type int32;
                       }
                     }
                     container replication-route-snpa {
                       description "Replication Route SNPA";
                       leaf network-element-id {
                         type ipaddr;
                       }
                     }
                     container layer2-multicast-port-snpa {
                       description "Layer-2 Multicast Port SNPA";
                       leaf layer2-multicast-port-id {
                         type int32;
                       }
                     }
                     container inh-snpa {
                       description "Indirection SNPA";
                       leaf inh-id {
                         type int32;
                       }
                     }
                   }
                 }
                 container rtd-flow-dep {
                 }
                 container communities {
                   leaf community {
                     type string;
                     description "Basic community";
                   }
                   leaf extended-community {
                     type string;
                     description "Extended community";
                   }
                 }
                 container attrset {
                   leaf attrset-as {
                     type int32;
                     description "Originator AS";
                   }
                   leaf med {
                     type int32;
                     description "Multiple exit discriminator";
                   }
                   leaf local-preference {
                     type int32;
                   }
                   leaf as-path {
                     type string;
                   }
                   leaf pmsi {
                     type string;
                     description "P-multicast service interface";
                   }
                   leaf cluster-id {
                     type string;
                   }
                   leaf originator {
                     type string;
                   }
                   leaf connector {
                     type string;
                   }
                   container communities {
                     leaf community {
                       type string;
                       description "Basic community";
                     }
                     leaf extended-community {
                       type string;
                       description "Extended community";
                     }
                   }
                 }
                 container link-state-information {
                   container link-state-link {
                     leaf color {
                       type int32;
                     }
                     leaf metric {
                       type int32;
                     }
                     leaf te-metric {
                       type int32;
                       description "LSP TE metric";
                     }
                     leaf ldp-support {
                       type string;
                     }
                     leaf rsvpte-support {
                       type string;
                     }
                     leaf maximum-bw {
                       type uint64;
                     }
                     leaf reservable-bw {
                       type uint64;
                     }
                     container protections {
                       leaf protection-type {
                         type string;
                         description "LSP protection desired";
                       }
                     }
                     container link-srlgs {
                       leaf link-srlg {
                         type string;
                       }
                     }
                     container unreserved-bws {
                       container unreserved-bw {
                         leaf unreserved-bw-priority {
                           type uint32;
                         }
                         leaf unreserved-bw-value {
                           type string;
                         }
                       }
                     }
                     container link-state-link-opaque-attrs {
                       leaf link-state-link-opaque-attrs-length {
                         type uint32;
                       }
                       leaf link-state-link-opaque-attrs-bytes {
                         type string;
                       }
                     }
                   }
                   container link-state-node {
                     leaf node-name {
                       type string;
                     }
                     leaf area-border-router {
                       type string;
                     }
                     leaf external-router {
                       type string;
                     }
                     leaf attached {
                       type string;
                     }
                     leaf overload {
                       type string;
                     }
                     container node-areas {
                       leaf node-area {
                         type string;
                       }
                     }
                     container node-ipv4-router-ids {
                       leaf node-ipv4-router-id {
                         type ipaddr;
                       }
                     }
                     container node-topologies {
                       container node-topology {
                         leaf id {
                           type uint32;
                         }
                       }
                     }
                     container link-state-node-opaque-attrs {
                       leaf link-state-node-opaque-attrs-length {
                         type uint32;
                       }
                       leaf link-state-node-opaque-attrs-bytes {
                         type string;
                       }
                     }
                   }
                   container link-state-unknown-tlvs {
                     container link-state-unknown-tlv {
                       leaf unknown-type {
                         type uint32;
                       }
                       leaf unknown-length {
                         type uint32;
                       }
                       leaf unknown-bytes {
                         type string;
                       }
                     }
                   }
                 }
                 container aggregate {
                 }
                 container nh {
                   description "Next-hop gateway information";
                   leaf to {
                     type string;
                     description "Neighbor address to which to send (next-hop address)";
                   }
                 }
                 container protocol-nh {
                   description "Protocol next hop";
                   container nh {
                     description "Next-hop gateway information";
                     leaf nh-string {
                       type string;
                     }
                     leaf elnh-address {
                       type int32;
                       description "Address of Element Next-hop";
                     }
                     leaf to {
                       type string;
                       description "Neighbor address to which to send (next-hop address)";
                     }
                     leaf via {
                       type string;
                       description "Reachable via a local interface";
                     }
                     leaf localized-table {
                       type string;
                       description "Name of localized table";
                     }
                     leaf weight {
                       type int32;
                       description "Next-hop weight";
                     }
                     leaf balance {
                       type int32;
                       description "Next-hop balance";
                     }
                     leaf uflags {
                       type int32;
                       description "Next-hop uflags";
                     }
                     leaf filter {
                       type string;
                       description "Next-hop firewall filter";
                     }
                     leaf selected-next-hop {
                       type empty;
                       description "Present if this next hop is selected";
                     }
                     leaf session {
                       type int32;
                       description "Session ID Associated with this NH";
                     }
                     leaf statistics-id-group-terse {
                       type string;
                       description "Statistics ID Group Associated with this NH";
                     }
                     leaf ext-int-type {
                       type string;
                       description "Next-hop type of equal-external-internal multipath";
                     }
                     leaf fc {
                       type int32;
                       description "Forwarding-class";
                     }
                     leaf lsp-name {
                       type string;
                       description "Tunneled into an RSVP LSP";
                     }
                     leaf mpls-label {
                       type string;
                       description "Label of MPLS packet";
                     }
                     leaf label-ttl-action {
                       type string;
                       description "TTL action associated with labels";
                     }
                     leaf load-balance-label {
                       type string;
                       description "Load balance action associated with labels";
                     }
                     leaf label-element {
                       type string;
                       description "Pointer to the tag label element";
                     }
                     leaf label-element-parent {
                       type string;
                       description "Pointer to the tag label element parent";
                     }
                     leaf label-element-refcount {
                       type string;
                       description "Number of references to the tag label element";
                     }
                     leaf label-element-childcount {
                       type string;
                       description "Number of child references to the tag label element";
                     }
                     leaf label-element-lspid {
                       type string;
                       description "LSP ID of the tag label element";
                     }
                     leaf nh-table-receive {
                       type string;
                       description "Destination is a local address";
                     }
                     leaf nh-table {
                       type string;
                       description "Indirect pointing to another table";
                     }
                     leaf nh-localized-ifl {
                       type string;
                       description "Indirect pointing to a localized ifl";
                     }
                     leaf nh-local-interface {
                       type string;
                       description "Destination is a local interface";
                     }
                     leaf nh-service {
                       type string;
                       description "Next-hop service";
                     }
                     leaf nh-service-pkt-dist {
                       type string;
                       description "Multi services packet distribution type";
                     }
                     leaf nh-service-app-data {
                       type string;
                       description "Multi services application specific data";
                     }
                     leaf nh-private-comp {
                       type string;
                       description "Private Composite Next-hop";
                     }
                     leaf nh-index {
                       type uint32;
                       description "Next-hop index";
                     }
                     leaf nh-address {
                       type int32;
                       description "Address of next hop";
                     }
                   }
                 }
               }
               container communities {
                 leaf community {
                   type string;
                   description "Basic community";
                 }
                 leaf extended-community {
                   type string;
                   description "Extended community";
                 }
               }
             }
           }
         }
       }
     }
   }
   rpc get-rtexport-table-information {
     description "Show instance export information";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
       leaf verbosity_level {
         default "brief";
         type enumeration {
           enum "brief" {
             description "Display brief output (default)";
           }
           enum "detail" {
             description "Display detailed output";
           }
         }
       }
       leaf table-name {
         description "Name of table";
         type string;
       }
     }
     output {
       container rtexport-table-information {
         container rte-table {
           container terse {
             leaf table-name {
               type string;
               description "Unicast routing table";
             }
             leaf table-export-on {
               type string;
             }
             leaf table-usage {
               type int32;
               description "Number of exported routes";
             }
           }
           container detail {
             leaf table-name {
               type string;
               description "Unicast routing table";
             }
             leaf table-usage {
               type int32;
               description "Number of exported routes";
             }
             leaf table-flags {
               type string;
             }
             leaf import-list {
               type string;
             }
           }
         }
         container rte-target {
           container terse {
             leaf target-string {
               type string;
               description "Route target";
             }
             leaf family {
               type string;
             }
             leaf subaf {
               type string;
             }
             leaf import-count {
               type int32;
             }
             leaf export-count {
               type int32;
             }
           }
           container detail {
             leaf target-string {
               type string;
               description "Route target";
             }
             leaf family {
               type string;
             }
             leaf subaf {
               type string;
             }
             leaf import-list {
               type string;
             }
             leaf export-list {
               type string;
             }
           }
         }
         container rte-instance {
           container terse {
             leaf instance-name {
               type string;
             }
             leaf rte-instance-type {
               type string;
             }
           }
           container detail {
             leaf instance-name {
               type string;
             }
             leaf rte-instance-type {
               type string;
             }
             leaf instance-flags {
               type string;
             }
             leaf instance-options {
               type string;
             }
             leaf import-policy {
               type string;
             }
             leaf export-policy {
               type string;
             }
           }
         }
       }
     }
   }
   rpc get-rtexport-target-information {
     description "Show VPN routing and forwarding route target export information";
     input {
       leaf verbosity_level {
         default "brief";
         type enumeration {
           enum "brief" {
             description "Display brief output (default)";
           }
           enum "detail" {
             description "Display detailed output";
           }
         }
       }
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
       leaf-list community {
         description "Community to match (can include wildcards)";
         type string;
       }
     }
   }
   rpc get-rtexport-instance-information {
     description "Show instance configuration and runtime information";
     input {
       leaf verbosity_level {
         default "brief";
         type enumeration {
           enum "brief" {
             description "Display brief output (default)";
           }
           enum "detail" {
             description "Display detailed output";
           }
         }
       }
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
       leaf instance-name {
         description "Name of instance";
         type string;
       }
     }
   }
   rpc get-rtflow-dep-information {
     description "Show flow route validation tables";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf table {
         description "Name of unicast routing table";
         type string;
       }
       leaf destination {
         description "IP address and optional prefix length of destination";
         type ipprefix-optional;
       }
     }
     output {
       container rtflow-dep-information {
         container rtflow-dep-table {
           leaf table-name {
             type string;
             description "Unicast routing table";
           }
           container fdep-node {
             leaf fdep-destination {
               type string;
               description "Destination prefix for tree node";
             }
             leaf fdep-prefixlen {
               type uint32;
               description "Destination prefix length for tree node";
             }
             container fdep-inode {
               leaf fdep-inode-color {
                 type string;
               }
               leaf fdep-inode-consist {
                 type string;
               }
               leaf fdep-inode-asn {
                 type uint32;
                 description "Neighbor AS for all more specific unicast routes";
               }
             }
             container fdep-rtnode {
               description "Entry that corresponding to a unicast route that is being tracked";
               leaf rtnode-state {
                 type string;
               }
               leaf rtnode-origin {
                 type ipaddr;
                 description "Unicast route origin (BGP gateway address or originator attribute";
               }
               leaf rtnode-next-as {
                 type uint32;
                 description "Neighbor AS for active unicast route";
               }
               leaf rtnode-refcount {
                 type uint32;
                 description "Dependent flow destinations";
               }
               leaf rtnode-flags {
                 type string;
               }
             }
             container fdep-depnode {
               leaf dep-entries {
                 type uint32;
                 description "Number of flow routes with this destination address";
               }
               leaf dep-active {
                 type uint32;
                 description "Number of flow routes which match unicast origin";
               }
               leaf dep-rtnode-prefix {
                 type ipaddr;
                 description "Prefix of unicast route used to resolve this flow destination";
               }
               leaf dep-rtnode-prefixlen {
                 type uint32;
                 description "Prefix length of unicast route used to resolve this flow destination";
               }
               leaf dep-flags {
                 type string;
               }
             }
           }
         }
       }
     }
   }
   rpc get-fib-localization-information {
     description "Show route localization information";
     input {
       leaf detail {
         description "Show detailed output";
         type empty;
       }
     }
     output {
       container fib-localization-information {
         container brief {
           description "Information about FIB localization";
           container fib-localization-state {
             description "FIB localization state";
             leaf ready-fib-local {
               type string;
               description "Ready FIB-local FPCs";
             }
             leaf ready-fib-remote {
               type string;
               description "Ready FIB-remote FPCs";
             }
             leaf ready-normal {
               type string;
               description "Ready normal FPCs";
             }
             leaf state-read-failed-on-backup {
               type empty;
             }
             leaf state-read-error {
               type empty;
             }
           }
         }
         container extensive {
           description "Information about FIB localization";
           container fib-localization-configuration {
             description "FIB localization configuration";
             leaf configured-protocols {
               type string;
               description "Configured FIB-local protocols";
             }
             leaf configured-fib-local {
               type string;
               description "Configured FIB-local FPCs";
             }
             leaf configured-fib-remote {
               type string;
               description "Configured FIB-remote FPCs";
             }
             leaf configuration-read-error {
               type empty;
             }
           }
           container fib-localization-state {
             description "FIB localization state";
             leaf ready-fib-local {
               type string;
               description "Ready FIB-local FPCs";
             }
             leaf ready-fib-remote {
               type string;
               description "Ready FIB-remote FPCs";
             }
             leaf ready-normal {
               type string;
               description "Ready normal FPCs";
             }
             leaf state-read-failed-on-backup {
               type empty;
             }
             leaf state-read-error {
               type empty;
             }
           }
           container fpc-slot-to-forwarding-engine-addresses-map {
             description "All known FPC slot-to-Forwarding-Engine-addresses mappings";
             leaf map-entry {
               type string;
               description "Map of an FPC slot to Forwarding Engine addresses";
             }
             leaf map-read-error {
               type empty;
             }
           }
         }
       }
     }
   }
 }
