/*
 * Copyright (c) 2017 Juniper Networks, Inc.
 * All rights reserved.
 */

 module show-as-path {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-as-path {
     description "Show table of known autonomous system paths";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
       leaf level {
         default "brief";
         type enumeration {
           enum "brief" {
             description "Display brief output (default)";
           }
           enum "detail" {
             description "Display detailed output";
           }
           enum "summary" {
             description "Display summary output";
           }
         }
       }
     }
     output {
       container juniper-routing-aspath {
         container aspath-domain {
           leaf identifier {
             type int32;
           }
           leaf primary {
             type int32;
           }
           leaf references {
             type int32;
           }
           leaf path-count {
             type int32;
           }
           leaf domain-flags {
             type string;
           }
           container local-asn {
             leaf asn {
               type int32;
             }
             leaf as-loops {
               type int32;
             }
           }
         }
         container aspath-table {
           container summary {
             leaf path-count {
               type int32;
             }
             leaf bucket-count {
               type int32;
             }
             leaf bucket-max-entries {
               type int32;
             }
             leaf bucket-min-entries {
               type int32;
             }
             leaf bucket-avg-entries {
               type int32;
             }
             leaf bucket-std-deviation {
               type string;
             }
             container aspath-bucket {
               leaf bucket {
                 type int32;
               }
               leaf count {
                 type int32;
               }
               container aspath-entry {
                 container brief {
                   leaf as-path {
                     type string;
                   }
                   leaf overhead {
                     type int32;
                   }
                   leaf compare-length {
                     type int32;
                   }
                 }
                 container detail {
                   leaf as-path {
                     type string;
                   }
                   leaf domain {
                     type int32;
                   }
                   leaf neighbor-as {
                     type int32;
                   }
                   leaf length {
                     type int32;
                   }
                   leaf segments {
                     type int32;
                   }
                   leaf unique-count {
                     type int32;
                   }
                   leaf path-references {
                     type int32;
                   }
                   leaf entry-state {
                     type string;
                   }
                   leaf overhead {
                     type int32;
                   }
                   leaf compare-length {
                     type int32;
                   }
                 }
               }
             }
           }
           container brief {
             leaf path-count {
               type int32;
             }
             container aspath-bucket {
               leaf bucket {
                 type int32;
               }
               leaf count {
                 type int32;
               }
               container aspath-entry {
                 container detail {
                   leaf as-path {
                     type string;
                   }
                   leaf domain {
                     type int32;
                   }
                   leaf neighbor-as {
                     type int32;
                   }
                   leaf length {
                     type int32;
                   }
                   leaf segments {
                     type int32;
                   }
                   leaf unique-count {
                     type int32;
                   }
                   leaf path-references {
                     type int32;
                   }
                   leaf entry-state {
                     type string;
                   }
                   leaf overhead {
                     type int32;
                   }
                   leaf compare-length {
                     type int32;
                   }
                 }
               }
             }
           }
           container detail {
             leaf path-count {
               type int32;
             }
             container aspath-bucket {
               leaf bucket {
                 type int32;
               }
               leaf count {
                 type int32;
               }
               container aspath-entry {
                 container brief {
                   leaf as-path {
                     type string;
                   }
                   leaf overhead {
                     type int32;
                   }
                   leaf compare-length {
                     type int32;
                   }
                 }
                 container detail {
                   leaf as-path {
                     type string;
                   }
                   leaf domain {
                     type int32;
                   }
                   leaf neighbor-as {
                     type int32;
                   }
                   leaf length {
                     type int32;
                   }
                   leaf segments {
                     type int32;
                   }
                   leaf unique-count {
                     type int32;
                   }
                   leaf path-references {
                     type int32;
                   }
                   leaf entry-state {
                     type string;
                   }
                   leaf overhead {
                     type int32;
                   }
                   leaf compare-length {
                     type int32;
                   }
                 }
               }
             }
           }
         }
       }
     }
   }
   rpc get-as-path-domain {
     description "Show autonomous-system domains";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
     }
     output {
       container juniper-routing-aspath {
         container aspath-domain {
           leaf identifier {
             type int32;
           }
           leaf primary {
             type int32;
           }
           leaf references {
             type int32;
           }
           leaf path-count {
             type int32;
           }
           leaf domain-flags {
             type string;
           }
           container local-asn {
             leaf asn {
               type int32;
             }
             leaf as-loops {
               type int32;
             }
           }
         }
         container aspath-table {
           container summary {
             leaf path-count {
               type int32;
             }
             leaf bucket-count {
               type int32;
             }
             leaf bucket-max-entries {
               type int32;
             }
             leaf bucket-min-entries {
               type int32;
             }
             leaf bucket-avg-entries {
               type int32;
             }
             leaf bucket-std-deviation {
               type string;
             }
             container aspath-bucket {
               leaf bucket {
                 type int32;
               }
               leaf count {
                 type int32;
               }
               container aspath-entry {
                 container brief {
                   leaf as-path {
                     type string;
                   }
                   leaf overhead {
                     type int32;
                   }
                   leaf compare-length {
                     type int32;
                   }
                 }
                 container detail {
                   leaf as-path {
                     type string;
                   }
                   leaf domain {
                     type int32;
                   }
                   leaf neighbor-as {
                     type int32;
                   }
                   leaf length {
                     type int32;
                   }
                   leaf segments {
                     type int32;
                   }
                   leaf unique-count {
                     type int32;
                   }
                   leaf path-references {
                     type int32;
                   }
                   leaf entry-state {
                     type string;
                   }
                   leaf overhead {
                     type int32;
                   }
                   leaf compare-length {
                     type int32;
                   }
                 }
               }
             }
           }
           container brief {
             leaf path-count {
               type int32;
             }
             container aspath-bucket {
               leaf bucket {
                 type int32;
               }
               leaf count {
                 type int32;
               }
               container aspath-entry {
                 container detail {
                   leaf as-path {
                     type string;
                   }
                   leaf domain {
                     type int32;
                   }
                   leaf neighbor-as {
                     type int32;
                   }
                   leaf length {
                     type int32;
                   }
                   leaf segments {
                     type int32;
                   }
                   leaf unique-count {
                     type int32;
                   }
                   leaf path-references {
                     type int32;
                   }
                   leaf entry-state {
                     type string;
                   }
                   leaf overhead {
                     type int32;
                   }
                   leaf compare-length {
                     type int32;
                   }
                 }
               }
             }
           }
           container detail {
             leaf path-count {
               type int32;
             }
             container aspath-bucket {
               leaf bucket {
                 type int32;
               }
               leaf count {
                 type int32;
               }
               container aspath-entry {
                 container brief {
                   leaf as-path {
                     type string;
                   }
                   leaf overhead {
                     type int32;
                   }
                   leaf compare-length {
                     type int32;
                   }
                 }
                 container detail {
                   leaf as-path {
                     type string;
                   }
                   leaf domain {
                     type int32;
                   }
                   leaf neighbor-as {
                     type int32;
                   }
                   leaf length {
                     type int32;
                   }
                   leaf segments {
                     type int32;
                   }
                   leaf unique-count {
                     type int32;
                   }
                   leaf path-references {
                     type int32;
                   }
                   leaf entry-state {
                     type string;
                   }
                   leaf overhead {
                     type int32;
                   }
                   leaf compare-length {
                     type int32;
                   }
                 }
               }
             }
           }
         }
       }
     }
   }
 }
