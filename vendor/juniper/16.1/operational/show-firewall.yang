/*
 * Copyright (c) 2017 Juniper Networks, Inc.
 * All rights reserved.
 */

 module show-firewall {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-firewall-information {
     description "Show firewall information";
     input {
       leaf application {
         description "Owner application";
         type enumeration {
           enum "cfm" {
             description "Statistics for implicit filters for CFM";
           }
           enum "rmps" {
             description "Statistics for implicit filters for RMPS";
           }
           enum "eswd" {
             description "Statistics for implicit filters for eswd";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
       leaf terse {
         description "Show filter names only";
         type empty;
       }
     }
     output {
       container firewall-information {
         container filter-information {
           description "Details of a firewall filter";
           leaf filter-name {
             type string;
             description "Name of filter";
           }
           container counter {
             description "Counter information";
             leaf counter-name {
               type string;
               description "Counter name";
             }
             leaf byte-count {
               type uint64;
               description "Bytes counted";
             }
             leaf packet-count {
               type uint64;
               description "Packets counted";
             }
           }
           container policer {
             description "Policer information";
             leaf policer-name {
               type string;
               description "Name of this policer";
             }
             leaf byte-count {
               type uint64;
               description "Bytes counted";
             }
             leaf packet-count {
               type uint64;
               description "Packets counted";
             }
           }
           container filter-version {
             description "Filter version information";
             leaf filter-name {
               type string;
               description "Name of filter";
             }
             leaf version {
               type uint32;
               description "Filter version";
             }
           }
         }
       }
     }
   }
   rpc get-firewall-counter-information {
     description "Counter name";
     input {
       leaf countername {
         description "Counter name";
         type string;
         mandatory true;
       }
       leaf filter {
         description "Filter name";
         type string;
         mandatory true;
       }
       leaf application {
         description "Owner application";
         type enumeration {
           enum "cfm" {
             description "Statistics for implicit filters for CFM";
           }
           enum "rmps" {
             description "Statistics for implicit filters for RMPS";
           }
           enum "eswd" {
             description "Statistics for implicit filters for eswd";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
   }
   rpc get-firewall-filter-information {
     description "Filter name";
     input {
       leaf filtername {
         description "Filter name";
         type string;
         mandatory true;
       }
       leaf counter {
         description "Counter name";
         type string;
       }
       leaf application {
         description "Owner application";
         type enumeration {
           enum "cfm" {
             description "Statistics for implicit filters for CFM";
           }
           enum "rmps" {
             description "Statistics for implicit filters for RMPS";
           }
           enum "eswd" {
             description "Statistics for implicit filters for eswd";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
   }
   rpc get-filter-version {
     description "Show filter version installed";
     output {
       container firewall-information {
         container filter-information {
           description "Details of a firewall filter";
           leaf filter-name {
             type string;
             description "Name of filter";
           }
           container counter {
             description "Counter information";
             leaf counter-name {
               type string;
               description "Counter name";
             }
             leaf byte-count {
               type uint64;
               description "Bytes counted";
             }
             leaf packet-count {
               type uint64;
               description "Packets counted";
             }
           }
           container policer {
             description "Policer information";
             leaf policer-name {
               type string;
               description "Name of this policer";
             }
             leaf byte-count {
               type uint64;
               description "Bytes counted";
             }
             leaf packet-count {
               type uint64;
               description "Packets counted";
             }
           }
           container filter-version {
             description "Filter version information";
             leaf filter-name {
               type string;
               description "Name of filter";
             }
             leaf version {
               type uint32;
               description "Filter version";
             }
           }
         }
       }
     }
   }
   rpc get-firewall-filter-regex-information {
     description "Show filter using regular expression";
     input {
       leaf filtername {
         description "Regular expression of filter names";
         type regular-expression;
       }
       leaf logical-system {
         description "Name of logical system, or 'all'";
         type string {
           junos:posix-pattern "^[a-zA-Z0-9_-]{1,63}$";
           junos:pattern-message "Logical-system name is a string consisting of up to 63 letters, numbers, dashes and underscores";
         }
       }
     }
   }
   rpc get-firewall-log-information {
     description "Show log entries for firewall activity";
     input {
       leaf get-firewall-log-detailed-information {
         description "Display detailed output";
         type empty;
       }
       leaf interface {
         description "Interface name";
         type string;
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container firewall-log-information {
         container log-information {
           description "Details of a single firewall log entry";
           container normal {
             description "Details of a single firewall log entry";
             leaf time {
               type string;
               description "Time of log";
             }
             leaf filter-name {
               type string;
               description "Name of filter";
             }
             leaf action-name {
               type string;
               description "Filter action";
             }
             leaf interface-name {
               type string;
               description "Name of interface";
             }
             leaf protocol-name {
               type string;
               description "Name of protocol";
             }
             leaf source-address {
               type string;
               description "Source address";
             }
             leaf destination-address {
               type string;
               description "Destination address";
             }
           }
           container extensive {
             description "Details of a single firewall log entry";
             leaf time {
               type string;
               description "Time of log";
             }
             leaf filter-name {
               type string;
               description "Name of filter";
             }
             leaf action-name {
               type string;
               description "Filter action";
             }
             leaf interface-name {
               type string;
               description "Name of interface";
             }
             leaf protocol-name {
               type string;
               description "Name of protocol";
             }
             leaf packet-length {
               type int32;
               description "Packet length";
             }
             leaf source-address {
               type string;
               description "Source address";
             }
             leaf destination-address {
               type string;
               description "Destination address";
             }
             leaf icmp-type {
               type int32;
               description "ICMP type";
             }
             leaf icmp-code {
               type int32;
               description "ICMP code";
             }
             leaf hex-dump-line {
               type string;
               description "Packet in Hex format";
             }
             leaf hex-dump-line1 {
               type string;
               description "Packet in Hex format";
             }
             leaf hex-dump-line2 {
               type string;
               description "Packet in Hex format";
             }
             leaf hex-dump-line3 {
               type string;
               description "Packet in Hex format";
             }
             leaf hex-dump-line4 {
               type string;
               description "Packet in Hex format";
             }
             leaf hex-dump-line5 {
               type string;
               description "Packet in Hex format";
             }
             leaf hex-dump-line6 {
               type string;
               description "Packet in Hex format";
             }
             leaf hex-dump-line7 {
               type string;
               description "Packet in Hex format";
             }
           }
           container detail {
             description "Details of a single firewall log entry";
             leaf time {
               type string;
               description "Time of log";
             }
             leaf filter-name {
               type string;
               description "Name of filter";
             }
             leaf action-name {
               type string;
               description "Filter action";
             }
             leaf interface-name {
               type string;
               description "Name of interface";
             }
             leaf protocol-name {
               type string;
               description "Name of protocol";
             }
             leaf packet-length {
               type int32;
               description "Packet length";
             }
             leaf source-address {
               type string;
               description "Source address";
             }
             leaf destination-address {
               type string;
               description "Destination address";
             }
             leaf icmp-type {
               type int32;
               description "ICMP type";
             }
             leaf icmp-code {
               type int32;
               description "ICMP code";
             }
           }
         }
       }
     }
   }
   rpc get-firewall-prefix-action-information {
     description "Show prefix-action statistics for a filter";
     input {
       leaf filter {
         description "Filter name";
         type string;
         mandatory true;
       }
       leaf prefix-action {
         description "Prefix-action name";
         type string;
         mandatory true;
       }
       leaf from {
         description "Starting counter or policer";
         default "0";
         type uint32 {
           range "0 .. 65535";
         }
       }
       leaf to {
         description "Ending counter or policer";
         default "65535";
         type uint32 {
           range "0 .. 65535";
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container firewall-prefix-action-information {
         leaf filter-name {
           type string;
           description "Name of filter";
         }
         container counter {
           description "Counter information";
           leaf counter-name {
             type string;
             description "Counter name";
           }
           leaf byte-count {
             type uint64;
             description "Bytes counted";
           }
           leaf packet-count {
             type uint64;
             description "Packets counted";
           }
         }
         container policer {
           description "Policer information";
           leaf policer-name {
             type string;
             description "Name of this policer";
           }
           leaf byte-count {
             type uint64;
             description "Bytes counted";
           }
           leaf packet-count {
             type uint64;
             description "Packets counted";
           }
         }
       }
     }
   }
 }
