/*
 * Copyright (c) 2017 Juniper Networks, Inc.
 * All rights reserved.
 */

 module set {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc set-logical-router {
     description "Set default logical system";
     input {
       leaf logical-system {
         description "Name of logical system";
         type string {
           junos:posix-pattern "^[a-zA-Z0-9_-]{1,63}$";
           junos:pattern-message "Logical-system name is a string consisting of up to 63 letters, numbers, dashes and underscores";
         }
         mandatory true;
       }
     }
     output {
       container cli {
         leaf banner {
           type string;
         }
         leaf complete-on-space {
           type string;
         }
         leaf force {
           type empty;
         }
         leaf history-mode {
           type string;
         }
         leaf idle-timeout {
           type int32;
         }
         leaf ignore-signals {
           type string;
         }
         leaf log-level {
           type int32;
         }
         leaf log-to-stderr {
           type string;
         }
         leaf logical-system {
           type string;
         }
         leaf clear-logical-system {
           type string;
         }
         leaf prompt {
           type string;
         }
         leaf prompt-change {
           type string;
         }
         leaf restart-on-upgrade {
           type string;
         }
         leaf screen-length {
           type int32;
         }
         leaf screen-width {
           type int32;
         }
         leaf show-cli {
           type empty;
         }
         leaf stdin-line {
           type string;
         }
         leaf terminal-type {
           type string;
         }
         leaf timestamp-format {
           type string;
         }
         leaf timestamp-disable {
           type empty;
         }
         leaf version-change {
           type empty;
         }
         leaf working-directory {
           type string;
         }
         leaf reset-time-zone {
           type empty;
         }
         container display-version {
           leaf extensive {
             type empty;
           }
         }
         container history {
           leaf count {
             type int32;
           }
         }
         container monitor {
           leaf status {
             type string;
           }
           leaf stop-all {
             type empty;
           }
           container start {
             leaf source-filename {
               type string;
             }
             leaf allow-access {
               type empty;
             }
           }
           container stop {
             leaf source-filename {
               type string;
             }
           }
           container style {
             leaf header {
               type empty;
             }
             leaf none {
               type empty;
             }
             leaf prepend {
               type empty;
             }
           }
         }
       }
     }
   }
   rpc set-cli-working-directory {
     description "Set working directory";
     input {
       leaf directory {
         description "Pathname of working directory";
         type string;
         mandatory true;
       }
     }
     output {
       container cli {
         leaf banner {
           type string;
         }
         leaf complete-on-space {
           type string;
         }
         leaf force {
           type empty;
         }
         leaf history-mode {
           type string;
         }
         leaf idle-timeout {
           type int32;
         }
         leaf ignore-signals {
           type string;
         }
         leaf log-level {
           type int32;
         }
         leaf log-to-stderr {
           type string;
         }
         leaf logical-system {
           type string;
         }
         leaf clear-logical-system {
           type string;
         }
         leaf prompt {
           type string;
         }
         leaf prompt-change {
           type string;
         }
         leaf restart-on-upgrade {
           type string;
         }
         leaf screen-length {
           type int32;
         }
         leaf screen-width {
           type int32;
         }
         leaf show-cli {
           type empty;
         }
         leaf stdin-line {
           type string;
         }
         leaf terminal-type {
           type string;
         }
         leaf timestamp-format {
           type string;
         }
         leaf timestamp-disable {
           type empty;
         }
         leaf version-change {
           type empty;
         }
         leaf working-directory {
           type string;
         }
         leaf reset-time-zone {
           type empty;
         }
         container display-version {
           leaf extensive {
             type empty;
           }
         }
         container history {
           leaf count {
             type int32;
           }
         }
         container monitor {
           leaf status {
             type string;
           }
           leaf stop-all {
             type empty;
           }
           container start {
             leaf source-filename {
               type string;
             }
             leaf allow-access {
               type empty;
             }
           }
           container stop {
             leaf source-filename {
               type string;
             }
           }
           container style {
             leaf header {
               type empty;
             }
             leaf none {
               type empty;
             }
             leaf prepend {
               type empty;
             }
           }
         }
       }
     }
   }
 }
