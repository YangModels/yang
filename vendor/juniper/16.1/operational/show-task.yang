/*
 * Copyright (c) 2017 Juniper Networks, Inc.
 * All rights reserved.
 */

 module show-task {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-lrmuxd-task-information {
     description "Show logical-system-mux per-task information";
     input {
       leaf level {
         default "summary";
         type enumeration {
           enum "summary" {
             description "Display summary output (default)";
           }
         }
       }
       leaf task-name {
         description "Name of task";
         type string;
       }
     }
   }
   rpc get-lrmuxd-tasks-io-statistics {
     description "Show task I/O statistics";
   }
   rpc get-lrmuxd-task-memory {
     description "Show memory utilization of lrmuxd tasks";
     input {
       leaf level {
         type enumeration {
           enum "summary" {
             description "Display current and maximum memory usage";
           }
           enum "brief" {
             description "Display current/maximum/available memory";
           }
           enum "detail" {
             description "Display memory usage by individual users";
           }
           enum "history" {
             description "Display memory usage in the recent past";
           }
         }
       }
     }
   }
   rpc get-routing-task-replication-state {
     description "Stateful replication";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
     }
     output {
       container task-replication-state {
         leaf task-gres-state {
           type string;
           description "Current state of graceful Routing Engine Switchover";
         }
         leaf task-re-mode {
           type string;
           description "Current mastership state of Routing Engine";
         }
         leaf task-protocol-replication-name {
           type string;
         }
         leaf task-protocol-replication-state {
           type string;
         }
       }
     }
   }
   rpc get-task-memory-information {
     description "Show memory utilization of routing tasks";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
       leaf level {
         type enumeration {
           enum "summary" {
             description "Display current and maximum memory usage";
           }
           enum "brief" {
             description "Display current/maximum/available memory";
           }
           enum "detail" {
             description "Display memory usage by individual users";
           }
           enum "history" {
             description "Display memory usage in the recent past";
           }
         }
       }
     }
     output {
       container task-memory-information {
         container summary {
           leaf task-memory-in-use-size {
             type int32;
           }
           leaf task-memory-in-use-avail {
             type string;
           }
           leaf task-memory-max-size {
             type int32;
           }
           leaf task-memory-max-avail {
             type string;
           }
           container task-memory-overall-report {
             container task-size-block-list {
             }
             container task-memory-stats-list {
             }
           }
           container task-memory-allocator-report {
             container task-block-list {
             }
             container task-lite-page-list {
             }
           }
           container task-memory-malloc-usage-report {
             container task-malloc-list {
             }
           }
         }
         container brief {
           leaf task-memory-in-use-size {
             type int32;
           }
           leaf task-memory-in-use-avail {
             type string;
           }
           leaf task-memory-max-size {
             type int32;
           }
           leaf task-memory-max-avail {
             type string;
           }
           leaf task-memory-max-when {
             type string;
           }
           leaf task-memory-free-size {
             type int32;
           }
           container task-memory-overall-report {
             container task-size-block-list {
             }
             container task-memory-stats-list {
             }
           }
           container task-memory-allocator-report {
             container task-block-list {
             }
             container task-lite-page-list {
             }
           }
           container task-memory-malloc-usage-report {
             container task-malloc-list {
             }
           }
         }
         container detail {
           leaf task-memory-dynamic-allocs {
             type string;
           }
           leaf task-memory-max-dynamic-allocs {
             type string;
           }
           leaf task-memory-bss-bytes {
             type string;
           }
           leaf task-memory-max-bss-bytes {
             type string;
           }
           leaf task-memory-page-data-bytes {
             type string;
           }
           leaf task-memory-max-page-data-bytes {
             type string;
           }
           leaf task-memory-dir-bytes {
             type string;
           }
           leaf task-memory-max-dir-bytes {
             type string;
           }
           leaf task-memory-total-bytes-in-use {
             type string;
           }
           leaf task-memory-total-bytes-percent {
             type string;
           }
           container task-memory-overall-report {
             leaf task-memory-total-bytes {
               type int32;
             }
             leaf task-memory-total-max-bytes {
               type int32;
             }
             leaf task-memory-total-free-bytes {
               type int32;
             }
             container task-size-block-list {
               container task-size-block {
                 leaf tsb-size {
                   type int32;
                   description "Size of this block";
                 }
                 leaf tsb-terse-transient {
                   type empty;
                 }
                 leaf tsb-terse-exclusive {
                   type empty;
                 }
                 leaf tsb-terse-fullpage {
                   type empty;
                 }
                 leaf tsb-allocs {
                   type string;
                   description "Number of items allocated now not using malloc";
                 }
                 leaf tsb-mallocs {
                   type string;
                   description "Number of items allocated using malloc";
                 }
                 leaf tsb-alloc-bytes {
                   type string;
                   description "Number of items allocated in bytes";
                 }
                 leaf tsb-max-allocs {
                   type string;
                   description "Maximum items ever allocated";
                 }
                 leaf tsb-max-bytes {
                   type string;
                   description "Maximum items ever allocated in bytes";
                 }
                 leaf tsb-free-bytes {
                   type string;
                   description "Number of free bytes";
                 }
               }
             }
             container task-memory-stats-list {
               container task-memory-stats {
                 leaf tms-name {
                   type string;
                 }
                 leaf tms-allocs {
                   type string;
                   description "Number of items allocated";
                 }
                 leaf tms-mallocs {
                   type string;
                   description "Number of items allocated using malloc";
                 }
                 leaf tms-alloc-bytes {
                   type string;
                   description "Number of bytes now allocated";
                 }
                 leaf tms-max-allocs {
                   type string;
                   description "Maximum items ever allocated";
                 }
                 leaf tms-max-bytes {
                   type string;
                   description "Maximum bytes ever allocated";
                 }
                 leaf tms-free-bytes {
                   type string;
                 }
               }
             }
           }
           container task-memory-allocator-report {
             leaf task-memory-total-bytes {
               type int32;
             }
             leaf task-memory-total-max-bytes {
               type int32;
             }
             container task-block-list {
               container task-block {
                 leaf tb-name {
                   type string;
                   description "Name for this block";
                 }
                 leaf tb-size {
                   type int32;
                   description "Actual size of this block";
                 }
                 leaf tb-alloc-size {
                   type string;
                   description "Allocated size for this block";
                 }
                 leaf tb-terse-debug {
                   type empty;
                 }
                 leaf tb-terse-transient {
                   type empty;
                 }
                 leaf tb-terse-exclusive {
                   type empty;
                 }
                 leaf tb-terse-fullpage {
                   type empty;
                 }
                 leaf tb-alloc-blocks {
                   type string;
                   description "Number of allocated structures";
                 }
                 leaf tb-alloc-bytes {
                   type string;
                   description "Number of allocated bytes";
                 }
                 leaf tb-max-alloc-blocks {
                   type int32;
                   description "Maximum number of structures ever allocated";
                 }
                 leaf tb-max-alloc-bytes {
                   type int32;
                   description "Maximum number of bytes ever allocated";
                 }
               }
             }
             container task-lite-page-list {
               container task-lite-page {
                 leaf tlp-name {
                   type string;
                   description "Name of this pool";
                 }
                 leaf tlp-alloc-pages {
                   type string;
                   description "Number of pages allocated";
                 }
                 leaf tlp-alloc-bytes {
                   type string;
                   description "Number of bytes allocated";
                 }
                 leaf tlp-max-alloc-pages {
                   type string;
                   description "Maximum pages ever allocated";
                 }
                 leaf tlp-max-alloc-bytes {
                   type string;
                   description "Maximum bytes ever allocated";
                 }
               }
             }
           }
           container task-memory-malloc-usage-report {
             leaf task-memory-total-bytes {
               type int32;
             }
             leaf task-memory-total-max-bytes {
               type int32;
             }
             container task-malloc-list {
               container task-malloc {
                 leaf tm-name {
                   type string;
                 }
                 leaf tm-allocs {
                   type string;
                   description "Number of allocations out";
                 }
                 leaf tm-alloc-bytes {
                   type string;
                   description "Number of bytes allocated";
                 }
                 leaf tm-max-allocs {
                   type string;
                   description "Maximum allocations ever out";
                 }
                 leaf tm-max-alloc-bytes {
                   type string;
                   description "Maximum bytes allocated";
                 }
                 leaf tm-function-calls {
                   type int32;
                   description "Number of function calls";
                 }
               }
             }
           }
         }
       }
     }
   }
   rpc get-snooping-task-memory-information {
     description "Show memory utilization of routing tasks";
     input {
       leaf level {
         type enumeration {
           enum "summary" {
             description "Display current and maximum memory usage";
           }
           enum "brief" {
             description "Display current/maximum/available memory";
           }
           enum "detail" {
             description "Display memory usage by individual users";
           }
           enum "history" {
             description "Display memory usage in the recent past";
           }
         }
       }
     }
     output {
       container task-memory-information {
         container summary {
           leaf task-memory-in-use-size {
             type int32;
           }
           leaf task-memory-in-use-avail {
             type string;
           }
           leaf task-memory-max-size {
             type int32;
           }
           leaf task-memory-max-avail {
             type string;
           }
           container task-memory-overall-report {
             container task-size-block-list {
             }
             container task-memory-stats-list {
             }
           }
           container task-memory-allocator-report {
             container task-block-list {
             }
             container task-lite-page-list {
             }
           }
           container task-memory-malloc-usage-report {
             container task-malloc-list {
             }
           }
         }
         container brief {
           leaf task-memory-in-use-size {
             type int32;
           }
           leaf task-memory-in-use-avail {
             type string;
           }
           leaf task-memory-max-size {
             type int32;
           }
           leaf task-memory-max-avail {
             type string;
           }
           leaf task-memory-max-when {
             type string;
           }
           leaf task-memory-free-size {
             type int32;
           }
           container task-memory-overall-report {
             container task-size-block-list {
             }
             container task-memory-stats-list {
             }
           }
           container task-memory-allocator-report {
             container task-block-list {
             }
             container task-lite-page-list {
             }
           }
           container task-memory-malloc-usage-report {
             container task-malloc-list {
             }
           }
         }
         container detail {
           leaf task-memory-dynamic-allocs {
             type string;
           }
           leaf task-memory-max-dynamic-allocs {
             type string;
           }
           leaf task-memory-bss-bytes {
             type string;
           }
           leaf task-memory-max-bss-bytes {
             type string;
           }
           leaf task-memory-page-data-bytes {
             type string;
           }
           leaf task-memory-max-page-data-bytes {
             type string;
           }
           leaf task-memory-dir-bytes {
             type string;
           }
           leaf task-memory-max-dir-bytes {
             type string;
           }
           leaf task-memory-total-bytes-in-use {
             type string;
           }
           leaf task-memory-total-bytes-percent {
             type string;
           }
           container task-memory-overall-report {
             leaf task-memory-total-bytes {
               type int32;
             }
             leaf task-memory-total-max-bytes {
               type int32;
             }
             leaf task-memory-total-free-bytes {
               type int32;
             }
             container task-size-block-list {
               container task-size-block {
                 leaf tsb-size {
                   type int32;
                   description "Size of this block";
                 }
                 leaf tsb-terse-transient {
                   type empty;
                 }
                 leaf tsb-terse-exclusive {
                   type empty;
                 }
                 leaf tsb-terse-fullpage {
                   type empty;
                 }
                 leaf tsb-allocs {
                   type string;
                   description "Number of items allocated now not using malloc";
                 }
                 leaf tsb-mallocs {
                   type string;
                   description "Number of items allocated using malloc";
                 }
                 leaf tsb-alloc-bytes {
                   type string;
                   description "Number of items allocated in bytes";
                 }
                 leaf tsb-max-allocs {
                   type string;
                   description "Maximum items ever allocated";
                 }
                 leaf tsb-max-bytes {
                   type string;
                   description "Maximum items ever allocated in bytes";
                 }
                 leaf tsb-free-bytes {
                   type string;
                   description "Number of free bytes";
                 }
               }
             }
             container task-memory-stats-list {
               container task-memory-stats {
                 leaf tms-name {
                   type string;
                 }
                 leaf tms-allocs {
                   type string;
                   description "Number of items allocated";
                 }
                 leaf tms-mallocs {
                   type string;
                   description "Number of items allocated using malloc";
                 }
                 leaf tms-alloc-bytes {
                   type string;
                   description "Number of bytes now allocated";
                 }
                 leaf tms-max-allocs {
                   type string;
                   description "Maximum items ever allocated";
                 }
                 leaf tms-max-bytes {
                   type string;
                   description "Maximum bytes ever allocated";
                 }
                 leaf tms-free-bytes {
                   type string;
                 }
               }
             }
           }
           container task-memory-allocator-report {
             leaf task-memory-total-bytes {
               type int32;
             }
             leaf task-memory-total-max-bytes {
               type int32;
             }
             container task-block-list {
               container task-block {
                 leaf tb-name {
                   type string;
                   description "Name for this block";
                 }
                 leaf tb-size {
                   type int32;
                   description "Actual size of this block";
                 }
                 leaf tb-alloc-size {
                   type string;
                   description "Allocated size for this block";
                 }
                 leaf tb-terse-debug {
                   type empty;
                 }
                 leaf tb-terse-transient {
                   type empty;
                 }
                 leaf tb-terse-exclusive {
                   type empty;
                 }
                 leaf tb-terse-fullpage {
                   type empty;
                 }
                 leaf tb-alloc-blocks {
                   type string;
                   description "Number of allocated structures";
                 }
                 leaf tb-alloc-bytes {
                   type string;
                   description "Number of allocated bytes";
                 }
                 leaf tb-max-alloc-blocks {
                   type int32;
                   description "Maximum number of structures ever allocated";
                 }
                 leaf tb-max-alloc-bytes {
                   type int32;
                   description "Maximum number of bytes ever allocated";
                 }
               }
             }
             container task-lite-page-list {
               container task-lite-page {
                 leaf tlp-name {
                   type string;
                   description "Name of this pool";
                 }
                 leaf tlp-alloc-pages {
                   type string;
                   description "Number of pages allocated";
                 }
                 leaf tlp-alloc-bytes {
                   type string;
                   description "Number of bytes allocated";
                 }
                 leaf tlp-max-alloc-pages {
                   type string;
                   description "Maximum pages ever allocated";
                 }
                 leaf tlp-max-alloc-bytes {
                   type string;
                   description "Maximum bytes ever allocated";
                 }
               }
             }
           }
           container task-memory-malloc-usage-report {
             leaf task-memory-total-bytes {
               type int32;
             }
             leaf task-memory-total-max-bytes {
               type int32;
             }
             container task-malloc-list {
               container task-malloc {
                 leaf tm-name {
                   type string;
                 }
                 leaf tm-allocs {
                   type string;
                   description "Number of allocations out";
                 }
                 leaf tm-alloc-bytes {
                   type string;
                   description "Number of bytes allocated";
                 }
                 leaf tm-max-allocs {
                   type string;
                   description "Maximum allocations ever out";
                 }
                 leaf tm-max-alloc-bytes {
                   type string;
                   description "Maximum bytes allocated";
                 }
                 leaf tm-function-calls {
                   type int32;
                   description "Number of function calls";
                 }
               }
             }
           }
         }
       }
     }
   }
 }
