/*
 * Copyright (c) 2017 Juniper Networks, Inc.
 * All rights reserved.
 */

 module show-bfd {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-bfd-session-information {
     description "Show all BFD sessions";
     input {
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container bfd-session-information {
         leaf sessions {
           type int32;
           description "Total number of active BFD sessions";
         }
         leaf clients {
           type int32;
           description "Total number of clients that are hosting BFD sessions";
         }
         leaf up-sessions {
           type string;
           description "Total number of BFD sessions which are UP";
         }
         leaf down-sessions {
           type string;
           description "Total number of BFD sessions which are not UP";
         }
         leaf cumulative-transmission-rate {
           type int32;
           description "Number of BFD control packets transmitted per second inall active sessions";
         }
         leaf cumulative-reception-rate {
           type int32;
           description "Number of BFD control packets received per second inall active sessions";
         }
         leaf cumulative-up-time {
           type string;
           description "Time taken to being up bfd sesison";
         }
         leaf error-value {
           type string;
           description "Error code that is returned when a 'clear' operation fails";
         }
         container summary {
           container bfd-session {
             description "Information about bidirectional forwarding detection session";
             container bfd-client {
               description "Information about the clients";
               leaf client-name {
                 type string;
                 description "Protocol for which the BFD session is active (forexample: OSPF, ISIS, Static, and so on) ";
               }
               leaf client-transmission-interval {
                 type int32;
                 description "Base frequency that the client proposes for sending BFDcontrol packets (seconds)";
               }
               leaf client-reception-interval {
                 type int32;
                 description "Base frequency that the client has proposed for peersto send BFD control packets (seconds)";
               }
               leaf client-multiplier {
                 type int32;
                 description "Multiplier that the client has requested to determine theliveness of the BFD session.";
               }
               leaf client-authentication {
                 type string;
                 description "Client requested authentication";
               }
               leaf client-holddown-interval {
                 type string;
                 description "Hold interval for which BFD does not send a session UP notification to the client (seconds)";
               }
               leaf client-state {
                 type string;
                 description "Tells whether client is in holddown or not";
               }
               leaf client-keychain {
                 type string;
                 description "Client requested keychain name";
               }
               leaf client-algorithm {
                 type int32;
                 description "Client requested algorithm";
               }
               leaf client-authentication-loose {
                 type string;
                 description "Client requested mode";
               }
             }
           }
         }
         container brief {
           leaf sessions {
             type int32;
             description "Total number of active BFD sessions";
           }
           leaf clients {
             type int32;
             description "Total number of clients that are hosting BFD sessions";
           }
           leaf up-sessions {
             type string;
             description "Total number of BFD sessions which are UP";
           }
           leaf down-sessions {
             type string;
             description "Total number of BFD sessions which are not UP";
           }
           leaf cumulative-transmission-rate {
             type int32;
             description "Number of BFD control packets transmitted per second inall active sessions";
           }
           leaf cumulative-reception-rate {
             type int32;
             description "Number of BFD control packets received per second inall active sessions";
           }
           leaf cumulative-up-time {
             type string;
             description "Time taken to being up bfd sesison";
           }
           container bfd-session {
             description "Information about bidirectional forwarding detection session";
             leaf session-neighbor {
               type string;
               description "IP address of the neighbor for the BFD session";
             }
             leaf session-state {
               type string;
               description "BFD session state";
             }
             leaf session-interface {
               type string;
               description "Name of the interface on which the BFD session is active";
             }
             leaf session-detection-time {
               type string;
               description "Time period within which the host must receive BFD controlpackets to continue considering the session active (seconds)";
             }
             leaf session-transmission-interval {
               type int32;
               description "Frequency at which the host system sends BFD controlpackets (seconds)";
             }
             leaf session-adaptive-multiplier {
               type int32;
               description "The adjusted value of detect multiplier.";
             }
             container bfd-client {
               description "Information about the clients";
               leaf client-name {
                 type string;
                 description "Protocol for which the BFD session is active (forexample: OSPF, ISIS, Static, and so on) ";
               }
               leaf client-transmission-interval {
                 type int32;
                 description "Base frequency that the client proposes for sending BFDcontrol packets (seconds)";
               }
               leaf client-reception-interval {
                 type int32;
                 description "Base frequency that the client has proposed for peersto send BFD control packets (seconds)";
               }
               leaf client-multiplier {
                 type int32;
                 description "Multiplier that the client has requested to determine theliveness of the BFD session.";
               }
               leaf client-authentication {
                 type string;
                 description "Client requested authentication";
               }
               leaf client-holddown-interval {
                 type string;
                 description "Hold interval for which BFD does not send a session UP notification to the client (seconds)";
               }
               leaf client-state {
                 type string;
                 description "Tells whether client is in holddown or not";
               }
               leaf client-keychain {
                 type string;
                 description "Client requested keychain name";
               }
               leaf client-algorithm {
                 type int32;
                 description "Client requested algorithm";
               }
               leaf client-authentication-loose {
                 type string;
                 description "Client requested mode";
               }
             }
           }
         }
         container detail {
           leaf sessions {
             type int32;
             description "Total number of active BFD sessions";
           }
           leaf clients {
             type int32;
             description "Total number of clients that are hosting BFD sessions";
           }
           leaf up-sessions {
             type string;
             description "Total number of BFD sessions which are UP";
           }
           leaf down-sessions {
             type string;
             description "Total number of BFD sessions which are not UP";
           }
           leaf cumulative-transmission-rate {
             type int32;
             description "Number of BFD control packets transmitted per second inall active sessions";
           }
           leaf cumulative-reception-rate {
             type int32;
             description "Number of BFD control packets received per second inall active sessions";
           }
           leaf cumulative-up-time {
             type string;
             description "Time taken to being up bfd sesison";
           }
           container bfd-session {
             description "Information about bidirectional forwarding detection session";
             leaf session-neighbor {
               type string;
               description "IP address of the neighbor for the BFD session";
             }
             leaf session-state {
               type string;
               description "BFD session state";
             }
             leaf session-interface {
               type string;
               description "Name of the interface on which the BFD session is active";
             }
             leaf session-detection-time {
               type string;
               description "Time period within which the host must receive BFD controlpackets to continue considering the session active (seconds)";
             }
             leaf session-transmission-interval {
               type int32;
               description "Frequency at which the host system sends BFD controlpackets (seconds)";
             }
             leaf session-adaptive-multiplier {
               type int32;
               description "The adjusted value of detect multiplier.";
             }
             leaf session-up-time {
               type string;
               description "Time since the current session began (hours:minutes:seconds)";
             }
             leaf previous-down-time {
               type string;
               description "Amount of time the previous session was down(hours:minutes:seconds)";
             }
             leaf session-down-time {
               type string;
               description "Time for which the current session was down(hours:minutes:seconds)";
             }
             leaf previous-up-time {
               type string;
               description "Duration of the previous session (hours:minutes:seconds)";
             }
             leaf local-diagnostic {
               type string;
               description "Information provided by the local host about BFD sessionsthat have failed (for example if the node is administrativelydown or a control timer has expired)";
             }
             leaf remote-diagnostic {
               type string;
               description "Information provided by the remote host about BFD sessionsthat have failed (for example if the node is administrativelydown or a control timer has expired)";
             }
             leaf v0-remote-state {
               type string;
               description "(BFD version 0 only.) Indicates whether the local system is receiving BFD control packets from the remote system.";
             }
             leaf remote-listen {
               type string;
               description "(BFD version 0 only.) Indicates whether the remote system isreceiving control packets transmitted by the local system.";
             }
             leaf remote-state {
               type string;
               description "(BFD version 1 only.) Indicates the remote session state";
             }
             leaf session-version {
               type int32;
               description "Version of the BFD protocol being used for the session";
             }
             leaf logical-system-id {
               type int32;
               description "Logical system on which the session is established";
             }
             leaf route-table-index {
               type int32;
               description "Routing table index for the current logical system";
             }
             leaf replicated {
               type string;
               description "Indicates whether the session is replicated between master andstandby RE";
             }
             leaf session-type {
               type string;
               description "Indicates the flavor of the BFD session";
             }
             container bfd-client {
               description "Information about the clients";
               leaf client-name {
                 type string;
                 description "Protocol for which the BFD session is active (forexample: OSPF, ISIS, Static, and so on) ";
               }
               leaf client-transmission-interval {
                 type int32;
                 description "Base frequency that the client proposes for sending BFDcontrol packets (seconds)";
               }
               leaf client-reception-interval {
                 type int32;
                 description "Base frequency that the client has proposed for peersto send BFD control packets (seconds)";
               }
               leaf client-multiplier {
                 type int32;
                 description "Multiplier that the client has requested to determine theliveness of the BFD session.";
               }
               leaf client-authentication {
                 type string;
                 description "Client requested authentication";
               }
               leaf client-holddown-interval {
                 type string;
                 description "Hold interval for which BFD does not send a session UP notification to the client (seconds)";
               }
               leaf client-state {
                 type string;
                 description "Tells whether client is in holddown or not";
               }
               leaf client-keychain {
                 type string;
                 description "Client requested keychain name";
               }
               leaf client-algorithm {
                 type int32;
                 description "Client requested algorithm";
               }
               leaf client-authentication-loose {
                 type string;
                 description "Client requested mode";
               }
             }
           }
         }
         container extensive {
           leaf sessions {
             type int32;
             description "Total number of active BFD sessions";
           }
           leaf clients {
             type int32;
             description "Total number of clients that are hosting BFD sessions";
           }
           leaf up-sessions {
             type string;
             description "Total number of BFD sessions which are UP";
           }
           leaf down-sessions {
             type string;
             description "Total number of BFD sessions which are not UP";
           }
           leaf cumulative-transmission-rate {
             type int32;
             description "Number of BFD control packets transmitted per second inall active sessions";
           }
           leaf cumulative-reception-rate {
             type int32;
             description "Number of BFD control packets received per second inall active sessions";
           }
           leaf cumulative-up-time {
             type string;
             description "Time taken to being up bfd sesison";
           }
           container bfd-session {
             description "Information about bidirectional forwarding detection session";
             leaf session-neighbor {
               type string;
               description "IP address of the neighbor for the BFD session";
             }
             leaf session-state {
               type string;
               description "BFD session state";
             }
             leaf session-interface {
               type string;
               description "Name of the interface on which the BFD session is active";
             }
             leaf session-detection-time {
               type string;
               description "Time period within which the host must receive BFD controlpackets to continue considering the session active (seconds)";
             }
             leaf session-transmission-interval {
               type int32;
               description "Frequency at which the host system sends BFD controlpackets (seconds)";
             }
             leaf session-adaptive-multiplier {
               type int32;
               description "The adjusted value of detect multiplier.";
             }
             leaf session-up-time {
               type string;
               description "Time since the current session began (hours:minutes:seconds)";
             }
             leaf previous-down-time {
               type string;
               description "Amount of time the previous session was down(hours:minutes:seconds)";
             }
             leaf session-down-time {
               type string;
               description "Time for which the current session was down(hours:minutes:seconds)";
             }
             leaf previous-up-time {
               type string;
               description "Duration of the previous session (hours:minutes:seconds)";
             }
             leaf local-diagnostic {
               type string;
               description "Information provided by the local host about BFD sessionsthat have failed (for example if the node is administrativelydown or a control timer has expired)";
             }
             leaf remote-diagnostic {
               type string;
               description "Information provided by the remote host about BFD sessionsthat have failed (for example if the node is administrativelydown or a control timer has expired)";
             }
             leaf v0-remote-state {
               type string;
               description "(BFD version 0 only.) Indicates whether the local system is receiving BFD control packets from the remote system.";
             }
             leaf remote-listen {
               type string;
               description "(BFD version 0 only.) Indicates whether the remote system isreceiving control packets transmitted by the local system.";
             }
             leaf remote-state {
               type string;
               description "(BFD version 1 only.) Indicates the remote session state";
             }
             leaf session-version {
               type int32;
               description "Version of the BFD protocol being used for the session";
             }
             leaf logical-system-id {
               type int32;
               description "Logical system on which the session is established";
             }
             leaf route-table-index {
               type int32;
               description "Routing table index for the current logical system";
             }
             leaf replicated {
               type string;
               description "Indicates whether the session is replicated between master andstandby RE";
             }
             leaf session-type {
               type string;
               description "Indicates the flavor of the BFD session";
             }
             leaf minimum-asynchronous-interval {
               type int32;
               description "Minimum amount of time that the local system proposes forthe delay between transmission of asynchronous control packetsacross the BFD session (seconds)";
             }
             leaf minimum-slow-interval {
               type int32;
               description "Either one second or the minimum asynchronous interval,whichever is greater";
             }
             leaf adaptive-asynchronous-transmission-interval {
               type int32;
               description "Minimum asynchronous interval used when there is routeflapping";
             }
             leaf adaptive-reception-interval {
               type int32;
               description "Adjusted value of minimum reception interval.";
             }
             leaf minimum-transmission-interval {
               type int32;
               description "Minimum amount of time that the local system proposes forthe delay between transmission of control packets across theBFD session (seconds). It is either the minimum slow interval orthe adaptive asynchronous transmission interval";
             }
             leaf minimum-reception-interval {
               type int32;
               description "Minimum amount of time that the local system waits betweenchecks for newly received control packets (seconds)";
             }
             leaf detection-multiplier {
               type int32;
               description "Desired detect time multiplier for BFD control packets.It is multiplied by the negotiated control packet receptioninterval to determine the session detection time (time todetect whether the session is alive).";
             }
             leaf neighbor-minimum-transmission-interval {
               type int32;
               description "Minimum amount of time that the remote system proposes forthe delay between transmission of control packets across the BFDsession (seconds)";
             }
             leaf neighbor-minimum-reception-interval {
               type int32;
               description "Minimum amount of time that the remote system waits betweenchecks for newly received control packets (seconds)";
             }
             leaf neighbor-session-multiplier {
               type int32;
               description "Neighbor's detection multiplier";
             }
             leaf issu-state {
               type string;
               description "ISSU state of the session";
             }
             leaf original-transmission-interval {
               type int32;
               description "Original pre-ISSU transmission interval";
             }
             leaf original-reception-interval {
               type int32;
               description "Original pre-ISSU reception interval";
             }
             leaf local-discriminator {
               type int32;
               description "Authentication code used by the local system to identify theBFD session";
             }
             leaf remote-discriminator {
               type int32;
               description "Authentication code used by the remote system to identify theBFD session";
             }
             leaf threshold-transmission-interval {
               type int32;
               description "The maximum duration (in seconds) for the transmissioninterval before an SNMP trap is generated";
             }
             leaf threshold-detection-time {
               type int32;
               description "The maximum duration (in seconds) for the detection timebefore an SNMP trap is generated";
             }
             leaf authentication {
               type string;
               description "Authentication status";
             }
             leaf session-keychain {
               type string;
               description "Authentication status";
             }
             leaf session-algorithm {
               type int32;
               description "Session authentication algorithm";
             }
             leaf session-authentication-loose {
               type int32;
               description "Session authentication mode";
             }
             leaf neighbor-fate {
               type string;
               description "Indicates whether the remote system is control-planeindependent";
             }
             leaf adaptation-disabled {
               type string;
               description "Indicates whether adaptation has been disabled";
             }
             leaf holddown-timer {
               type string;
               description "Status of version negotiation";
             }
             leaf l2ckt-neighbor-address {
               type string;
               description "L2circuit neighbor address";
             }
             leaf l2ckt-vc-id {
               type int32;
               description "L2circuit virtual circuit id";
             }
             leaf l2vpn-local-site-id {
               type int32;
               description "Local site id of the L2vpn";
             }
             leaf l2vpn-remote-site-id {
               type int32;
               description "Remote site id of the L2vpn";
             }
             leaf l2vpn-fec129-agi {
               type string;
               description "AGI of the L2vpn";
             }
             leaf l2vpn-fec129-saii {
               type string;
               description "SAII of the L2vpn";
             }
             leaf l2vpn-fec129-taii {
               type string;
               description "TAII of the L2vpn";
             }
             leaf tunnel-name {
               type string;
               description "Name of the BFD tunnel";
             }
             leaf tunnel-path {
               type string;
               description "Path of the BFD tunnel";
             }
             leaf tunnel-prefix {
               type string;
               description "Prefix for the Label Distribution Protocol tunnel";
             }
             leaf tunnel-prefix-length {
               type int32;
               description "Length of prefix for the Label Distribution Protocol tunnel";
             }
             leaf tunnel-type {
               type string;
               description "Type of tunnel";
             }
             leaf tunnel-destination {
               type string;
               description "Destination for the Label Distribution Protocol tunnel";
             }
             leaf multihop {
               type string;
               description "Multihop session";
             }
             leaf multihop-time-to-live {
               type int32;
               description "Time-to-live for multihop session";
             }
             leaf multihop-routing-table-index {
               type int32;
               description "Multihop session index in the routing table ";
             }
             leaf multihop-local-address {
               type string;
               description "Multihop local address";
             }
             leaf echo-mode-desired {
               type string;
               description "Indicates whether the local system proposes that echotransmissions be enabled for the BFD session";
             }
             leaf echo-mode-state {
               type string;
               description "Indicates whether echo transmissions are enabled for theBFD session";
             }
             leaf no-absorb {
               type string;
               description "Incoming packets are not absorbed";
             }
             leaf no-refresh {
               type string;
               description "The adjacency is not refreshed";
             }
             leaf update-adjacency {
               type string;
               description "Indicates whether the adjacency needs to be updated";
             }
             leaf update-transmit {
               type string;
               description "Indicates whether a transmission needs to be updated";
             }
             container bfd-client {
               description "Information about the clients";
               leaf client-name {
                 type string;
                 description "Protocol for which the BFD session is active (forexample: OSPF, ISIS, Static, and so on) ";
               }
               leaf client-transmission-interval {
                 type int32;
                 description "Base frequency that the client proposes for sending BFDcontrol packets (seconds)";
               }
               leaf client-reception-interval {
                 type int32;
                 description "Base frequency that the client has proposed for peersto send BFD control packets (seconds)";
               }
               leaf client-multiplier {
                 type int32;
                 description "Multiplier that the client has requested to determine theliveness of the BFD session.";
               }
               leaf client-authentication {
                 type string;
                 description "Client requested authentication";
               }
               leaf client-holddown-interval {
                 type string;
                 description "Hold interval for which BFD does not send a session UP notification to the client (seconds)";
               }
               leaf client-state {
                 type string;
                 description "Tells whether client is in holddown or not";
               }
               leaf client-keychain {
                 type string;
                 description "Client requested keychain name";
               }
               leaf client-algorithm {
                 type int32;
                 description "Client requested algorithm";
               }
               leaf client-authentication-loose {
                 type string;
                 description "Client requested mode";
               }
             }
           }
         }
         container trace-info {
           leaf sessions {
             type int32;
             description "Total number of active BFD sessions";
           }
           leaf clients {
             type int32;
             description "Total number of clients that are hosting BFD sessions";
           }
           leaf up-sessions {
             type string;
             description "Total number of BFD sessions which are UP";
           }
           leaf down-sessions {
             type string;
             description "Total number of BFD sessions which are not UP";
           }
           leaf cumulative-transmission-rate {
             type int32;
             description "Number of BFD control packets transmitted per second inall active sessions";
           }
           leaf cumulative-reception-rate {
             type int32;
             description "Number of BFD control packets received per second inall active sessions";
           }
           leaf cumulative-up-time {
             type string;
             description "Time taken to being up bfd sesison";
           }
           container bfd-session {
             description "Information about bidirectional forwarding detection session";
             leaf session-neighbor {
               type string;
               description "IP address of the neighbor for the BFD session";
             }
             leaf session-state {
               type string;
               description "BFD session state";
             }
             leaf session-interface {
               type string;
               description "Name of the interface on which the BFD session is active";
             }
             leaf session-detection-time {
               type string;
               description "Time period within which the host must receive BFD controlpackets to continue considering the session active (seconds)";
             }
             leaf session-transmission-interval {
               type int32;
               description "Frequency at which the host system sends BFD controlpackets (seconds)";
             }
             leaf session-adaptive-multiplier {
               type int32;
               description "The adjusted value of detect multiplier.";
             }
             leaf session-up-time {
               type string;
               description "Time since the current session began (hours:minutes:seconds)";
             }
             leaf previous-down-time {
               type string;
               description "Amount of time the previous session was down(hours:minutes:seconds)";
             }
             leaf session-down-time {
               type string;
               description "Time for which the current session was down(hours:minutes:seconds)";
             }
             leaf previous-up-time {
               type string;
               description "Duration of the previous session (hours:minutes:seconds)";
             }
             leaf local-diagnostic {
               type string;
               description "Information provided by the local host about BFD sessionsthat have failed (for example if the node is administrativelydown or a control timer has expired)";
             }
             leaf remote-diagnostic {
               type string;
               description "Information provided by the remote host about BFD sessionsthat have failed (for example if the node is administrativelydown or a control timer has expired)";
             }
             leaf v0-remote-state {
               type string;
               description "(BFD version 0 only.) Indicates whether the local system is receiving BFD control packets from the remote system.";
             }
             leaf remote-listen {
               type string;
               description "(BFD version 0 only.) Indicates whether the remote system isreceiving control packets transmitted by the local system.";
             }
             leaf remote-state {
               type string;
               description "(BFD version 1 only.) Indicates the remote session state";
             }
             leaf session-version {
               type int32;
               description "Version of the BFD protocol being used for the session";
             }
             leaf logical-system-id {
               type int32;
               description "Logical system on which the session is established";
             }
             leaf route-table-index {
               type int32;
               description "Routing table index for the current logical system";
             }
             leaf replicated {
               type string;
               description "Indicates whether the session is replicated between master andstandby RE";
             }
             leaf session-type {
               type string;
               description "Indicates the flavor of the BFD session";
             }
             leaf minimum-asynchronous-interval {
               type int32;
               description "Minimum amount of time that the local system proposes forthe delay between transmission of asynchronous control packetsacross the BFD session (seconds)";
             }
             leaf minimum-slow-interval {
               type int32;
               description "Either one second or the minimum asynchronous interval,whichever is greater";
             }
             leaf adaptive-asynchronous-transmission-interval {
               type int32;
               description "Minimum asynchronous interval used when there is routeflapping";
             }
             leaf adaptive-reception-interval {
               type int32;
               description "Adjusted value of minimum reception interval.";
             }
             leaf minimum-transmission-interval {
               type int32;
               description "Minimum amount of time that the local system proposes forthe delay between transmission of control packets across theBFD session (seconds). It is either the minimum slow interval orthe adaptive asynchronous transmission interval";
             }
             leaf minimum-reception-interval {
               type int32;
               description "Minimum amount of time that the local system waits betweenchecks for newly received control packets (seconds)";
             }
             leaf detection-multiplier {
               type int32;
               description "Desired detect time multiplier for BFD control packets.It is multiplied by the negotiated control packet receptioninterval to determine the session detection time (time todetect whether the session is alive).";
             }
             leaf neighbor-minimum-transmission-interval {
               type int32;
               description "Minimum amount of time that the remote system proposes forthe delay between transmission of control packets across the BFDsession (seconds)";
             }
             leaf neighbor-minimum-reception-interval {
               type int32;
               description "Minimum amount of time that the remote system waits betweenchecks for newly received control packets (seconds)";
             }
             leaf neighbor-session-multiplier {
               type int32;
               description "Neighbor's detection multiplier";
             }
             leaf issu-state {
               type string;
               description "ISSU state of the session";
             }
             leaf original-transmission-interval {
               type int32;
               description "Original pre-ISSU transmission interval";
             }
             leaf original-reception-interval {
               type int32;
               description "Original pre-ISSU reception interval";
             }
             leaf local-discriminator {
               type int32;
               description "Authentication code used by the local system to identify theBFD session";
             }
             leaf remote-discriminator {
               type int32;
               description "Authentication code used by the remote system to identify theBFD session";
             }
             leaf threshold-transmission-interval {
               type int32;
               description "The maximum duration (in seconds) for the transmissioninterval before an SNMP trap is generated";
             }
             leaf threshold-detection-time {
               type int32;
               description "The maximum duration (in seconds) for the detection timebefore an SNMP trap is generated";
             }
             leaf authentication {
               type string;
               description "Authentication status";
             }
             leaf session-keychain {
               type string;
               description "Authentication status";
             }
             leaf session-algorithm {
               type int32;
               description "Session authentication algorithm";
             }
             leaf session-authentication-loose {
               type int32;
               description "Session authentication mode";
             }
             leaf neighbor-fate {
               type string;
               description "Indicates whether the remote system is control-planeindependent";
             }
             leaf adaptation-disabled {
               type string;
               description "Indicates whether adaptation has been disabled";
             }
             leaf holddown-timer {
               type string;
               description "Status of version negotiation";
             }
             leaf l2ckt-neighbor-address {
               type string;
               description "L2circuit neighbor address";
             }
             leaf l2ckt-vc-id {
               type int32;
               description "L2circuit virtual circuit id";
             }
             leaf l2vpn-local-site-id {
               type int32;
               description "Local site id of the L2vpn";
             }
             leaf l2vpn-remote-site-id {
               type int32;
               description "Remote site id of the L2vpn";
             }
             leaf l2vpn-fec129-agi {
               type string;
               description "AGI of the L2vpn";
             }
             leaf l2vpn-fec129-saii {
               type string;
               description "SAII of the L2vpn";
             }
             leaf l2vpn-fec129-taii {
               type string;
               description "TAII of the L2vpn";
             }
             leaf tunnel-name {
               type string;
               description "Name of the BFD tunnel";
             }
             leaf tunnel-path {
               type string;
               description "Path of the BFD tunnel";
             }
             leaf tunnel-prefix {
               type string;
               description "Prefix for the Label Distribution Protocol tunnel";
             }
             leaf tunnel-prefix-length {
               type int32;
               description "Length of prefix for the Label Distribution Protocol tunnel";
             }
             leaf tunnel-type {
               type string;
               description "Type of tunnel";
             }
             leaf tunnel-destination {
               type string;
               description "Destination for the Label Distribution Protocol tunnel";
             }
             leaf multihop {
               type string;
               description "Multihop session";
             }
             leaf multihop-time-to-live {
               type int32;
               description "Time-to-live for multihop session";
             }
             leaf multihop-routing-table-index {
               type int32;
               description "Multihop session index in the routing table ";
             }
             leaf multihop-local-address {
               type string;
               description "Multihop local address";
             }
             leaf echo-mode-desired {
               type string;
               description "Indicates whether the local system proposes that echotransmissions be enabled for the BFD session";
             }
             leaf echo-mode-state {
               type string;
               description "Indicates whether echo transmissions are enabled for theBFD session";
             }
             leaf no-absorb {
               type string;
               description "Incoming packets are not absorbed";
             }
             leaf no-refresh {
               type string;
               description "The adjacency is not refreshed";
             }
             leaf update-adjacency {
               type string;
               description "Indicates whether the adjacency needs to be updated";
             }
             leaf update-transmit {
               type string;
               description "Indicates whether a transmission needs to be updated";
             }
             leaf trace-session-type {
               type string;
               description "Trace session type";
             }
             leaf trace-rtbl-index {
               type int32;
               description "Route table Index";
             }
             leaf trace-ifl-index {
               type int32;
               description "Interface index";
             }
             leaf trace-src-addr {
               type string;
               description "Source address";
             }
             leaf trace-dest-addr {
               type string;
               description "Destination address";
             }
             leaf trace-tunnel-label {
               type int32;
               description "Tunnel label for PW";
             }
             leaf trace-bundle-ifd {
               type int32;
               description "Bundle ifd";
             }
             leaf trace-bundle-af {
               type int32;
               description "Bundle family";
             }
             leaf trace-session-enabled {
               type string;
               description "Session tracing status";
             }
             container bfd-client {
               description "Information about the clients";
               leaf client-name {
                 type string;
                 description "Protocol for which the BFD session is active (forexample: OSPF, ISIS, Static, and so on) ";
               }
               leaf client-transmission-interval {
                 type int32;
                 description "Base frequency that the client proposes for sending BFDcontrol packets (seconds)";
               }
               leaf client-reception-interval {
                 type int32;
                 description "Base frequency that the client has proposed for peersto send BFD control packets (seconds)";
               }
               leaf client-multiplier {
                 type int32;
                 description "Multiplier that the client has requested to determine theliveness of the BFD session.";
               }
               leaf client-authentication {
                 type string;
                 description "Client requested authentication";
               }
               leaf client-holddown-interval {
                 type string;
                 description "Hold interval for which BFD does not send a session UP notification to the client (seconds)";
               }
               leaf client-state {
                 type string;
                 description "Tells whether client is in holddown or not";
               }
               leaf client-keychain {
                 type string;
                 description "Client requested keychain name";
               }
               leaf client-algorithm {
                 type int32;
                 description "Client requested algorithm";
               }
               leaf client-authentication-loose {
                 type string;
                 description "Client requested mode";
               }
             }
           }
         }
       }
     }
   }
   rpc get-bfd-session-revert {
     description "Show BFD session on revert thread";
     input {
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
   }
   rpc get-bfd-session-address {
     description "Show BFD session with specific neighbor address";
     input {
       leaf session_addr {
         description "Neighbor address of session";
         type ipaddr;
         mandatory true;
       }
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
   }
   rpc get-bfd-session-discriminator {
     description "Show BFD session with specific local discriminator";
     input {
       leaf discr_number {
         description "Local discriminator of session";
         type uint32;
         mandatory true;
       }
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
   }
   rpc get-bfd-session-client {
     description "Show all BFD sessions of a particular client";
   }
   rpc get-bfd-session-client-rsvp {
     description "Show RSVP-OAM BFD sessions";
     input {
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
     }
   }
   rpc get-bfd-session-client-vpls {
     description "Show VPLS-OAM BFD sessions";
     input {
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
     }
   }
   rpc get-bfd-session-client-vpls-instance {
     description "Show vpls bfd sessions under the instance";
     input {
       leaf routing-instance {
         description "Name of routing instance";
         type string {
           junos:posix-pattern "!^((__.*__)|(all)|(.*[ ].*)|()|(.{129,}))$";
           junos:pattern-message "Must be a non-reserved string of 128 characters or less with no spaces.";
         }
         mandatory true;
       }
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
     }
   }
   rpc get-bfd-session-prefix {
     description "Show all BFD sessions for this LDP FEC";
     input {
       leaf prefix_addr {
         description "Prefix address of session";
         type ipprefix;
         mandatory true;
       }
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
   }
   rpc get-bfd-subscriber-session {
     description "Show subscriber session info";
     input {
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
     }
   }
 }
