/*
 * Copyright (c) 2017 Juniper Networks, Inc.
 * All rights reserved.
 */

 module show-dot1x {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-dot1x-interface-information {
     description "Show 802.1X interface information";
     input {
       leaf verbosity_level {
         default "brief";
         type enumeration {
           enum "brief" {
             description "Display brief output (default)";
           }
           enum "detail" {
             description "Display detailed output";
           }
         }
       }
       leaf interface-name {
         description "Name of interface";
         type interface-name;
       }
     }
     output {
       container dot1x-interface-information {
         container interface {
           container brief {
             leaf interface-name {
               type string;
             }
             leaf role {
               type string;
               description "Role of interface";
             }
             leaf state {
               type string;
               description "Current state of interface";
             }
             leaf user-mac-address {
               type mac-addr;
               description "MAC address of client";
             }
             leaf user-name {
               type string;
               description "User name as sent by client for authentication";
             }
             container supplicant-list {
             }
           }
           container detail {
             leaf interface-name {
               type string;
             }
             leaf role {
               type string;
               description "Role of interface";
             }
             leaf administrative-state {
               type string;
               description "Administrative state of port";
             }
             leaf administrative-mode {
               type string;
               description "Supplicant authorization mode";
             }
             leaf number-of-retries {
               type uint32;
               description "Number of retries after which port is placed into wait state";
             }
             leaf quiet-period {
               type uint32;
               description "Time to wait after authentication failure";
             }
             leaf transmit-period {
               type uint32;
               description "Interval before retransmitting initial EAPOL PDUs";
             }
             leaf mac-radius {
               type string;
               description "MAC-RADIUS status";
             }
             leaf mac-radius-strict {
               type string;
               description "MAC-RADIUS-STRICT status";
             }
             leaf mac-radius-protocol {
               type string;
               description "MAC-RADIUS-PROTOCOL status";
             }
             leaf reauthentication {
               type string;
               description "Reauthentication status";
             }
             leaf reauthentication-interval {
               type uint32;
               description "Reauthentication interval";
             }
             leaf supplicant-timeout {
               type uint32;
               description "Time to wait for response from supplicant before resending request";
             }
             leaf server-timeout {
               type uint32;
               description "Time to wait before invoking server-fail action";
             }
             leaf max-eapol-request {
               type uint32;
               description "Maximum number of EAPOL request IDs to client";
             }
             leaf frame-control {
               type string;
               description "Block only ingress traffic before authentication";
             }
             leaf guest-vlan {
               type string;
               description "VLAN members for unauthenticated or non-responsive hosts";
             }
             leaf number-of-connected-supplicants {
               type uint32;
               description "Number of connected supplicants";
             }
             container supplicant-list {
               container supplicant {
               }
             }
           }
         }
         container dot1x-static-mac-address {
           description "Information about configured static MAC addresses";
           leaf static-mac-address {
             type mac-addr;
             description "MAC address configured for bypass";
           }
           leaf static-mac-prefix {
             type int32;
             description "MAC prefix configured for bypass clients";
           }
           leaf static-mac-vlan-assignment {
             type string;
             description "VLAN assigned to the client with this MAC address";
           }
           leaf static-mac-interface {
             type string;
             description "Interface on which client MAC was learned";
           }
         }
         container dot1x-accounting-attribute {
           description "Information about dot1x session accounting attributes";
           leaf dot1x-accounting-attribute-user {
             type string;
             description "User name as sent by the supplicant for authentication";
           }
           leaf dot1x-accounting-attribute-mac-address {
             type string;
             description "MAC address of the supplicant";
           }
           leaf dot1x-accounting-attribute-nas-port {
             type int32;
             description "NAS Port AVP(5)";
           }
           leaf dot1x-accounting-attribute-nas-port-id {
             type string;
             description "NAS Port ID AVP(87)";
           }
           leaf dot1x-accounting-attribute-called-station-id {
             type string;
             description "Called Station Id AVP(30)";
           }
           leaf dot1x-accounting-attribute-calling-station-id {
             type string;
             description "Calling Station Id AVP(31)";
           }
           leaf dot1x-accounting-attribute-framed-ip-address {
             type string;
             description "Framed IP Address AVP(8)";
           }
           leaf dot1x-accounting-attribute-filter-id {
             type string;
             description "Filter ID AVP(11)";
           }
           leaf dot1x-accounting-attribute-framed-mtu {
             type int32;
             description "Framed MTU AVP(12)";
           }
           leaf dot1x-accounting-attribute-client-system-name {
             type string;
             description "Client System Name AVP(26)";
           }
           leaf dot1x-accounting-attribute-session-timeout {
             type int32;
             description "Session Timeout AVP(27)";
           }
           leaf dot1x-accounting-attribute-acct-authentic {
             type string;
             description "Acct Authentic Cause(45)";
           }
           leaf dot1x-accounting-attribute-nas-identifier {
             type string;
             description "NAS Identifier(32)";
           }
           leaf dot1x-accounting-attribute-acct-status {
             type string;
             description "Acct Status Type(40)";
           }
           leaf dot1x-accounting-attribute-acct-session {
             type int32;
             description "Acct Session Id(44)";
           }
         }
         container dot1x-authentication-failed-users {
           description "List of users who failed authentication";
           leaf authentication-failed-interface {
             type string;
             description "Interface used in failed authentication";
           }
           leaf authentication-failed-mac-addr {
             type mac-addr;
             description "MAC address used by user who failed authentication";
           }
           leaf authentication-failed-user {
             type string;
             description "Users who failed authentication";
           }
           leaf authentication-failed-count {
             type int32;
             description "Number of failed authentication attempts";
           }
         }
         container dot1x-interface-statistics {
           description "Display interface statistics";
           container statistics {
             description "Display interface statistics";
             leaf eapol-interface-name {
               type string;
               description "Interface name";
             }
             leaf eapol-request-id-frames {
               type int32;
               description "Number of EAPOL Request ID packets transmitted";
             }
             leaf eapol-request-frames {
               type int32;
               description "Number of EAPOL Request packets transmitted";
             }
             leaf eapol-total-transmitted-packets {
               type int32;
               description "Total Number of EAPOL packets transmitted";
             }
             leaf eapol-start-frames {
               type int32;
               description "Number of EAPOL START packets received";
             }
             leaf eapol-logoff-frames {
               type int32;
               description "Number of EAPOL LOGOFF packets received";
             }
             leaf eapol-response-id-frames {
               type int32;
               description "Number of EAPOL Response ID packets received";
             }
             leaf eapol-response-frames {
               type int32;
               description "Number of EAPOL Response packets received";
             }
             leaf coa-request-frames {
               type int32;
               description "Number of CoA Request packets received";
             }
             leaf coa-ack-frames {
               type int32;
               description "Number of EAPOL Request packets transmitted";
             }
             leaf coa-nak-frames {
               type int32;
               description "Number of EAPOL Request packets transmitted";
             }
             leaf eapol-invalid-frames {
               type int32;
               description "Number of Invalid EAPOL packets received";
             }
             leaf eapol-length-error-frames {
               type int32;
               description "Number of invalid length EAPOL packets received";
             }
             leaf eapol-total-received-frames {
               type int32;
               description "Total Number of EAPOL packets received";
             }
             leaf eapol-lastframe-version {
               type int32;
               description "Version of the last EAPOL packet received";
             }
             leaf eapol-lastframe-macaddress {
               type string;
               description "Source Mac Address of last frame received";
             }
           }
         }
         container dot1x-staticmac-bypassed-users {
           description "List of users who bypassed authentication";
           container static-mac-info {
             leaf static-mac-bypass {
               type mac-addr;
               description "MAC address of bypassed client";
             }
             leaf static-mac-bypass-interface {
               type string;
               description "Interface on which MAC address is bypassed";
             }
             leaf static-mac-bypass-vlan {
               type string;
               description "VLAN of bypassed client";
             }
           }
         }
         container dot1x-firewall-interface {
           container firewall {
             leaf filter-name {
               type string;
               description "Filter name";
             }
           }
           container brief {
             leaf counter-name {
               type string;
               description "Counter name";
             }
             leaf bytes {
               type uint32;
               description "Number of bytes";
             }
             leaf packets {
               type uint32;
               description "Number of Packets";
             }
           }
           container policer {
             leaf policer-name {
               type string;
               description "Policer name";
             }
             leaf packet-count {
               type uint32;
               description "Number of Packets";
             }
           }
         }
       }
     }
   }
   rpc get-dot1x-static-mac-addresess {
     description "Show 802.1X static MAC addresses";
   }
   rpc get-dot1x-interface-mac-addresses {
     description "Show 802.1X static MAC addresses on this interface";
     input {
       leaf interface-name {
         description "Show static MAC addresses of interface";
         type interface-name;
       }
     }
   }
   rpc get-dot1x-accounting-attributes {
     description "Show 802.1x accounting attributes";
   }
   rpc get-dot1x-interface-accounting-attributes {
     description "Show 802.1x accounting attributes on this interface";
     input {
       leaf interface-name {
         description "Show accounting attributes";
         type interface-name;
       }
     }
   }
   rpc get-dot1x-authentication-failed-users {
     description "List users who have failed 802.1X authentication";
   }
   rpc get-static-mac-bypassed-users {
     description "List users who have bypassed 802.1X authentication";
   }
   rpc get-dot1x-statistics {
     description "Show 802.1X statistics";
   }
   rpc get-dot1x-statistics-interface {
     description "Show 802.1X statistics on this interface";
     input {
       leaf interface-name {
         description "Show statistics for this interface";
         default "all";
         type interface-name;
       }
     }
   }
   rpc get-dot1x-firewall-interface {
     description "Show dot1x firewall statistics for an interface";
     input {
       leaf interface-name {
         description "Show firewall statistics for this interface";
         type interface-name;
       }
     }
   }
 }
