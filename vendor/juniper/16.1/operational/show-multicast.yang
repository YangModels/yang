/*
 * Copyright (c) 2017 Juniper Networks, Inc.
 * All rights reserved.
 */

 module show-multicast {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-mc-fwd-cache-information {
     description "Show multicast forwarding cache statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf family {
         description "Address Family";
         type enumeration {
           enum "inet" {
             description "Display IPv4 information";
           }
           enum "inet6" {
             description "Display IPv6 information";
           }
         }
       }
     }
     output {
       container mc-fwd-cache-information {
         container mc-fwd-cache-threshold {
           leaf mc-instance {
             type string;
             description "Multicast Instance";
           }
           leaf mc-fwd-cache-family {
             type string;
             description "Multicast address family";
           }
           container mc-cache-params {
             leaf mc-cache-param-name {
               type string;
               description "Multicast Fwd Cache Parameter";
             }
             leaf mc-cache-param-value {
               type uint32;
               description "Multicast Fwd Cache parameter value";
             }
           }
         }
       }
     }
   }
   rpc get-multicast-route-information {
     description "Show the multicast routing table";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf mode {
         default "all";
         type enumeration {
           enum "all" {
             description "Display all route entries";
           }
           enum "active" {
             description "Display active route entries";
           }
           enum "inactive" {
             description "Display inactive route entries";
           }
         }
       }
       leaf verbosity_level {
         default "brief";
         type enumeration {
           enum "summary" {
             description "Display summary output";
           }
           enum "brief" {
             description "Display brief output (default)";
           }
           enum "detail" {
             description "Display detailed output";
           }
           enum "extensive" {
             description "Display extensive output";
           }
         }
       }
       leaf family {
         description "Address family";
         default "inet";
         type enumeration {
           enum "inet" {
             description "Display IPv4 information";
           }
           enum "inet6" {
             description "Display IPv6 information";
           }
         }
       }
       leaf table {
         description "Entries in a particular routing table";
         status deprecated;
         type string;
       }
       leaf group {
         description "IP address and optional prefix length of group";
         type ipprefix;
       }
       leaf source-prefix {
         description "IP address and optional prefix length of source for routes";
         type ipprefix;
       }
       leaf regexp {
         description "Regular expression for session to match";
         type string;
       }
       leaf display-tunnel-name {
         description "Display provider tunnel name instead of branch information";
         type empty;
       }
       leaf display-origin-protocol {
         description "Display originating protocol instead of upstream protocol";
         type empty;
       }
       leaf oif-count {
         description "Display outgoing interface count instead of list";
         type empty;
       }
     }
     output {
       container multicast-route-information {
         leaf multicast-route-no-group-prefix {
           type ipaddr;
         }
         leaf multicast-route-no-family {
           type string;
         }
         container route-family {
           leaf multicast-instance {
             type string;
           }
           leaf address-family {
             type string;
           }
           leaf bulking-indicator {
             type string;
           }
           container multicast-route-summaries {
             container multicast-route-summary {
               leaf multicast-route-type {
                 type string;
               }
               leaf multicast-route-state-type {
                 type string;
               }
               leaf multicast-route-count {
                 type int32;
               }
             }
           }
           container multicast-route {
             leaf multicast-group-address {
               type ipaddr;
               description "Group address";
             }
             leaf multicast-group-prefix-length {
               type uint32;
               description "Group prefix length";
             }
             leaf multicast-route-protocol {
               type string;
             }
             leaf multicast-route-packet-type {
               type string;
             }
             leaf multicast-source-address {
               type ipaddr;
               description "Source address";
             }
             leaf multicast-source-prefix-length {
               type uint32;
               description "Source prefix length";
             }
             leaf multicast-route-vlan-id {
               type int32;
             }
             leaf multicast-route-bridge-domain {
               type string;
             }
             leaf multicast-route-mesh-group {
               type string;
             }
             leaf upstream-interface-name {
               type string;
             }
             leaf rpf-check-disabled {
               type empty;
               description "Reverse path forwarding check is disabled";
             }
             leaf upstream-neighbor {
               type ipaddr;
               description "IP Address of Upstream Neighbor";
             }
             leaf incoming-interface-list-names {
               type string;
               description "Incoming interface names";
             }
             leaf outgoing-interface-count {
               type int32;
             }
             leaf rejected-downstream-interface-names {
               type string;
               description "Downstream interfaces rejected by bandwidth admission control";
             }
             leaf session-name {
               type string;
             }
             leaf forwarding-rate-kilobytes {
               type uint32;
             }
             leaf forwarding-rate-packets {
               type uint32;
             }
             leaf forwarded-packet-count {
               type uint32;
             }
             leaf multicast-statistics-timed-out {
               type empty;
             }
             leaf rpf-next-hop-id {
               type uint32;
             }
             leaf next-hop-id {
               type uint32;
             }
             leaf incoming-interface-list-id {
               type uint32;
               description "Incoming Interface list id";
             }
             leaf upstream-nbr-nh-id {
               type uint32;
               description "Upstream Neighbor Next-hop ID";
             }
             leaf upstream-protocol {
               type string;
             }
             leaf multicast-route-state {
               type string;
             }
             leaf multicast-route-forwarding-state {
               type string;
             }
             leaf multicast-route-uptime {
               type string;
             }
             leaf multicast-route-timeout {
               type string;
             }
             leaf interface-mismatch-count {
               type uint32;
             }
             container summary {
               leaf multicast-route-vlan {
                 type string;
               }
               leaf bandwidth-for-admission-control {
                 type uint64;
                 description "Bandwidth used for admission control";
               }
               container multicast-route-source {
               }
               container upstream-rpf-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
                 leaf upstream-rpf-labels {
                   type string;
                   description "Sender-Based RPF labels";
                 }
                 leaf rpf-session-id {
                   type uint32;
                   description "Session id";
                 }
                 leaf rpf-session-status {
                   type string;
                   description "Session Status";
                 }
                 leaf rpf-min-rate {
                   type uint32;
                   description "Min rate";
                 }
                 leaf rpf-weight {
                   type uint32;
                   description "RPF Weight";
                 }
               }
               container downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container multicast-route-summaries {
                 container multicast-route-summary {
                   leaf multicast-route-type {
                     type string;
                   }
                   leaf multicast-route-state-type {
                     type string;
                   }
                   leaf multicast-route-count {
                     type int32;
                   }
                 }
               }
             }
             container brief {
               leaf multicast-group-address {
                 type ipaddr;
                 description "Group address";
               }
               leaf multicast-group-prefix-length {
                 type uint32;
                 description "Group prefix length";
               }
               leaf multicast-route-protocol {
                 type string;
               }
               leaf multicast-route-packet-type {
                 type string;
               }
               leaf multicast-source-address {
                 type ipaddr;
                 description "Source address";
               }
               leaf multicast-source-prefix-length {
                 type uint32;
                 description "Source prefix length";
               }
               leaf multicast-route-vlan-id {
                 type int32;
               }
               leaf multicast-route-bridge-domain {
                 type string;
               }
               leaf multicast-route-mesh-group {
                 type string;
               }
               leaf upstream-interface-name {
                 type string;
               }
               leaf rpf-check-disabled {
                 type empty;
                 description "Reverse path forwarding check is disabled";
               }
               leaf upstream-neighbor {
                 type ipaddr;
                 description "IP Address of Upstream Neighbor";
               }
               leaf outgoing-interface-count {
                 type int32;
               }
               leaf incoming-interface-list-names {
                 type string;
                 description "Incoming interface names";
               }
               leaf rejected-downstream-interface-names {
                 type string;
                 description "Downstream interfaces rejected by bandwidth admission control";
               }
               leaf multicast-route-vlan {
                 type string;
               }
               leaf bandwidth-for-admission-control {
                 type uint64;
                 description "Bandwidth used for admission control";
               }
               container multicast-route-source {
               }
               container upstream-rpf-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
                 leaf upstream-rpf-labels {
                   type string;
                   description "Sender-Based RPF labels";
                 }
                 leaf rpf-session-id {
                   type uint32;
                   description "Session id";
                 }
                 leaf rpf-session-status {
                   type string;
                   description "Session Status";
                 }
                 leaf rpf-min-rate {
                   type uint32;
                   description "Min rate";
                 }
                 leaf rpf-weight {
                   type uint32;
                   description "RPF Weight";
                 }
               }
               container downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container multicast-route-summaries {
                 container multicast-route-summary {
                   leaf multicast-route-type {
                     type string;
                   }
                   leaf multicast-route-state-type {
                     type string;
                   }
                   leaf multicast-route-count {
                     type int32;
                   }
                 }
               }
             }
             container detail {
               leaf multicast-group-address {
                 type ipaddr;
                 description "Group address";
               }
               leaf multicast-group-prefix-length {
                 type uint32;
                 description "Group prefix length";
               }
               leaf multicast-route-protocol {
                 type string;
               }
               leaf multicast-route-packet-type {
                 type string;
               }
               leaf multicast-source-address {
                 type ipaddr;
                 description "Source address";
               }
               leaf multicast-source-prefix-length {
                 type uint32;
                 description "Source prefix length";
               }
               leaf multicast-route-vlan-id {
                 type int32;
               }
               leaf multicast-route-bridge-domain {
                 type string;
               }
               leaf multicast-route-mesh-group {
                 type string;
               }
               leaf upstream-interface-name {
                 type string;
               }
               leaf rpf-check-disabled {
                 type empty;
                 description "Reverse path forwarding check is disabled";
               }
               leaf upstream-neighbor {
                 type ipaddr;
                 description "IP Address of Upstream Neighbor";
               }
               leaf outgoing-interface-count {
                 type int32;
               }
               leaf incoming-interface-list-names {
                 type string;
                 description "Incoming interface names";
               }
               leaf rejected-downstream-interface-names {
                 type string;
                 description "Downstream interfaces rejected by bandwidth admission control";
               }
               leaf session-name {
                 type string;
               }
               leaf forwarding-rate-kilobytes {
                 type uint32;
               }
               leaf forwarding-rate-packets {
                 type uint32;
               }
               leaf forwarded-packet-count {
                 type uint32;
               }
               leaf multicast-statistics-timed-out {
                 type empty;
               }
               leaf rpf-next-hop-id {
                 type uint32;
               }
               leaf next-hop-id {
                 type uint32;
               }
               leaf incoming-interface-list-id {
                 type uint32;
                 description "Incoming Interface list id";
               }
               leaf upstream-nbr-nh-id {
                 type uint32;
                 description "Upstream Neighbor Next-hop ID";
               }
               leaf upstream-protocol {
                 type string;
               }
               leaf multicast-route-vlan {
                 type string;
               }
               leaf bandwidth-for-admission-control {
                 type uint64;
                 description "Bandwidth used for admission control";
               }
               container multicast-route-source {
               }
               container upstream-rpf-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
                 leaf upstream-rpf-labels {
                   type string;
                   description "Sender-Based RPF labels";
                 }
                 leaf rpf-session-id {
                   type uint32;
                   description "Session id";
                 }
                 leaf rpf-session-status {
                   type string;
                   description "Session Status";
                 }
                 leaf rpf-min-rate {
                   type uint32;
                   description "Min rate";
                 }
                 leaf rpf-weight {
                   type uint32;
                   description "RPF Weight";
                 }
               }
               container downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container multicast-route-summaries {
                 container multicast-route-summary {
                   leaf multicast-route-type {
                     type string;
                   }
                   leaf multicast-route-state-type {
                     type string;
                   }
                   leaf multicast-route-count {
                     type int32;
                   }
                 }
               }
             }
             container extensive {
               leaf multicast-group-address {
                 type ipaddr;
                 description "Group address";
               }
               leaf multicast-group-prefix-length {
                 type uint32;
                 description "Group prefix length";
               }
               leaf multicast-route-protocol {
                 type string;
               }
               leaf multicast-route-packet-type {
                 type string;
               }
               leaf multicast-source-address {
                 type ipaddr;
                 description "Source address";
               }
               leaf multicast-source-prefix-length {
                 type uint32;
                 description "Source prefix length";
               }
               leaf multicast-route-vlan-id {
                 type int32;
               }
               leaf multicast-route-bridge-domain {
                 type string;
               }
               leaf multicast-route-mesh-group {
                 type string;
               }
               leaf upstream-interface-name {
                 type string;
               }
               leaf rpf-check-disabled {
                 type empty;
                 description "Reverse path forwarding check is disabled";
               }
               leaf upstream-neighbor {
                 type ipaddr;
                 description "IP Address of Upstream Neighbor";
               }
               leaf outgoing-interface-count {
                 type int32;
               }
               leaf incoming-interface-list-names {
                 type string;
                 description "Incoming interface names";
               }
               leaf rejected-downstream-interface-names {
                 type string;
                 description "Downstream interfaces rejected by bandwidth admission control";
               }
               leaf session-name {
                 type string;
               }
               leaf forwarding-rate-kilobytes {
                 type uint32;
               }
               leaf forwarding-rate-packets {
                 type uint32;
               }
               leaf forwarded-packet-count {
                 type uint32;
               }
               leaf multicast-statistics-timed-out {
                 type empty;
               }
               leaf rpf-next-hop-id {
                 type uint32;
               }
               leaf next-hop-id {
                 type uint32;
               }
               leaf incoming-interface-list-id {
                 type uint32;
                 description "Incoming Interface list id";
               }
               leaf upstream-nbr-nh-id {
                 type uint32;
                 description "Upstream Neighbor Next-hop ID";
               }
               leaf upstream-protocol {
                 type string;
               }
               leaf multicast-route-state {
                 type string;
               }
               leaf multicast-route-forwarding-state {
                 type string;
               }
               leaf multicast-route-uptime {
                 type string;
               }
               leaf multicast-route-timeout {
                 type string;
               }
               leaf interface-mismatch-count {
                 type uint32;
               }
               leaf multicast-route-vlan {
                 type string;
               }
               leaf bandwidth-for-admission-control {
                 type uint64;
                 description "Bandwidth used for admission control";
               }
               container multicast-route-source {
               }
               container upstream-rpf-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
                 leaf upstream-rpf-labels {
                   type string;
                   description "Sender-Based RPF labels";
                 }
                 leaf rpf-session-id {
                   type uint32;
                   description "Session id";
                 }
                 leaf rpf-session-status {
                   type string;
                   description "Session Status";
                 }
                 leaf rpf-min-rate {
                   type uint32;
                   description "Min rate";
                 }
                 leaf rpf-weight {
                   type uint32;
                   description "RPF Weight";
                 }
               }
               container downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container multicast-route-summaries {
                 container multicast-route-summary {
                   leaf multicast-route-type {
                     type string;
                   }
                   leaf multicast-route-state-type {
                     type string;
                   }
                   leaf multicast-route-count {
                     type int32;
                   }
                 }
               }
             }
           }
           container l2ng-multicast-route {
             leaf multicast-group-address {
               type ipaddr;
               description "Group address";
             }
             leaf multicast-group-prefix-length {
               type uint32;
               description "Group prefix length";
             }
             leaf multicast-route-protocol {
               type string;
             }
             leaf multicast-route-packet-type {
               type string;
             }
             leaf multicast-source-address {
               type ipaddr;
               description "Source address";
             }
             leaf multicast-source-prefix-length {
               type uint32;
               description "Source prefix length";
             }
             leaf multicast-route-vlan-id {
               type int32;
             }
             leaf multicast-route-vlan {
               type string;
             }
             leaf multicast-route-mesh-group {
               type string;
             }
             leaf upstream-interface-name {
               type string;
             }
             leaf rpf-check-disabled {
               type empty;
               description "Reverse path forwarding check is disabled";
             }
             leaf incoming-interface-list-names {
               type string;
               description "Incoming interface names";
             }
             leaf rejected-downstream-interface-names {
               type string;
               description "Downstream interfaces rejected by bandwidth admission control";
             }
             leaf session-name {
               type string;
             }
             leaf forwarding-rate-kilobytes {
               type uint32;
             }
             leaf forwarding-rate-packets {
               type uint32;
             }
             leaf forwarded-packet-count {
               type uint32;
             }
             leaf multicast-statistics-timed-out {
               type empty;
             }
             leaf next-hop-id {
               type uint32;
             }
             leaf incoming-interface-list-id {
               type uint32;
               description "Incoming Interface list id";
             }
             leaf upstream-protocol {
               type string;
             }
             leaf multicast-route-state {
               type string;
             }
             leaf multicast-route-forwarding-state {
               type string;
             }
             leaf multicast-route-uptime {
               type string;
             }
             leaf multicast-route-timeout {
               type string;
             }
             leaf interface-mismatch-count {
               type uint32;
             }
             container summary {
               leaf multicast-route-bridge-domain {
                 type string;
               }
               leaf bandwidth-for-admission-control {
                 type uint64;
                 description "Bandwidth used for admission control";
               }
               container l2ng-downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container l2ng-multicast-route-summary {
                 leaf multicast-route-type {
                   type string;
                 }
                 leaf multicast-route-state-type {
                   type string;
                 }
                 leaf multicast-route-count {
                   type int32;
                 }
               }
             }
             container brief {
               leaf multicast-group-address {
                 type ipaddr;
                 description "Group address";
               }
               leaf multicast-group-prefix-length {
                 type uint32;
                 description "Group prefix length";
               }
               leaf multicast-route-protocol {
                 type string;
               }
               leaf multicast-route-packet-type {
                 type string;
               }
               leaf multicast-source-address {
                 type ipaddr;
                 description "Source address";
               }
               leaf multicast-source-prefix-length {
                 type uint32;
                 description "Source prefix length";
               }
               leaf multicast-route-vlan-id {
                 type int32;
               }
               leaf multicast-route-vlan {
                 type string;
               }
               leaf multicast-route-mesh-group {
                 type string;
               }
               leaf upstream-interface-name {
                 type string;
               }
               leaf rpf-check-disabled {
                 type empty;
                 description "Reverse path forwarding check is disabled";
               }
               leaf incoming-interface-list-names {
                 type string;
                 description "Incoming interface names";
               }
               leaf rejected-downstream-interface-names {
                 type string;
                 description "Downstream interfaces rejected by bandwidth admission control";
               }
               leaf multicast-route-bridge-domain {
                 type string;
               }
               leaf bandwidth-for-admission-control {
                 type uint64;
                 description "Bandwidth used for admission control";
               }
               container l2ng-downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container l2ng-multicast-route-summary {
                 leaf multicast-route-type {
                   type string;
                 }
                 leaf multicast-route-state-type {
                   type string;
                 }
                 leaf multicast-route-count {
                   type int32;
                 }
               }
             }
             container detail {
               leaf multicast-group-address {
                 type ipaddr;
                 description "Group address";
               }
               leaf multicast-group-prefix-length {
                 type uint32;
                 description "Group prefix length";
               }
               leaf multicast-route-protocol {
                 type string;
               }
               leaf multicast-route-packet-type {
                 type string;
               }
               leaf multicast-source-address {
                 type ipaddr;
                 description "Source address";
               }
               leaf multicast-source-prefix-length {
                 type uint32;
                 description "Source prefix length";
               }
               leaf multicast-route-vlan-id {
                 type int32;
               }
               leaf multicast-route-vlan {
                 type string;
               }
               leaf multicast-route-mesh-group {
                 type string;
               }
               leaf upstream-interface-name {
                 type string;
               }
               leaf rpf-check-disabled {
                 type empty;
                 description "Reverse path forwarding check is disabled";
               }
               leaf incoming-interface-list-names {
                 type string;
                 description "Incoming interface names";
               }
               leaf rejected-downstream-interface-names {
                 type string;
                 description "Downstream interfaces rejected by bandwidth admission control";
               }
               leaf session-name {
                 type string;
               }
               leaf forwarding-rate-kilobytes {
                 type uint32;
               }
               leaf forwarding-rate-packets {
                 type uint32;
               }
               leaf forwarded-packet-count {
                 type uint32;
               }
               leaf multicast-statistics-timed-out {
                 type empty;
               }
               leaf next-hop-id {
                 type uint32;
               }
               leaf incoming-interface-list-id {
                 type uint32;
                 description "Incoming Interface list id";
               }
               leaf upstream-protocol {
                 type string;
               }
               leaf multicast-route-bridge-domain {
                 type string;
               }
               leaf bandwidth-for-admission-control {
                 type uint64;
                 description "Bandwidth used for admission control";
               }
               container l2ng-downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container l2ng-multicast-route-summary {
                 leaf multicast-route-type {
                   type string;
                 }
                 leaf multicast-route-state-type {
                   type string;
                 }
                 leaf multicast-route-count {
                   type int32;
                 }
               }
             }
             container extensive {
               leaf multicast-group-address {
                 type ipaddr;
                 description "Group address";
               }
               leaf multicast-group-prefix-length {
                 type uint32;
                 description "Group prefix length";
               }
               leaf multicast-route-protocol {
                 type string;
               }
               leaf multicast-route-packet-type {
                 type string;
               }
               leaf multicast-source-address {
                 type ipaddr;
                 description "Source address";
               }
               leaf multicast-source-prefix-length {
                 type uint32;
                 description "Source prefix length";
               }
               leaf multicast-route-vlan-id {
                 type int32;
               }
               leaf multicast-route-vlan {
                 type string;
               }
               leaf multicast-route-mesh-group {
                 type string;
               }
               leaf upstream-interface-name {
                 type string;
               }
               leaf rpf-check-disabled {
                 type empty;
                 description "Reverse path forwarding check is disabled";
               }
               leaf incoming-interface-list-names {
                 type string;
                 description "Incoming interface names";
               }
               leaf rejected-downstream-interface-names {
                 type string;
                 description "Downstream interfaces rejected by bandwidth admission control";
               }
               leaf session-name {
                 type string;
               }
               leaf forwarding-rate-kilobytes {
                 type uint32;
               }
               leaf forwarding-rate-packets {
                 type uint32;
               }
               leaf forwarded-packet-count {
                 type uint32;
               }
               leaf multicast-statistics-timed-out {
                 type empty;
               }
               leaf next-hop-id {
                 type uint32;
               }
               leaf incoming-interface-list-id {
                 type uint32;
                 description "Incoming Interface list id";
               }
               leaf upstream-protocol {
                 type string;
               }
               leaf multicast-route-state {
                 type string;
               }
               leaf multicast-route-forwarding-state {
                 type string;
               }
               leaf multicast-route-uptime {
                 type string;
               }
               leaf multicast-route-timeout {
                 type string;
               }
               leaf interface-mismatch-count {
                 type uint32;
               }
               leaf multicast-route-bridge-domain {
                 type string;
               }
               leaf bandwidth-for-admission-control {
                 type uint64;
                 description "Bandwidth used for admission control";
               }
               container l2ng-downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container l2ng-multicast-route-summary {
                 leaf multicast-route-type {
                   type string;
                 }
                 leaf multicast-route-state-type {
                   type string;
                 }
                 leaf multicast-route-count {
                   type int32;
                 }
               }
             }
           }
         }
       }
     }
   }
   rpc get-multicast-next-hops-information {
     description "Show the multicast next-hop table";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "terse" {
             description "Display terse output";
           }
           enum "brief" {
             description "Display brief output (default)";
           }
           enum "detail" {
             description "Display detailed output";
           }
         }
       }
       leaf identifier {
         description "ID of next hop";
         type uint32;
       }
       leaf family {
         description "Address family";
         default "inet";
         type enumeration {
           enum "inet" {
             description "Display IPv4 information";
           }
           enum "inet6" {
             description "Display IPv6 information";
           }
         }
       }
     }
     output {
       container multicast-next-hops-information {
         container next-hops-family {
           leaf address-family {
             type string;
           }
           container iflist-next-hop {
             container regular {
               leaf next-hop-id {
                 type uint32;
               }
               leaf next-hop-ref-count {
                 type uint32;
               }
               leaf next-hop-kernel-ref-count {
                 type uint32;
               }
               leaf next-hop-addr {
                 type uint32;
               }
               leaf rpf-next-hop-id {
                 type uint32;
               }
               container next-hop-downstream-interface {
                 leaf interface-name {
                   type string;
                   description "Name of interface";
                 }
                 leaf interface-index {
                   type int32;
                 }
                 leaf interface-nh-index {
                   type uint32;
                   description "Logical interface nexthop index";
                 }
               }
             }
             container terse {
               leaf next-hop-id {
                 type uint32;
               }
               leaf next-hop-ref-count {
                 type uint32;
               }
               leaf next-hop-kernel-ref-count {
                 type uint32;
               }
               leaf next-hop-downstream-interface-count {
                 type uint32;
               }
               leaf rpf-next-hop-id {
                 type uint32;
               }
               container next-hop-downstream-interface {
                 leaf interface-nh-index {
                   type uint32;
                   description "Logical interface nexthop index";
                 }
               }
             }
           }
         }
       }
     }
   }
   rpc get-satellite-control-next-hop {
     description "Show satellite multicast unicast next-hops";
     input {
       leaf verbosity_level {
         default "brief";
         type enumeration {
           enum "brief" {
             description "Display brief output (default)";
           }
           enum "detail" {
             description "Display detailed output";
           }
         }
       }
     }
   }
   rpc get-multicast-rpf-information {
     description "Show reverse-path forwarding (RPF) source network information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf verbosity_level {
         type enumeration {
           enum "summary" {
             description "Display summary output";
           }
         }
       }
       leaf prefix {
         description "IP address and optional prefix length of host";
         type ipprefix;
       }
       leaf family {
         description "Address family";
         default "inet";
         type enumeration {
           enum "inet" {
             description "Display RPF information for IPv4 ";
           }
           enum "inet6" {
             description "Display RPF information for IPv6 ";
           }
         }
       }
     }
     output {
       container multicast-rpf-information {
         container rpf-family {
           leaf rpf-table-name {
             type string;
           }
           leaf rpf-table-entry-count {
             type uint32;
           }
           leaf address-family {
             type string;
           }
           container rpf-route {
             leaf prefix {
               type ipaddr;
             }
             leaf rpf-route-inactive {
               type empty;
             }
             leaf rpf-route-protocol {
               type string;
             }
             leaf interface-name {
               type string;
               description "Name of interface";
             }
             leaf rpf-route-neighbor {
               type ipaddr;
             }
           }
         }
       }
     }
   }
   rpc get-multicast-scope-information {
     description "Show administratively scoped multicast information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf family {
         description "Address family";
         default "inet";
         type enumeration {
           enum "inet" {
             description "Display IPv4 information";
           }
           enum "inet6" {
             description "Display IPv6 information";
           }
         }
       }
     }
     output {
       container multicast-scope-information {
         container groups {
           container multicast-scope-policy-interfaces {
             container multicast-scope-policy-interface {
             }
           }
           container multicast-scope {
             leaf scope-name {
               type string;
               description "Name of multicast scope";
             }
             leaf address-prefix {
               type ipaddr;
             }
             leaf interface-name {
               type string;
               description "Name of interface";
             }
             leaf scope-state {
               type string;
             }
             leaf scope-rejects {
               type uint32;
               description "Number of rejects in multicast scope";
             }
           }
         }
         container policy {
           leaf multicast-scope-policy {
             type string;
           }
           container multicast-scope-policy-interfaces {
             leaf instance-name {
               type string;
             }
             leaf address-family {
               type string;
             }
             container multicast-scope-policy-interface {
             }
           }
           container multicast-scope {
             leaf interface-name {
               type string;
               description "Name of interface";
             }
             leaf scope-state {
               type string;
             }
             leaf scope-rejects {
               type uint32;
               description "Number of rejects in multicast scope";
             }
           }
         }
       }
     }
   }
   rpc get-multicast-sessions-information {
     description "Show announced multicast sessions";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf regexp {
         description "Regular expression for sessions to match";
         type string;
       }
     }
     output {
       container multicast-sessions-information {
         leaf multicast-session-count {
           type uint32;
         }
         leaf multicast-sessions-type {
           type string;
         }
         container multicast-session {
           container terse {
             leaf session-announcement {
               type string;
             }
             leaf session-name {
               type string;
             }
             leaf upstream-protocol {
               type string;
             }
           }
           container detail {
             leaf session-version {
               type string;
             }
             leaf session-name {
               type string;
             }
             leaf session-description {
               type string;
             }
             leaf session-uri {
               type string;
             }
             leaf session-email {
               type string;
             }
             leaf session-phone {
               type string;
             }
             leaf session-bandwidth {
               type string;
             }
             leaf session-start-time {
               type string;
             }
             leaf session-stop-time {
               type string;
             }
             leaf session-encryption-key {
               type string;
             }
             leaf session-attribute {
               type string;
             }
             leaf session-media {
               type string;
             }
             leaf upstream-protocol {
               type string;
             }
             container session-origin {
               leaf session-originator-username {
                 type string;
               }
               leaf session-originator-address {
                 type string;
               }
             }
             container session-connection-data {
               leaf session-address {
                 type string;
               }
               leaf session-ttl {
                 type uint32;
               }
               leaf session-layers {
                 type uint32;
               }
             }
           }
         }
       }
     }
   }
   rpc get-multicast-statistics-information {
     description "Show multicast statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf interface {
         description "Name of interface";
         type string;
       }
       leaf family {
         description "Address family";
         default "inet";
         type enumeration {
           enum "inet" {
             description "Display statistics for IPv4 ";
           }
           enum "inet6" {
             description "Display statistics for IPv6 ";
           }
         }
       }
     }
     output {
       container multicast-statistics-information {
         container multicast-statistics {
           leaf instance-name {
             type string;
           }
           leaf address-family {
             type string;
           }
           leaf mc-resolves-no-mc-interface {
             type uint32;
             description "Number of resolve requests on non-multicast interfaces";
           }
           leaf mc-global-resolves-no-route {
             type uint32;
             description "Number of resolve requests with no route to source";
           }
           leaf mc-notifies-no-mc-interface {
             type uint32;
             description "Number of routing notifications on non-multicast interfaces";
           }
           leaf mc-notifies-no-route {
             type uint32;
             description "Number of routing notifications with no route to source";
           }
           leaf mc-mismatches-no-mc-interface {
             type uint32;
             description "Number of interface mismatches on non-multicast interfaces";
           }
           leaf mc-groups-no-mc-interface {
             type uint32;
             description "Number of group memberships on non-multicast interfaces";
           }
           container mc-stats-interface {
             leaf interface-name {
               type string;
               description "Name of interface";
             }
             leaf protocol-name {
               type string;
             }
             leaf mc-mismatch-errors {
               type uint32;
               description "Number of interface mismatch errors";
             }
             leaf mc-mismatches {
               type uint32;
               description "Number of interface mismatches";
             }
             leaf mc-mismatches-no-route {
               type uint32;
               description "Number of interface mismatches due to no route to source";
             }
             leaf mc-resolves {
               type uint32;
               description "Number of resolve requests";
             }
             leaf mc-routing-notifies {
               type uint32;
               description "Number of routing notifications";
             }
             leaf mc-resolves-no-route {
               type uint32;
               description "Number of resolve requests with no route to source";
             }
             leaf mc-resolve-errors {
               type uint32;
               description "Number of resolve errors";
             }
             leaf mc-resolves-filtered {
               type uint32;
               description "Number of resolve requests filtered by policy";
             }
             leaf mc-routing-notifies-filtered {
               type uint32;
               description "Number of routing notifications filtered by policy";
             }
             leaf mc-input-kbytes {
               type uint64;
               description "Number of input kilobytes";
             }
             leaf mc-input-packets {
               type uint64;
               description "Number of input packets";
             }
             leaf mc-output-kbytes {
               type uint64;
               description "Number of output kilobytes";
             }
             leaf mc-output-packets {
               type uint64;
               description "Number of output packets";
             }
             container mc-stats-interface-p2mp-nbr {
               leaf mc-p2mp-nbr-address {
                 type ipaddr;
                 description "P2MP Neighbor address";
               }
               leaf mc-p2mp-mismatch-errors {
                 type uint32;
                 description "Number of interface mismatch errors";
               }
               leaf mc-p2mp-mismatches {
                 type uint32;
                 description "Number of interface mismatches";
               }
               leaf mc-p2mp-mismatches-no-route {
                 type uint32;
                 description "Number of interface mismatches due to no route to source";
               }
               leaf mc-p2mp-resolves {
                 type uint32;
                 description "Number of resolve requests";
               }
               leaf mc-p2mp-routing-notifies {
                 type uint32;
                 description "Number of routing notifications";
               }
               leaf mc-p2mp-resolves-no-route {
                 type uint32;
                 description "Number of resolve requests with no route to source";
               }
               leaf mc-p2mp-resolve-errors {
                 type uint32;
                 description "Number of resolve errors";
               }
               leaf mc-p2mp-resolves-filtered {
                 type uint32;
                 description "Number of resolve requests filtered by policy";
               }
               leaf mc-p2mp-routing-notifies-filtered {
                 type uint32;
                 description "Number of routing notifications filtered by policy";
               }
               leaf mc-p2mp-input-kbytes {
                 type uint64;
                 description "Number of input kilobytes";
               }
               leaf mc-p2mp-input-packets {
                 type uint64;
                 description "Number of input packets";
               }
               leaf mc-p2mp-output-kbytes {
                 type uint64;
                 description "Number of output kilobytes";
               }
               leaf mc-p2mp-output-packets {
                 type uint64;
                 description "Number of output packets";
               }
             }
           }
         }
       }
     }
   }
   rpc get-satellite-control-statistics {
     description "Show satellite multicast statistics";
     input {
       leaf verbosity_level {
         default "detail";
         type enumeration {
           enum "brief" {
             description "Display brief output (default)";
           }
           enum "detail" {
             description "Display detailed output";
           }
         }
       }
     }
   }
   rpc get-multicast-tunnels-information {
     description "Show multicast tunnel information";
     status deprecated;
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container multicast-tunnels-information {
         container multicast-tunnel {
           leaf interface-name {
             type string;
             description "Name of interface";
           }
           leaf tunnel-local-address {
             type ipaddr;
           }
           leaf tunnel-remote-address {
             type ipaddr;
           }
           leaf tunnel-ttl {
             type uint32;
           }
         }
       }
     }
   }
   rpc get-multicast-usage-information {
     description "Show multicast usage information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf verbosity_level {
         default "brief";
         type enumeration {
           enum "brief" {
             description "Display brief output (default)";
           }
           enum "detail" {
             description "Display detailed output";
           }
         }
       }
       leaf family {
         description "Address family";
         default "inet";
         type enumeration {
           enum "inet" {
             description "Display IPv4 information";
           }
           enum "inet6" {
             description "Display IPv6 information";
           }
         }
       }
     }
     output {
       container multicast-usage-information {
         leaf multicast-usage-no-group-prefix {
           type ipaddr;
         }
         leaf multicast-usage-strange-family {
           type uint32;
         }
         leaf multicast-usage-timed-out {
           type empty;
         }
         container multicast-group {
           container ipv4 {
             leaf multicast-group-address {
               type ipaddr;
               description "Group address";
             }
             leaf multicast-source-count {
               type uint32;
             }
             leaf multicast-packet-count {
               type uint32;
             }
             leaf multicast-packet-count-not-available {
               type empty;
             }
             leaf multicast-byte-count {
               type uint32;
             }
             leaf multicast-byte-count-not-available {
               type empty;
             }
             container multicast-group-source {
               container ipv6 {
                 leaf multicast-source-address {
                   type ipaddr;
                   description "Source address";
                 }
                 leaf multicast-source-prefix-length {
                   type uint32;
                   description "Source prefix length";
                 }
               }
             }
           }
           container ipv6 {
             leaf multicast-group-address {
               type ipaddr;
               description "Group address";
             }
             leaf multicast-source-count {
               type uint32;
             }
             leaf multicast-packet-count {
               type uint32;
             }
             leaf multicast-packet-count-not-available {
               type empty;
             }
             leaf multicast-byte-count {
               type uint32;
             }
             leaf multicast-byte-count-not-available {
               type empty;
             }
             container multicast-group-source {
               container ipv4 {
                 leaf multicast-source-address {
                   type ipaddr;
                   description "Source address";
                 }
                 leaf multicast-source-prefix-length {
                   type uint32;
                   description "Source prefix length";
                 }
               }
               container ipv6 {
                 leaf multicast-source-address {
                   type ipaddr;
                   description "Source address";
                 }
                 leaf multicast-source-prefix-length {
                   type uint32;
                   description "Source prefix length";
                 }
                 leaf multicast-packet-count {
                   type uint32;
                 }
                 leaf multicast-byte-count {
                   type uint32;
                 }
                 leaf multicast-packet-count-not-available {
                   type empty;
                 }
                 leaf multicast-byte-count-not-available {
                   type empty;
                 }
               }
             }
           }
         }
         container multicast-source {
           container ipv4 {
             leaf multicast-source-address {
               type ipaddr;
               description "Source address";
             }
             leaf multicast-source-prefix-length {
               type uint32;
               description "Source prefix length";
             }
             leaf multicast-group-count {
               type uint32;
             }
             leaf multicast-packet-count {
               type uint32;
             }
             leaf multicast-packet-count-not-available {
               type empty;
             }
             leaf multicast-byte-count {
               type uint32;
             }
             leaf multicast-byte-count-not-available {
               type empty;
             }
             container multicast-source-group {
               container ipv6 {
                 leaf multicast-group-address {
                   type ipaddr;
                   description "Group address";
                 }
               }
             }
           }
           container ipv6 {
             leaf multicast-source-address {
               type ipaddr;
               description "Source address";
             }
             leaf multicast-source-prefix-length {
               type uint32;
               description "Source prefix length";
             }
             leaf multicast-group-count {
               type uint32;
             }
             leaf multicast-packet-count {
               type uint32;
             }
             leaf multicast-packet-count-not-available {
               type empty;
             }
             leaf multicast-byte-count {
               type uint32;
             }
             leaf multicast-byte-count-not-available {
               type empty;
             }
             container multicast-source-group {
               container ipv4 {
                 leaf multicast-group-address {
                   type ipaddr;
                   description "Group address";
                 }
               }
               container ipv6 {
                 leaf multicast-group-address {
                   type ipaddr;
                   description "Group address";
                 }
                 leaf multicast-packet-count {
                   type uint32;
                 }
                 leaf multicast-byte-count {
                   type uint32;
                 }
                 leaf multicast-packet-count-not-available {
                   type empty;
                 }
                 leaf multicast-byte-count-not-available {
                   type empty;
                 }
               }
             }
           }
         }
       }
     }
   }
   rpc get-multicast-flow-maps-information {
     description "Show configured flow maps";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf verbosity_level {
         default "brief";
         type enumeration {
           enum "brief" {
             description "Display brief output (default)";
           }
           enum "detail" {
             description "Display detailed output";
           }
         }
       }
     }
     output {
       container multicast-flow-maps-information {
         container multicast-flow-maps {
           description "Information about multicast flow maps for one routing instance";
           leaf instance-name {
             type string;
           }
           container multicast-flow-map {
             description "Information about a multicast flow map";
             container brief {
               description "Information about a multicast flow map";
               leaf flow-map-name {
                 type string;
                 description "Name of the flow map";
               }
               leaf policy-name {
                 type string;
                 description "Name of the policy";
               }
               leaf cache-timeout {
                 type string;
                 description "Delay before discarding a matched cache entry";
               }
               leaf flow-bandwidth {
                 type uint64;
                 description "Bandwidth for matched flows";
               }
               leaf bandwidth-type {
                 type string;
                 description "Bandwidth type for matched flows";
               }
             }
             container detail {
               description "Information about a multicast flow map";
               leaf flow-map-name {
                 type string;
                 description "Name of the flow map";
               }
               leaf policy-name {
                 type string;
                 description "Name of the policy";
               }
               leaf cache-timeout {
                 type string;
                 description "Delay before discarding a matched cache entry";
               }
               leaf flow-bandwidth {
                 type uint64;
                 description "Bandwidth for matched flows";
               }
               leaf bandwidth-type {
                 type string;
                 description "Bandwidth type for matched flows";
               }
               container redundant-sources {
                 description "Redundant source addresses";
                 leaf multicast-source-address {
                   type ipaddr;
                   description "Source address";
                 }
               }
             }
           }
         }
       }
     }
   }
   rpc get-multicast-interface-information {
     description "Show configured interfaces";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container multicast-interface-information {
         container multicast-interface {
           description "Information about a multicast interface";
           leaf interface-name {
             type string;
             description "Name of interface";
           }
           leaf interface-max-bandwidth {
             type uint64;
             description "Maximum bandwidth for multicast flows";
           }
           leaf interface-local-bandwidth-deduction {
             type int64;
             description "Bandwidth deduction for local multicast flows";
           }
           leaf interface-mapped-bandwidth-deduction {
             type int64;
             description "Bandwidth deduction for mapped multicast flows";
           }
           leaf interface-remaining-bandwidth {
             type int64;
             description "Remaining bandwidth for multicast flows";
           }
           leaf interface-reverse-oif-mapping {
             type string;
             description "Reverse OIF mapping is enabled";
           }
           leaf interface-reverse-oif-mapping-no-qos-adjust {
             type string;
             description "Reverse OIF mapping no QoS adjust is enabled";
           }
           leaf interface-subscriber-leave-timer {
             type uint32;
             description "Bw restore waiting time after subscriber leaves group";
           }
           leaf interface-no-qos-adjust {
             type string;
             description "Interface no QoS adjustment is enabled";
           }
         }
       }
     }
   }
   rpc get-multicast-pim-to-igmp-proxy-information {
     description "Show pim-to-igmp-proxy information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
     }
     output {
       container multicast-pim-to-igmp-proxy-information {
         container multicast-pim-to-igmp-proxy {
           description "Pim-to-igmp-proxy state";
           leaf instance-name {
             type string;
           }
           leaf proxy-state {
             type string;
           }
         }
       }
     }
   }
   rpc get-multicast-pim-to-mld-proxy-information {
     description "Show pim-to-mld-proxy information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
     }
     output {
       container multicast-pim-to-mld-proxy-information {
         container multicast-pim-to-mld-proxy {
           description "Pim-to-mld-proxy state";
           leaf instance-name {
             type string;
           }
           leaf proxy-state {
             type string;
           }
         }
       }
     }
   }
   rpc get-multicast-backup-pe-groups-information {
     description "Show backup PE groups";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
     }
     output {
       container multicast-backup-pe-groups-information {
         container multicast-backup-pe-groups {
           description "Information about multicast backup PE groups for one routing instance";
           leaf instance-name {
             type string;
           }
           container multicast-backup-pe-group {
             description "Information about a multicast backup PE group";
             container brief {
               description "Information about a multicast backup PE group";
               leaf multicast-backup-pe-group-name {
                 type string;
                 description "Name of the backup PE group";
               }
               leaf designated-pe {
                 type ipaddr;
                 description "Address of the designated PE";
               }
               leaf transitions {
                 type uint32;
                 description "Number of times desginated PE has changed";
               }
               leaf last-transition {
                 type string;
                 description "Time since last designated PE transition (hours:minutes:seconds)";
               }
               leaf local-pe-address {
                 type ipaddr;
                 description "Local address used in designated router election";
               }
               container backup-pes {
                 description "Backup PE addresses";
                 leaf multicast-backup-pe-address {
                   type ipaddr;
                   description "Backup PE address";
                 }
               }
             }
           }
         }
       }
     }
   }
   rpc get-multicast-backup-pe-group-information {
     description "Show information for specified group";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf group_name {
         description "Name of the group";
         type string;
         mandatory true;
       }
     }
     output {
       container multicast-backup-pe-groups-information {
         container multicast-backup-pe-groups {
           description "Information about multicast backup PE groups for one routing instance";
           leaf instance-name {
             type string;
           }
           container multicast-backup-pe-group {
             description "Information about a multicast backup PE group";
             container brief {
               description "Information about a multicast backup PE group";
               leaf multicast-backup-pe-group-name {
                 type string;
                 description "Name of the backup PE group";
               }
               leaf designated-pe {
                 type ipaddr;
                 description "Address of the designated PE";
               }
               leaf transitions {
                 type uint32;
                 description "Number of times desginated PE has changed";
               }
               leaf last-transition {
                 type string;
                 description "Time since last designated PE transition (hours:minutes:seconds)";
               }
               leaf local-pe-address {
                 type ipaddr;
                 description "Local address used in designated router election";
               }
               container backup-pes {
                 description "Backup PE addresses";
                 leaf multicast-backup-pe-address {
                   type ipaddr;
                   description "Backup PE address";
                 }
               }
             }
           }
         }
       }
     }
   }
   rpc get-multicast-backup-pe-address-information {
     description "Show groups a PE address is associated with";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf pe_address {
         description "IP address of the PE";
         type ipaddr;
         mandatory true;
       }
     }
     output {
       container multicast-backup-pe-address-information {
         container brief {
           description "Information about multicast backup PE";
           leaf multicast-backup-pe-address {
             type ipaddr;
             description "Backup PE address";
           }
           leaf pe-address-local {
             type string;
             description "Indicates if this address belongs to this local PE";
           }
           leaf lsp-to-pe-up {
             type string;
             description "Indicates if the LSP to this PE is up";
           }
           container multicast-backup-pe-group-list {
             description "Information about multicast backup PE groups associatd with PE";
             container multicast-backup-pe-group-member {
               description "Information about a multicast backup PE group";
             }
           }
         }
       }
     }
   }
   rpc get-multicast-snooping-route-information {
     description "Show the multicast snooping routing table";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf mode {
         default "data";
         type enumeration {
           enum "all" {
             description "Display all route entries";
           }
           enum "active" {
             description "Display active route entries";
           }
           enum "inactive" {
             description "Display inactive route entries";
           }
           enum "control" {
             description "Display control route entries";
           }
           enum "data" {
             description "Display data route entries";
           }
         }
       }
       leaf verbosity_level {
         default "brief";
         type enumeration {
           enum "brief" {
             description "Display brief output (default)";
           }
           enum "detail" {
             description "Display detailed output";
           }
           enum "extensive" {
             description "Display extensive output";
           }
         }
       }
       leaf family {
         description "Address family";
         type enumeration {
           enum "inet" {
             description "Display IPv4 information";
           }
           enum "inet6" {
             description "Display IPv6 information";
           }
         }
       }
       leaf vlan-id {
         description "VLAN ID for a learning domain";
         type uint32 {
           range "0 .. 4094";
         }
       }
       leaf mesh-group {
         description "Name of a mesh-group";
         type string;
       }
       leaf group {
         description "IP address and optional prefix length of group";
         type ipprefix;
       }
       leaf source-prefix {
         description "IP address and optional prefix length of source";
         type ipprefix;
       }
       leaf regexp {
         description "Regular expression for session to match";
         type string;
       }
       leaf bridge-domain {
         description "Name of bridge-domain";
         type string;
       }
       leaf instance {
         description "Name of routing-instance";
         type string;
       }
     }
     output {
       container multicast-route-information {
         leaf multicast-route-no-group-prefix {
           type ipaddr;
         }
         leaf multicast-route-no-family {
           type string;
         }
         container route-family {
           leaf multicast-instance {
             type string;
           }
           leaf address-family {
             type string;
           }
           leaf bulking-indicator {
             type string;
           }
           container multicast-route-summaries {
             container multicast-route-summary {
               leaf multicast-route-type {
                 type string;
               }
               leaf multicast-route-state-type {
                 type string;
               }
               leaf multicast-route-count {
                 type int32;
               }
             }
           }
           container multicast-route {
             leaf multicast-group-address {
               type ipaddr;
               description "Group address";
             }
             leaf multicast-group-prefix-length {
               type uint32;
               description "Group prefix length";
             }
             leaf multicast-route-protocol {
               type string;
             }
             leaf multicast-route-packet-type {
               type string;
             }
             leaf multicast-source-address {
               type ipaddr;
               description "Source address";
             }
             leaf multicast-source-prefix-length {
               type uint32;
               description "Source prefix length";
             }
             leaf multicast-route-vlan-id {
               type int32;
             }
             leaf multicast-route-bridge-domain {
               type string;
             }
             leaf multicast-route-mesh-group {
               type string;
             }
             leaf upstream-interface-name {
               type string;
             }
             leaf rpf-check-disabled {
               type empty;
               description "Reverse path forwarding check is disabled";
             }
             leaf upstream-neighbor {
               type ipaddr;
               description "IP Address of Upstream Neighbor";
             }
             leaf incoming-interface-list-names {
               type string;
               description "Incoming interface names";
             }
             leaf outgoing-interface-count {
               type int32;
             }
             leaf rejected-downstream-interface-names {
               type string;
               description "Downstream interfaces rejected by bandwidth admission control";
             }
             leaf session-name {
               type string;
             }
             leaf forwarding-rate-kilobytes {
               type uint32;
             }
             leaf forwarding-rate-packets {
               type uint32;
             }
             leaf forwarded-packet-count {
               type uint32;
             }
             leaf multicast-statistics-timed-out {
               type empty;
             }
             leaf rpf-next-hop-id {
               type uint32;
             }
             leaf next-hop-id {
               type uint32;
             }
             leaf incoming-interface-list-id {
               type uint32;
               description "Incoming Interface list id";
             }
             leaf upstream-nbr-nh-id {
               type uint32;
               description "Upstream Neighbor Next-hop ID";
             }
             leaf upstream-protocol {
               type string;
             }
             leaf multicast-route-state {
               type string;
             }
             leaf multicast-route-forwarding-state {
               type string;
             }
             leaf multicast-route-uptime {
               type string;
             }
             leaf multicast-route-timeout {
               type string;
             }
             leaf interface-mismatch-count {
               type uint32;
             }
             container summary {
               leaf multicast-route-vlan {
                 type string;
               }
               leaf bandwidth-for-admission-control {
                 type uint64;
                 description "Bandwidth used for admission control";
               }
               container multicast-route-source {
               }
               container upstream-rpf-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
                 leaf upstream-rpf-labels {
                   type string;
                   description "Sender-Based RPF labels";
                 }
                 leaf rpf-session-id {
                   type uint32;
                   description "Session id";
                 }
                 leaf rpf-session-status {
                   type string;
                   description "Session Status";
                 }
                 leaf rpf-min-rate {
                   type uint32;
                   description "Min rate";
                 }
                 leaf rpf-weight {
                   type uint32;
                   description "RPF Weight";
                 }
               }
               container downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container multicast-route-summaries {
                 container multicast-route-summary {
                   leaf multicast-route-type {
                     type string;
                   }
                   leaf multicast-route-state-type {
                     type string;
                   }
                   leaf multicast-route-count {
                     type int32;
                   }
                 }
               }
             }
             container brief {
               leaf multicast-group-address {
                 type ipaddr;
                 description "Group address";
               }
               leaf multicast-group-prefix-length {
                 type uint32;
                 description "Group prefix length";
               }
               leaf multicast-route-protocol {
                 type string;
               }
               leaf multicast-route-packet-type {
                 type string;
               }
               leaf multicast-source-address {
                 type ipaddr;
                 description "Source address";
               }
               leaf multicast-source-prefix-length {
                 type uint32;
                 description "Source prefix length";
               }
               leaf multicast-route-vlan-id {
                 type int32;
               }
               leaf multicast-route-bridge-domain {
                 type string;
               }
               leaf multicast-route-mesh-group {
                 type string;
               }
               leaf upstream-interface-name {
                 type string;
               }
               leaf rpf-check-disabled {
                 type empty;
                 description "Reverse path forwarding check is disabled";
               }
               leaf upstream-neighbor {
                 type ipaddr;
                 description "IP Address of Upstream Neighbor";
               }
               leaf outgoing-interface-count {
                 type int32;
               }
               leaf incoming-interface-list-names {
                 type string;
                 description "Incoming interface names";
               }
               leaf rejected-downstream-interface-names {
                 type string;
                 description "Downstream interfaces rejected by bandwidth admission control";
               }
               leaf multicast-route-vlan {
                 type string;
               }
               leaf bandwidth-for-admission-control {
                 type uint64;
                 description "Bandwidth used for admission control";
               }
               container multicast-route-source {
               }
               container upstream-rpf-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
                 leaf upstream-rpf-labels {
                   type string;
                   description "Sender-Based RPF labels";
                 }
                 leaf rpf-session-id {
                   type uint32;
                   description "Session id";
                 }
                 leaf rpf-session-status {
                   type string;
                   description "Session Status";
                 }
                 leaf rpf-min-rate {
                   type uint32;
                   description "Min rate";
                 }
                 leaf rpf-weight {
                   type uint32;
                   description "RPF Weight";
                 }
               }
               container downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container multicast-route-summaries {
                 container multicast-route-summary {
                   leaf multicast-route-type {
                     type string;
                   }
                   leaf multicast-route-state-type {
                     type string;
                   }
                   leaf multicast-route-count {
                     type int32;
                   }
                 }
               }
             }
             container detail {
               leaf multicast-group-address {
                 type ipaddr;
                 description "Group address";
               }
               leaf multicast-group-prefix-length {
                 type uint32;
                 description "Group prefix length";
               }
               leaf multicast-route-protocol {
                 type string;
               }
               leaf multicast-route-packet-type {
                 type string;
               }
               leaf multicast-source-address {
                 type ipaddr;
                 description "Source address";
               }
               leaf multicast-source-prefix-length {
                 type uint32;
                 description "Source prefix length";
               }
               leaf multicast-route-vlan-id {
                 type int32;
               }
               leaf multicast-route-bridge-domain {
                 type string;
               }
               leaf multicast-route-mesh-group {
                 type string;
               }
               leaf upstream-interface-name {
                 type string;
               }
               leaf rpf-check-disabled {
                 type empty;
                 description "Reverse path forwarding check is disabled";
               }
               leaf upstream-neighbor {
                 type ipaddr;
                 description "IP Address of Upstream Neighbor";
               }
               leaf outgoing-interface-count {
                 type int32;
               }
               leaf incoming-interface-list-names {
                 type string;
                 description "Incoming interface names";
               }
               leaf rejected-downstream-interface-names {
                 type string;
                 description "Downstream interfaces rejected by bandwidth admission control";
               }
               leaf session-name {
                 type string;
               }
               leaf forwarding-rate-kilobytes {
                 type uint32;
               }
               leaf forwarding-rate-packets {
                 type uint32;
               }
               leaf forwarded-packet-count {
                 type uint32;
               }
               leaf multicast-statistics-timed-out {
                 type empty;
               }
               leaf rpf-next-hop-id {
                 type uint32;
               }
               leaf next-hop-id {
                 type uint32;
               }
               leaf incoming-interface-list-id {
                 type uint32;
                 description "Incoming Interface list id";
               }
               leaf upstream-nbr-nh-id {
                 type uint32;
                 description "Upstream Neighbor Next-hop ID";
               }
               leaf upstream-protocol {
                 type string;
               }
               leaf multicast-route-vlan {
                 type string;
               }
               leaf bandwidth-for-admission-control {
                 type uint64;
                 description "Bandwidth used for admission control";
               }
               container multicast-route-source {
               }
               container upstream-rpf-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
                 leaf upstream-rpf-labels {
                   type string;
                   description "Sender-Based RPF labels";
                 }
                 leaf rpf-session-id {
                   type uint32;
                   description "Session id";
                 }
                 leaf rpf-session-status {
                   type string;
                   description "Session Status";
                 }
                 leaf rpf-min-rate {
                   type uint32;
                   description "Min rate";
                 }
                 leaf rpf-weight {
                   type uint32;
                   description "RPF Weight";
                 }
               }
               container downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container multicast-route-summaries {
                 container multicast-route-summary {
                   leaf multicast-route-type {
                     type string;
                   }
                   leaf multicast-route-state-type {
                     type string;
                   }
                   leaf multicast-route-count {
                     type int32;
                   }
                 }
               }
             }
             container extensive {
               leaf multicast-group-address {
                 type ipaddr;
                 description "Group address";
               }
               leaf multicast-group-prefix-length {
                 type uint32;
                 description "Group prefix length";
               }
               leaf multicast-route-protocol {
                 type string;
               }
               leaf multicast-route-packet-type {
                 type string;
               }
               leaf multicast-source-address {
                 type ipaddr;
                 description "Source address";
               }
               leaf multicast-source-prefix-length {
                 type uint32;
                 description "Source prefix length";
               }
               leaf multicast-route-vlan-id {
                 type int32;
               }
               leaf multicast-route-bridge-domain {
                 type string;
               }
               leaf multicast-route-mesh-group {
                 type string;
               }
               leaf upstream-interface-name {
                 type string;
               }
               leaf rpf-check-disabled {
                 type empty;
                 description "Reverse path forwarding check is disabled";
               }
               leaf upstream-neighbor {
                 type ipaddr;
                 description "IP Address of Upstream Neighbor";
               }
               leaf outgoing-interface-count {
                 type int32;
               }
               leaf incoming-interface-list-names {
                 type string;
                 description "Incoming interface names";
               }
               leaf rejected-downstream-interface-names {
                 type string;
                 description "Downstream interfaces rejected by bandwidth admission control";
               }
               leaf session-name {
                 type string;
               }
               leaf forwarding-rate-kilobytes {
                 type uint32;
               }
               leaf forwarding-rate-packets {
                 type uint32;
               }
               leaf forwarded-packet-count {
                 type uint32;
               }
               leaf multicast-statistics-timed-out {
                 type empty;
               }
               leaf rpf-next-hop-id {
                 type uint32;
               }
               leaf next-hop-id {
                 type uint32;
               }
               leaf incoming-interface-list-id {
                 type uint32;
                 description "Incoming Interface list id";
               }
               leaf upstream-nbr-nh-id {
                 type uint32;
                 description "Upstream Neighbor Next-hop ID";
               }
               leaf upstream-protocol {
                 type string;
               }
               leaf multicast-route-state {
                 type string;
               }
               leaf multicast-route-forwarding-state {
                 type string;
               }
               leaf multicast-route-uptime {
                 type string;
               }
               leaf multicast-route-timeout {
                 type string;
               }
               leaf interface-mismatch-count {
                 type uint32;
               }
               leaf multicast-route-vlan {
                 type string;
               }
               leaf bandwidth-for-admission-control {
                 type uint64;
                 description "Bandwidth used for admission control";
               }
               container multicast-route-source {
               }
               container upstream-rpf-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
                 leaf upstream-rpf-labels {
                   type string;
                   description "Sender-Based RPF labels";
                 }
                 leaf rpf-session-id {
                   type uint32;
                   description "Session id";
                 }
                 leaf rpf-session-status {
                   type string;
                   description "Session Status";
                 }
                 leaf rpf-min-rate {
                   type uint32;
                   description "Min rate";
                 }
                 leaf rpf-weight {
                   type uint32;
                   description "RPF Weight";
                 }
               }
               container downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container multicast-route-summaries {
                 container multicast-route-summary {
                   leaf multicast-route-type {
                     type string;
                   }
                   leaf multicast-route-state-type {
                     type string;
                   }
                   leaf multicast-route-count {
                     type int32;
                   }
                 }
               }
             }
           }
           container l2ng-multicast-route {
             leaf multicast-group-address {
               type ipaddr;
               description "Group address";
             }
             leaf multicast-group-prefix-length {
               type uint32;
               description "Group prefix length";
             }
             leaf multicast-route-protocol {
               type string;
             }
             leaf multicast-route-packet-type {
               type string;
             }
             leaf multicast-source-address {
               type ipaddr;
               description "Source address";
             }
             leaf multicast-source-prefix-length {
               type uint32;
               description "Source prefix length";
             }
             leaf multicast-route-vlan-id {
               type int32;
             }
             leaf multicast-route-vlan {
               type string;
             }
             leaf multicast-route-mesh-group {
               type string;
             }
             leaf upstream-interface-name {
               type string;
             }
             leaf rpf-check-disabled {
               type empty;
               description "Reverse path forwarding check is disabled";
             }
             leaf incoming-interface-list-names {
               type string;
               description "Incoming interface names";
             }
             leaf rejected-downstream-interface-names {
               type string;
               description "Downstream interfaces rejected by bandwidth admission control";
             }
             leaf session-name {
               type string;
             }
             leaf forwarding-rate-kilobytes {
               type uint32;
             }
             leaf forwarding-rate-packets {
               type uint32;
             }
             leaf forwarded-packet-count {
               type uint32;
             }
             leaf multicast-statistics-timed-out {
               type empty;
             }
             leaf next-hop-id {
               type uint32;
             }
             leaf incoming-interface-list-id {
               type uint32;
               description "Incoming Interface list id";
             }
             leaf upstream-protocol {
               type string;
             }
             leaf multicast-route-state {
               type string;
             }
             leaf multicast-route-forwarding-state {
               type string;
             }
             leaf multicast-route-uptime {
               type string;
             }
             leaf multicast-route-timeout {
               type string;
             }
             leaf interface-mismatch-count {
               type uint32;
             }
             container summary {
               leaf multicast-route-bridge-domain {
                 type string;
               }
               leaf bandwidth-for-admission-control {
                 type uint64;
                 description "Bandwidth used for admission control";
               }
               container l2ng-downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container l2ng-multicast-route-summary {
                 leaf multicast-route-type {
                   type string;
                 }
                 leaf multicast-route-state-type {
                   type string;
                 }
                 leaf multicast-route-count {
                   type int32;
                 }
               }
             }
             container brief {
               leaf multicast-group-address {
                 type ipaddr;
                 description "Group address";
               }
               leaf multicast-group-prefix-length {
                 type uint32;
                 description "Group prefix length";
               }
               leaf multicast-route-protocol {
                 type string;
               }
               leaf multicast-route-packet-type {
                 type string;
               }
               leaf multicast-source-address {
                 type ipaddr;
                 description "Source address";
               }
               leaf multicast-source-prefix-length {
                 type uint32;
                 description "Source prefix length";
               }
               leaf multicast-route-vlan-id {
                 type int32;
               }
               leaf multicast-route-vlan {
                 type string;
               }
               leaf multicast-route-mesh-group {
                 type string;
               }
               leaf upstream-interface-name {
                 type string;
               }
               leaf rpf-check-disabled {
                 type empty;
                 description "Reverse path forwarding check is disabled";
               }
               leaf incoming-interface-list-names {
                 type string;
                 description "Incoming interface names";
               }
               leaf rejected-downstream-interface-names {
                 type string;
                 description "Downstream interfaces rejected by bandwidth admission control";
               }
               leaf multicast-route-bridge-domain {
                 type string;
               }
               leaf bandwidth-for-admission-control {
                 type uint64;
                 description "Bandwidth used for admission control";
               }
               container l2ng-downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container l2ng-multicast-route-summary {
                 leaf multicast-route-type {
                   type string;
                 }
                 leaf multicast-route-state-type {
                   type string;
                 }
                 leaf multicast-route-count {
                   type int32;
                 }
               }
             }
             container detail {
               leaf multicast-group-address {
                 type ipaddr;
                 description "Group address";
               }
               leaf multicast-group-prefix-length {
                 type uint32;
                 description "Group prefix length";
               }
               leaf multicast-route-protocol {
                 type string;
               }
               leaf multicast-route-packet-type {
                 type string;
               }
               leaf multicast-source-address {
                 type ipaddr;
                 description "Source address";
               }
               leaf multicast-source-prefix-length {
                 type uint32;
                 description "Source prefix length";
               }
               leaf multicast-route-vlan-id {
                 type int32;
               }
               leaf multicast-route-vlan {
                 type string;
               }
               leaf multicast-route-mesh-group {
                 type string;
               }
               leaf upstream-interface-name {
                 type string;
               }
               leaf rpf-check-disabled {
                 type empty;
                 description "Reverse path forwarding check is disabled";
               }
               leaf incoming-interface-list-names {
                 type string;
                 description "Incoming interface names";
               }
               leaf rejected-downstream-interface-names {
                 type string;
                 description "Downstream interfaces rejected by bandwidth admission control";
               }
               leaf session-name {
                 type string;
               }
               leaf forwarding-rate-kilobytes {
                 type uint32;
               }
               leaf forwarding-rate-packets {
                 type uint32;
               }
               leaf forwarded-packet-count {
                 type uint32;
               }
               leaf multicast-statistics-timed-out {
                 type empty;
               }
               leaf next-hop-id {
                 type uint32;
               }
               leaf incoming-interface-list-id {
                 type uint32;
                 description "Incoming Interface list id";
               }
               leaf upstream-protocol {
                 type string;
               }
               leaf multicast-route-bridge-domain {
                 type string;
               }
               leaf bandwidth-for-admission-control {
                 type uint64;
                 description "Bandwidth used for admission control";
               }
               container l2ng-downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container l2ng-multicast-route-summary {
                 leaf multicast-route-type {
                   type string;
                 }
                 leaf multicast-route-state-type {
                   type string;
                 }
                 leaf multicast-route-count {
                   type int32;
                 }
               }
             }
             container extensive {
               leaf multicast-group-address {
                 type ipaddr;
                 description "Group address";
               }
               leaf multicast-group-prefix-length {
                 type uint32;
                 description "Group prefix length";
               }
               leaf multicast-route-protocol {
                 type string;
               }
               leaf multicast-route-packet-type {
                 type string;
               }
               leaf multicast-source-address {
                 type ipaddr;
                 description "Source address";
               }
               leaf multicast-source-prefix-length {
                 type uint32;
                 description "Source prefix length";
               }
               leaf multicast-route-vlan-id {
                 type int32;
               }
               leaf multicast-route-vlan {
                 type string;
               }
               leaf multicast-route-mesh-group {
                 type string;
               }
               leaf upstream-interface-name {
                 type string;
               }
               leaf rpf-check-disabled {
                 type empty;
                 description "Reverse path forwarding check is disabled";
               }
               leaf incoming-interface-list-names {
                 type string;
                 description "Incoming interface names";
               }
               leaf rejected-downstream-interface-names {
                 type string;
                 description "Downstream interfaces rejected by bandwidth admission control";
               }
               leaf session-name {
                 type string;
               }
               leaf forwarding-rate-kilobytes {
                 type uint32;
               }
               leaf forwarding-rate-packets {
                 type uint32;
               }
               leaf forwarded-packet-count {
                 type uint32;
               }
               leaf multicast-statistics-timed-out {
                 type empty;
               }
               leaf next-hop-id {
                 type uint32;
               }
               leaf incoming-interface-list-id {
                 type uint32;
                 description "Incoming Interface list id";
               }
               leaf upstream-protocol {
                 type string;
               }
               leaf multicast-route-state {
                 type string;
               }
               leaf multicast-route-forwarding-state {
                 type string;
               }
               leaf multicast-route-uptime {
                 type string;
               }
               leaf multicast-route-timeout {
                 type string;
               }
               leaf interface-mismatch-count {
                 type uint32;
               }
               leaf multicast-route-bridge-domain {
                 type string;
               }
               leaf bandwidth-for-admission-control {
                 type uint64;
                 description "Bandwidth used for admission control";
               }
               container l2ng-downstream-interface-names {
                 leaf interface-name {
                   type string;
                   description "Name of interface";
                 }
                 leaf interface-nh-index {
                   type uint32;
                   description "Logical interface nexthop index";
                 }
                 leaf sub-mcnh-index {
                   type uint32;
                   description "Sub multicast composite nexthop index";
                 }
               }
               container l2ng-multicast-route-summary {
                 leaf multicast-route-type {
                   type string;
                 }
                 leaf multicast-route-state-type {
                   type string;
                 }
                 leaf multicast-route-count {
                   type int32;
                 }
               }
             }
           }
         }
       }
     }
   }
   rpc get-satellite-control-multicast {
     description "Show the satellite multicast snooping information";
     input {
       leaf verbosity_level {
         default "brief";
         type enumeration {
           enum "brief" {
             description "Display brief output (default)";
           }
           enum "detail" {
             description "Display detailed output";
           }
           enum "extensive" {
             description "Display extensive output";
           }
         }
       }
       leaf vswitch-name {
         description "Virtual switch name";
         type string;
       }
       leaf bridge-domain-name {
         description "Bridge domain name";
         type string;
       }
       leaf group {
         description "Multicast Group Address";
         type ipaddr;
       }
       leaf source {
         description "Source Address";
         type ipaddr;
       }
     }
   }
   rpc get-multicast-snooping-next-hops-information {
     description "Show the multicast next-hop snooping table";
     input {
       leaf verbosity_level {
         default "brief";
         type enumeration {
           enum "brief" {
             description "Display brief output (default)";
           }
           enum "detail" {
             description "Display detailed output";
           }
         }
       }
       leaf identifier {
         description "ID of next hop";
         type uint32;
       }
       leaf family {
         description "Address family";
         type enumeration {
           enum "inet" {
             description "Display IPv4 information";
           }
           enum "inet6" {
             description "Display IPv6 information";
           }
         }
       }
     }
     output {
       container multicast-next-hops-information {
         container next-hops-family {
           leaf address-family {
             type string;
           }
           container iflist-next-hop {
             container regular {
               leaf next-hop-id {
                 type uint32;
               }
               leaf next-hop-ref-count {
                 type uint32;
               }
               leaf next-hop-kernel-ref-count {
                 type uint32;
               }
               leaf next-hop-addr {
                 type uint32;
               }
               leaf rpf-next-hop-id {
                 type uint32;
               }
               container next-hop-downstream-interface {
                 leaf interface-name {
                   type string;
                   description "Name of interface";
                 }
                 leaf interface-index {
                   type int32;
                 }
                 leaf interface-nh-index {
                   type uint32;
                   description "Logical interface nexthop index";
                 }
               }
             }
             container terse {
               leaf next-hop-id {
                 type uint32;
               }
               leaf next-hop-ref-count {
                 type uint32;
               }
               leaf next-hop-kernel-ref-count {
                 type uint32;
               }
               leaf next-hop-downstream-interface-count {
                 type uint32;
               }
               leaf rpf-next-hop-id {
                 type uint32;
               }
               container next-hop-downstream-interface {
                 leaf interface-nh-index {
                   type uint32;
                   description "Logical interface nexthop index";
                 }
               }
             }
           }
         }
       }
     }
   }
   rpc get-satellite-control-indirect-next-hop {
     description "Show satellite multicast next-hops";
     input {
       leaf verbosity_level {
         default "brief";
         type enumeration {
           enum "brief" {
             description "Display brief output (default)";
           }
           enum "detail" {
             description "Display detailed output";
           }
           enum "extensive" {
             description "Display extensive output";
           }
         }
       }
       leaf nexthop-id {
         description "Next-hop ID";
         type int32;
       }
     }
   }
   rpc get-satellite-control-ecid {
     description "Show the satellite multicast ECID mapping database";
     input {
       leaf verbosity_level {
         default "brief";
         type enumeration {
           enum "brief" {
             description "Display brief output (default)";
           }
           enum "detail" {
             description "Display detailed output";
           }
           enum "extensive" {
             description "Display extensive output";
           }
         }
       }
       leaf device-id {
         description "Device ID";
         type int32;
       }
       leaf ecid {
         description "ECID";
         type int32;
       }
       leaf reference-id {
         description "Reference ID";
         type int32;
       }
     }
   }
   rpc get-satellite-control-summary {
     description "Show satellite multicast summary information";
     input {
       leaf verbosity_level {
         default "detail";
         type enumeration {
           enum "brief" {
             description "Display brief output (default)";
           }
           enum "detail" {
             description "Display detailed output";
           }
         }
       }
     }
   }
 }
