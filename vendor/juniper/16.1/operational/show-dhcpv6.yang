/*
 * Copyright (c) 2017 Juniper Networks, Inc.
 * All rights reserved.
 */

 module show-dhcpv6 {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-dhcpv6-relay-binding-information {
     description "Show DHCPv6 relay client binding information";
     input {
       leaf level {
         default "brief";
         type enumeration {
           enum "brief" {
             description "Display brief information";
           }
           enum "detail" {
             description "Display detailed information";
           }
           enum "summary" {
             description "Display summary information";
           }
         }
       }
       container show-choice {
         choice show-choice_c {
           case address {
             leaf address {
               description "IPv6 Prefix, session-id or CID of DHCPv6 client binding";
               type string;
             }
           }
           case interfaces-wildcard {
             leaf interfaces-wildcard {
               description "Interfaces to show bindings on (can be '*' wildcard)";
               type string {
                 junos:posix-pattern "^( (((ge-)|(xe-)|(et-))( [[:digit:]]+(-([[:digit:]]+))+(-([[:digit:]]+)?)?)?) | (ae))+$";
                 junos:pattern-message "Must be an interface wildcard string";
               }
             }
           }
           case interfaces-vlan {
             leaf interfaces-vlan {
               description "Interface VLAN-ID/SVLAN-ID on which to show bindings";
               type string {
                 junos:posix-pattern "^(( (((ge-)|(xe-)|(et-))( [[:digit:]]+(-([[:digit:]]+))+(-([[:digit:]]+)?)?)?) | (ae))(/:)([[:digit:]]+(-[[:digit:]]+))?)+$";
                 junos:pattern-message "Must be an interface:VLAN string";
               }
             }
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcpv6-relay-binding-information {
         container dhcpv6-brief {
           description "Information about the address assigned to each of one or more DHCPv6 clients";
           container dhcpv6-binding-summary {
             leaf dhcpv6-binding-count {
               type int32;
               description "Number of bindings in this routing instance";
             }
             leaf dhcpv6-init-count {
               type int32;
               description "Number of clients in init state";
             }
             leaf dhcpv6-bound-count {
               type int32;
               description "Number of clients in bound state ";
             }
             leaf dhcpv6-selecting-count {
               type int32;
               description "Number of clients in selecting state ";
             }
             leaf dhcpv6-requesting-count {
               type int32;
               description "Number of clients in requesting state ";
             }
             leaf dhcpv6-renewing-count {
               type int32;
               description "Number of clients in renewing state ";
             }
             leaf dhcpv6-rebinding-count {
               type int32;
               description "Number of clients in rebinding state ";
             }
             leaf dhcpv6-releasing-count {
               type int32;
               description "Number of clients in releasing state ";
             }
             leaf dhcpv6-restore-count {
               type int32;
               description "Number of clients waiting to be restored";
             }
           }
           container dhcpv6-binding-internal-states {
             leaf dhcpv6-init {
               type int32;
               description "Number of clients init state";
             }
             leaf dhcpv6-selecting {
               type int32;
               description "Number of clients in selecting state";
             }
             leaf dhcpv6-requesting {
               type int32;
               description "Number of clients in requesting state";
             }
             leaf dhcpv6-bound {
               type int32;
               description "Number of clients in bound state";
             }
             leaf dhcpv6-renewing {
               type int32;
               description "Number of clients in renewing state";
             }
             leaf dhcpv6-rebinding {
               type int32;
               description "Number of clients in rebinding state";
             }
             leaf dhcpv6-wait-cm-add {
               type int32;
               description "Number of clients in wait-cm-add state";
             }
             leaf dhcpv6-wait-cm-add-delete {
               type int32;
               description "Number of clients in wait-cm-add-delete state";
             }
             leaf dhcpv6-wait-cm-delete {
               type int32;
               description "Number of clients in wait-cm-delete state";
             }
             leaf dhcpv6-wait-subscr-add {
               type int32;
               description "Number of clients in wait-subscr-add state";
             }
             leaf dhcpv6-wait-subscr-add-delete {
               type int32;
               description "Number of clients in wait-subscr-add-delete state";
             }
             leaf dhcpv6-wait-subscr-delete {
               type int32;
               description "Number of clients in wait-subscr-delete state";
             }
             leaf dhcpv6-wait-cm-update {
               type int32;
               description "Number of clients in wait-cm-update state";
             }
             leaf dhcpv6-wait-cm-update-delete {
               type int32;
               description "Number of clients in wait-cm-update-delete state";
             }
             leaf dhcpv6-wait-auth-req {
               type int32;
               description "Number of clients in wait-auth-req state";
             }
             leaf dhcpv6-wait-auth-req-delete {
               type int32;
               description "Number of clients in wait-auth-req-delete state";
             }
             leaf dhcpv6-wait-auth-req-release {
               type int32;
               description "Number of clients in wait-auth-req-release state";
             }
             leaf dhcpv6-wait-auth-req-release-terminated {
               type int32;
               description "Number of clients in wait-auth-req-release-terminated state";
             }
             leaf dhcpv6-wait-auth-act-prof {
               type int32;
               description "Number of clients in wait-auth-act-prof state";
             }
             leaf dhcpv6-wait-auth-act-prof-delete {
               type int32;
               description "Number of clients in wait-auth-act-prof-delete state";
             }
             leaf dhcpv6-wait-service-deactivation {
               type int32;
               description "Number of clients in wait-service-deactivation state";
             }
             leaf dhcpv6-wait-dual-stack-peer-logout {
               type int32;
               description "Number of clients in wait-dual-stack-peer-logout state";
             }
             leaf dhcpv6-wait-prof-inst {
               type int32;
               description "Number of clients in wait-prof-inst state";
             }
             leaf dhcpv6-wait-prof-inst-delete {
               type int32;
               description "Number of clients in wait-prof-inst-delete state";
             }
             leaf dhcpv6-wait-prof-delete {
               type int32;
               description "Number of clients in wait-prof-delete state";
             }
             leaf dhcpv6-wait-interface {
               type int32;
               description "Number of clients in wait-interface state";
             }
             leaf dhcpv6-wait-sdb-init-mirror-req {
               type int32;
               description "Number of clients in wait-sdb-init-mirror-req state";
             }
             leaf dhcpv6-wait-sdb-init-mirror-req-delete {
               type int32;
               description "Number of clients in wait-sdb-init-mirror-req-delete state";
             }
             leaf dhcpv6-wait-sdb-active-mirror-req {
               type int32;
               description "Number of clients in wait-sdb-active-mirror-req state";
             }
             leaf dhcpv6-wait-sdb-active-mirror-req-delete {
               type int32;
               description "Number of clients in wait-sdb-active-mirror-req-delete state";
             }
             leaf dhcpv6-wait-sdb-terminated-mirror-req {
               type int32;
               description "Number of clients in wait-sdb-terminated-mirror-req state";
             }
             leaf dhcpv6-wait-sdb-dual-stack-terminating {
               type int32;
               description "Number of clients in wait-sdb-dual-stack-terminating state";
             }
             leaf dhcpv6-wait-sdb-dual-stack-clear {
               type int32;
               description "Number of clients in wait-sdb-dual-stack-clear state";
             }
             leaf dhcpv6-bound-on-intf-delete {
               type int32;
               description "Number of clients in bound-on-intf-delete state";
             }
             leaf dhcpv6-release-wait-server-reply {
               type int32;
               description "Number of clients in release-wait-server-reply state";
             }
           }
           container dhcpv6-binding {
             description "Information about the address assigned to an IPv6 Dynamic Host Configuration Protocol client";
             leaf allocated-address {
               type ipaddr;
               description "IPv4 or IPv6 address assigned to the DHCP client";
             }
             leaf session-id {
               type string;
               description "Session ID of the client";
             }
             leaf lease-expires {
               type int32;
               description "Number of seconds lease will expire in";
             }
             leaf lease-state {
               type string;
               description "Status of the address assignment";
             }
             leaf interface-name {
               type string;
               description "Name of the interface via which the DHCP server transmitted the address assignment";
             }
             leaf client-duid {
               type string;
               description "Client DUID";
             }
           }
         }
         container dhcpv6-detail {
           description "Information about the address assigned to each of one or more DHCPv6 clients";
           container dhcpv6-binding-summary {
             leaf dhcpv6-binding-count {
               type int32;
               description "Number of bindings in this routing instance";
             }
             leaf dhcpv6-init-count {
               type int32;
               description "Number of clients in init state";
             }
             leaf dhcpv6-bound-count {
               type int32;
               description "Number of clients in bound state ";
             }
             leaf dhcpv6-selecting-count {
               type int32;
               description "Number of clients in selecting state ";
             }
             leaf dhcpv6-requesting-count {
               type int32;
               description "Number of clients in requesting state ";
             }
             leaf dhcpv6-renewing-count {
               type int32;
               description "Number of clients in renewing state ";
             }
             leaf dhcpv6-rebinding-count {
               type int32;
               description "Number of clients in rebinding state ";
             }
             leaf dhcpv6-releasing-count {
               type int32;
               description "Number of clients in releasing state ";
             }
             leaf dhcpv6-restore-count {
               type int32;
               description "Number of clients waiting to be restored";
             }
           }
           container dhcpv6-binding-internal-states {
             leaf dhcpv6-init {
               type int32;
               description "Number of clients init state";
             }
             leaf dhcpv6-selecting {
               type int32;
               description "Number of clients in selecting state";
             }
             leaf dhcpv6-requesting {
               type int32;
               description "Number of clients in requesting state";
             }
             leaf dhcpv6-bound {
               type int32;
               description "Number of clients in bound state";
             }
             leaf dhcpv6-renewing {
               type int32;
               description "Number of clients in renewing state";
             }
             leaf dhcpv6-rebinding {
               type int32;
               description "Number of clients in rebinding state";
             }
             leaf dhcpv6-wait-cm-add {
               type int32;
               description "Number of clients in wait-cm-add state";
             }
             leaf dhcpv6-wait-cm-add-delete {
               type int32;
               description "Number of clients in wait-cm-add-delete state";
             }
             leaf dhcpv6-wait-cm-delete {
               type int32;
               description "Number of clients in wait-cm-delete state";
             }
             leaf dhcpv6-wait-subscr-add {
               type int32;
               description "Number of clients in wait-subscr-add state";
             }
             leaf dhcpv6-wait-subscr-add-delete {
               type int32;
               description "Number of clients in wait-subscr-add-delete state";
             }
             leaf dhcpv6-wait-subscr-delete {
               type int32;
               description "Number of clients in wait-subscr-delete state";
             }
             leaf dhcpv6-wait-cm-update {
               type int32;
               description "Number of clients in wait-cm-update state";
             }
             leaf dhcpv6-wait-cm-update-delete {
               type int32;
               description "Number of clients in wait-cm-update-delete state";
             }
             leaf dhcpv6-wait-auth-req {
               type int32;
               description "Number of clients in wait-auth-req state";
             }
             leaf dhcpv6-wait-auth-req-delete {
               type int32;
               description "Number of clients in wait-auth-req-delete state";
             }
             leaf dhcpv6-wait-auth-req-release {
               type int32;
               description "Number of clients in wait-auth-req-release state";
             }
             leaf dhcpv6-wait-auth-req-release-terminated {
               type int32;
               description "Number of clients in wait-auth-req-release-terminated state";
             }
             leaf dhcpv6-wait-auth-act-prof {
               type int32;
               description "Number of clients in wait-auth-act-prof state";
             }
             leaf dhcpv6-wait-auth-act-prof-delete {
               type int32;
               description "Number of clients in wait-auth-act-prof-delete state";
             }
             leaf dhcpv6-wait-service-deactivation {
               type int32;
               description "Number of clients in wait-service-deactivation state";
             }
             leaf dhcpv6-wait-dual-stack-peer-logout {
               type int32;
               description "Number of clients in wait-dual-stack-peer-logout state";
             }
             leaf dhcpv6-wait-prof-inst {
               type int32;
               description "Number of clients in wait-prof-inst state";
             }
             leaf dhcpv6-wait-prof-inst-delete {
               type int32;
               description "Number of clients in wait-prof-inst-delete state";
             }
             leaf dhcpv6-wait-prof-delete {
               type int32;
               description "Number of clients in wait-prof-delete state";
             }
             leaf dhcpv6-wait-interface {
               type int32;
               description "Number of clients in wait-interface state";
             }
             leaf dhcpv6-wait-sdb-init-mirror-req {
               type int32;
               description "Number of clients in wait-sdb-init-mirror-req state";
             }
             leaf dhcpv6-wait-sdb-init-mirror-req-delete {
               type int32;
               description "Number of clients in wait-sdb-init-mirror-req-delete state";
             }
             leaf dhcpv6-wait-sdb-active-mirror-req {
               type int32;
               description "Number of clients in wait-sdb-active-mirror-req state";
             }
             leaf dhcpv6-wait-sdb-active-mirror-req-delete {
               type int32;
               description "Number of clients in wait-sdb-active-mirror-req-delete state";
             }
             leaf dhcpv6-wait-sdb-terminated-mirror-req {
               type int32;
               description "Number of clients in wait-sdb-terminated-mirror-req state";
             }
             leaf dhcpv6-wait-sdb-dual-stack-terminating {
               type int32;
               description "Number of clients in wait-sdb-dual-stack-terminating state";
             }
             leaf dhcpv6-wait-sdb-dual-stack-clear {
               type int32;
               description "Number of clients in wait-sdb-dual-stack-clear state";
             }
             leaf dhcpv6-bound-on-intf-delete {
               type int32;
               description "Number of clients in bound-on-intf-delete state";
             }
             leaf dhcpv6-release-wait-server-reply {
               type int32;
               description "Number of clients in release-wait-server-reply state";
             }
           }
           container dhcpv6-binding {
             description "Information about the address assigned to an IPv6 Dynamic Host Configuration Protocol client";
             leaf session-id {
               type string;
               description "Session ID of the client";
             }
             leaf allocated-address {
               type ipaddr;
               description "IPv4 or IPv6 address assigned to the DHCP client";
             }
             leaf allocated-prefix {
               type ipaddr;
               description "IPv6 prefix address assigned to the DHCP client";
             }
             leaf client-duid {
               type string;
               description "Client DUID";
             }
             leaf client-id-len {
               type int32;
               description "Number of bytes in client id";
             }
             leaf client-id {
               type string;
               description "Four bytes of the client id";
             }
             leaf alt-client-id-len {
               type int32;
               description "Number of bytes in alternate client id";
             }
             leaf alt-client-id {
               type string;
               description "Four byte of the alternate client id";
             }
             leaf lease-state {
               type string;
               description "Status of the address assignment";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf preferred-lease-end-time {
               type string;
               description "Prefferred time when the address assignment should expire, in the format YYYY-MM-DD hh:mm:ss TZ (year, month, date, hour in 24-hour format, minute, second, time zone). The value 'never' indicates that the lease does not expire";
             }
             leaf preferred-lease-expires {
               type int32;
               description "Number of seconds preferred lease will expire in";
             }
             leaf lease-start-time {
               type string;
               description "Time when the client obtained the address assignment, in the format YYYY-MM-DD hh:mm:ss TZ (year, month, date, hour in 24-hour format, minute, second, time zone)";
             }
             leaf lease-time-violated {
               type string;
               description "Status of lease time validation violation";
             }
             leaf last-packet-received-time {
               type string;
               description "Time at which the most recent packet from the client was received, in the format YYYY-MM-DD hh:mm:ss TZ (year, month, date, hour in 24-hour format, minute, second, time zone)";
             }
             leaf interface-name {
               type string;
               description "Name of the interface via which the DHCP server transmitted the address assignment";
             }
             leaf vlan-id {
               type int32;
               description "Vlan id of the client interface";
             }
             leaf svlan-id {
               type int32;
               description "Svlan id of the client interface";
             }
             leaf demux-interface-name {
               type string;
               description "Demux interface name";
             }
             leaf server-ip-address {
               type ipaddr;
               description "IP address of the DHCP server";
             }
             leaf next-hop-server-facing-relay {
               type ipaddr;
               description "IP address of the DHCP Relay one hop closer to the Server";
             }
             leaf server-interface-name {
               type string;
               description "Interface that server was from";
             }
             leaf v6-relay-address {
               type ipaddr;
               description "IPv6 address of the DHCPv6 relay that relayed the address assigned by the DHCPv6 server";
             }
             leaf previous-v6-relay-address {
               type ipaddr;
               description "Previous IPv6 address of the DHCPv6 relay that relayed the address assigned by the DHCPv6 server";
             }
             leaf pool-name {
               type string;
               description "Client pool name";
             }
             leaf profile-name {
               type string;
               description "Client profile name";
             }
             leaf liveness-detection-state {
               type string;
               description "Status of the liveness detection session with the client";
             }
             leaf dual-stack-group {
               type string;
               description "Dual stack group referenece by this client";
             }
             leaf dual-stack-peer-address {
               type ipaddr;
               description "Peer IP or IPV6 address for this dual stack client";
             }
             leaf generated-circuit-id {
               type string;
               description "Generated circuit id";
             }
             leaf generated-remote-id-enterprise-number {
               type int32;
               description "Generated remote id enterprise number";
             }
             leaf generated-remote-id {
               type string;
               description "Generated remote id";
             }
             leaf dhcpv6-server-id {
               type string;
               description "DHCPv6 server id";
             }
             leaf dhcp-lease-binding-type {
               type string;
               description "Type of the address assignment";
             }
             leaf client-option-type {
               type string;
               description "Type option 60 or option 82";
             }
             leaf client-option-len {
               type int32;
               description "Number of bytes in client option 60 / option 82 data";
             }
             leaf client-option-data {
               type string;
               description "Hex dump of client option 60 / option 82 data";
             }
             leaf option-18-length-from-client {
               type int32;
               description "Option 18 length from client";
             }
             leaf option-18-data-from-client {
               type string;
               description "Option 18 data from client";
             }
             leaf hardware-type {
               type string;
               description "Client hardware type";
             }
             leaf logical-system-routing-instance {
               type string;
               description "Client router context logical system and routing instance";
             }
             leaf bridge-domain {
               type string;
               description "Client router context bridge domain";
             }
             leaf authentication-num-servers {
               type int32;
               description "Number of servers in authentication group";
             }
             leaf client-stale-count {
               type int32;
               description "Number of clients in stale list";
             }
             leaf auth-client-limit {
               type int32;
               description "Client limit from authentication daemon";
             }
             leaf auth-relay-server-group {
               type string;
               description "Value of pointer to authentication daemon server group";
             }
             leaf aci-iflset-name {
               type string;
               description "ACI-VLAN iflset name";
             }
             leaf aci-iflset-index {
               type int32;
               description "ACI-VLAN iflset index";
             }
             leaf aci-iflset-session-id {
               type string;
               description "ACI-VLAN iflset Session ID";
             }
           }
         }
       }
     }
   }
   rpc get-dhcpv6-relay-binding-ltv-information {
     description "Display lease time violated client bindings";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcpv6-relay-binding-information {
         container dhcpv6-brief {
           description "Information about the address assigned to each of one or more DHCPv6 clients";
           container dhcpv6-binding-summary {
             leaf dhcpv6-binding-count {
               type int32;
               description "Number of bindings in this routing instance";
             }
             leaf dhcpv6-init-count {
               type int32;
               description "Number of clients in init state";
             }
             leaf dhcpv6-bound-count {
               type int32;
               description "Number of clients in bound state ";
             }
             leaf dhcpv6-selecting-count {
               type int32;
               description "Number of clients in selecting state ";
             }
             leaf dhcpv6-requesting-count {
               type int32;
               description "Number of clients in requesting state ";
             }
             leaf dhcpv6-renewing-count {
               type int32;
               description "Number of clients in renewing state ";
             }
             leaf dhcpv6-rebinding-count {
               type int32;
               description "Number of clients in rebinding state ";
             }
             leaf dhcpv6-releasing-count {
               type int32;
               description "Number of clients in releasing state ";
             }
             leaf dhcpv6-restore-count {
               type int32;
               description "Number of clients waiting to be restored";
             }
           }
           container dhcpv6-binding-internal-states {
             leaf dhcpv6-init {
               type int32;
               description "Number of clients init state";
             }
             leaf dhcpv6-selecting {
               type int32;
               description "Number of clients in selecting state";
             }
             leaf dhcpv6-requesting {
               type int32;
               description "Number of clients in requesting state";
             }
             leaf dhcpv6-bound {
               type int32;
               description "Number of clients in bound state";
             }
             leaf dhcpv6-renewing {
               type int32;
               description "Number of clients in renewing state";
             }
             leaf dhcpv6-rebinding {
               type int32;
               description "Number of clients in rebinding state";
             }
             leaf dhcpv6-wait-cm-add {
               type int32;
               description "Number of clients in wait-cm-add state";
             }
             leaf dhcpv6-wait-cm-add-delete {
               type int32;
               description "Number of clients in wait-cm-add-delete state";
             }
             leaf dhcpv6-wait-cm-delete {
               type int32;
               description "Number of clients in wait-cm-delete state";
             }
             leaf dhcpv6-wait-subscr-add {
               type int32;
               description "Number of clients in wait-subscr-add state";
             }
             leaf dhcpv6-wait-subscr-add-delete {
               type int32;
               description "Number of clients in wait-subscr-add-delete state";
             }
             leaf dhcpv6-wait-subscr-delete {
               type int32;
               description "Number of clients in wait-subscr-delete state";
             }
             leaf dhcpv6-wait-cm-update {
               type int32;
               description "Number of clients in wait-cm-update state";
             }
             leaf dhcpv6-wait-cm-update-delete {
               type int32;
               description "Number of clients in wait-cm-update-delete state";
             }
             leaf dhcpv6-wait-auth-req {
               type int32;
               description "Number of clients in wait-auth-req state";
             }
             leaf dhcpv6-wait-auth-req-delete {
               type int32;
               description "Number of clients in wait-auth-req-delete state";
             }
             leaf dhcpv6-wait-auth-req-release {
               type int32;
               description "Number of clients in wait-auth-req-release state";
             }
             leaf dhcpv6-wait-auth-req-release-terminated {
               type int32;
               description "Number of clients in wait-auth-req-release-terminated state";
             }
             leaf dhcpv6-wait-auth-act-prof {
               type int32;
               description "Number of clients in wait-auth-act-prof state";
             }
             leaf dhcpv6-wait-auth-act-prof-delete {
               type int32;
               description "Number of clients in wait-auth-act-prof-delete state";
             }
             leaf dhcpv6-wait-service-deactivation {
               type int32;
               description "Number of clients in wait-service-deactivation state";
             }
             leaf dhcpv6-wait-dual-stack-peer-logout {
               type int32;
               description "Number of clients in wait-dual-stack-peer-logout state";
             }
             leaf dhcpv6-wait-prof-inst {
               type int32;
               description "Number of clients in wait-prof-inst state";
             }
             leaf dhcpv6-wait-prof-inst-delete {
               type int32;
               description "Number of clients in wait-prof-inst-delete state";
             }
             leaf dhcpv6-wait-prof-delete {
               type int32;
               description "Number of clients in wait-prof-delete state";
             }
             leaf dhcpv6-wait-interface {
               type int32;
               description "Number of clients in wait-interface state";
             }
             leaf dhcpv6-wait-sdb-init-mirror-req {
               type int32;
               description "Number of clients in wait-sdb-init-mirror-req state";
             }
             leaf dhcpv6-wait-sdb-init-mirror-req-delete {
               type int32;
               description "Number of clients in wait-sdb-init-mirror-req-delete state";
             }
             leaf dhcpv6-wait-sdb-active-mirror-req {
               type int32;
               description "Number of clients in wait-sdb-active-mirror-req state";
             }
             leaf dhcpv6-wait-sdb-active-mirror-req-delete {
               type int32;
               description "Number of clients in wait-sdb-active-mirror-req-delete state";
             }
             leaf dhcpv6-wait-sdb-terminated-mirror-req {
               type int32;
               description "Number of clients in wait-sdb-terminated-mirror-req state";
             }
             leaf dhcpv6-wait-sdb-dual-stack-terminating {
               type int32;
               description "Number of clients in wait-sdb-dual-stack-terminating state";
             }
             leaf dhcpv6-wait-sdb-dual-stack-clear {
               type int32;
               description "Number of clients in wait-sdb-dual-stack-clear state";
             }
             leaf dhcpv6-bound-on-intf-delete {
               type int32;
               description "Number of clients in bound-on-intf-delete state";
             }
             leaf dhcpv6-release-wait-server-reply {
               type int32;
               description "Number of clients in release-wait-server-reply state";
             }
           }
           container dhcpv6-binding {
             description "Information about the address assigned to an IPv6 Dynamic Host Configuration Protocol client";
             leaf allocated-address {
               type ipaddr;
               description "IPv4 or IPv6 address assigned to the DHCP client";
             }
             leaf session-id {
               type string;
               description "Session ID of the client";
             }
             leaf lease-expires {
               type int32;
               description "Number of seconds lease will expire in";
             }
             leaf lease-state {
               type string;
               description "Status of the address assignment";
             }
             leaf interface-name {
               type string;
               description "Name of the interface via which the DHCP server transmitted the address assignment";
             }
             leaf client-duid {
               type string;
               description "Client DUID";
             }
           }
         }
         container dhcpv6-detail {
           description "Information about the address assigned to each of one or more DHCPv6 clients";
           container dhcpv6-binding-summary {
             leaf dhcpv6-binding-count {
               type int32;
               description "Number of bindings in this routing instance";
             }
             leaf dhcpv6-init-count {
               type int32;
               description "Number of clients in init state";
             }
             leaf dhcpv6-bound-count {
               type int32;
               description "Number of clients in bound state ";
             }
             leaf dhcpv6-selecting-count {
               type int32;
               description "Number of clients in selecting state ";
             }
             leaf dhcpv6-requesting-count {
               type int32;
               description "Number of clients in requesting state ";
             }
             leaf dhcpv6-renewing-count {
               type int32;
               description "Number of clients in renewing state ";
             }
             leaf dhcpv6-rebinding-count {
               type int32;
               description "Number of clients in rebinding state ";
             }
             leaf dhcpv6-releasing-count {
               type int32;
               description "Number of clients in releasing state ";
             }
             leaf dhcpv6-restore-count {
               type int32;
               description "Number of clients waiting to be restored";
             }
           }
           container dhcpv6-binding-internal-states {
             leaf dhcpv6-init {
               type int32;
               description "Number of clients init state";
             }
             leaf dhcpv6-selecting {
               type int32;
               description "Number of clients in selecting state";
             }
             leaf dhcpv6-requesting {
               type int32;
               description "Number of clients in requesting state";
             }
             leaf dhcpv6-bound {
               type int32;
               description "Number of clients in bound state";
             }
             leaf dhcpv6-renewing {
               type int32;
               description "Number of clients in renewing state";
             }
             leaf dhcpv6-rebinding {
               type int32;
               description "Number of clients in rebinding state";
             }
             leaf dhcpv6-wait-cm-add {
               type int32;
               description "Number of clients in wait-cm-add state";
             }
             leaf dhcpv6-wait-cm-add-delete {
               type int32;
               description "Number of clients in wait-cm-add-delete state";
             }
             leaf dhcpv6-wait-cm-delete {
               type int32;
               description "Number of clients in wait-cm-delete state";
             }
             leaf dhcpv6-wait-subscr-add {
               type int32;
               description "Number of clients in wait-subscr-add state";
             }
             leaf dhcpv6-wait-subscr-add-delete {
               type int32;
               description "Number of clients in wait-subscr-add-delete state";
             }
             leaf dhcpv6-wait-subscr-delete {
               type int32;
               description "Number of clients in wait-subscr-delete state";
             }
             leaf dhcpv6-wait-cm-update {
               type int32;
               description "Number of clients in wait-cm-update state";
             }
             leaf dhcpv6-wait-cm-update-delete {
               type int32;
               description "Number of clients in wait-cm-update-delete state";
             }
             leaf dhcpv6-wait-auth-req {
               type int32;
               description "Number of clients in wait-auth-req state";
             }
             leaf dhcpv6-wait-auth-req-delete {
               type int32;
               description "Number of clients in wait-auth-req-delete state";
             }
             leaf dhcpv6-wait-auth-req-release {
               type int32;
               description "Number of clients in wait-auth-req-release state";
             }
             leaf dhcpv6-wait-auth-req-release-terminated {
               type int32;
               description "Number of clients in wait-auth-req-release-terminated state";
             }
             leaf dhcpv6-wait-auth-act-prof {
               type int32;
               description "Number of clients in wait-auth-act-prof state";
             }
             leaf dhcpv6-wait-auth-act-prof-delete {
               type int32;
               description "Number of clients in wait-auth-act-prof-delete state";
             }
             leaf dhcpv6-wait-service-deactivation {
               type int32;
               description "Number of clients in wait-service-deactivation state";
             }
             leaf dhcpv6-wait-dual-stack-peer-logout {
               type int32;
               description "Number of clients in wait-dual-stack-peer-logout state";
             }
             leaf dhcpv6-wait-prof-inst {
               type int32;
               description "Number of clients in wait-prof-inst state";
             }
             leaf dhcpv6-wait-prof-inst-delete {
               type int32;
               description "Number of clients in wait-prof-inst-delete state";
             }
             leaf dhcpv6-wait-prof-delete {
               type int32;
               description "Number of clients in wait-prof-delete state";
             }
             leaf dhcpv6-wait-interface {
               type int32;
               description "Number of clients in wait-interface state";
             }
             leaf dhcpv6-wait-sdb-init-mirror-req {
               type int32;
               description "Number of clients in wait-sdb-init-mirror-req state";
             }
             leaf dhcpv6-wait-sdb-init-mirror-req-delete {
               type int32;
               description "Number of clients in wait-sdb-init-mirror-req-delete state";
             }
             leaf dhcpv6-wait-sdb-active-mirror-req {
               type int32;
               description "Number of clients in wait-sdb-active-mirror-req state";
             }
             leaf dhcpv6-wait-sdb-active-mirror-req-delete {
               type int32;
               description "Number of clients in wait-sdb-active-mirror-req-delete state";
             }
             leaf dhcpv6-wait-sdb-terminated-mirror-req {
               type int32;
               description "Number of clients in wait-sdb-terminated-mirror-req state";
             }
             leaf dhcpv6-wait-sdb-dual-stack-terminating {
               type int32;
               description "Number of clients in wait-sdb-dual-stack-terminating state";
             }
             leaf dhcpv6-wait-sdb-dual-stack-clear {
               type int32;
               description "Number of clients in wait-sdb-dual-stack-clear state";
             }
             leaf dhcpv6-bound-on-intf-delete {
               type int32;
               description "Number of clients in bound-on-intf-delete state";
             }
             leaf dhcpv6-release-wait-server-reply {
               type int32;
               description "Number of clients in release-wait-server-reply state";
             }
           }
           container dhcpv6-binding {
             description "Information about the address assigned to an IPv6 Dynamic Host Configuration Protocol client";
             leaf session-id {
               type string;
               description "Session ID of the client";
             }
             leaf allocated-address {
               type ipaddr;
               description "IPv4 or IPv6 address assigned to the DHCP client";
             }
             leaf allocated-prefix {
               type ipaddr;
               description "IPv6 prefix address assigned to the DHCP client";
             }
             leaf client-duid {
               type string;
               description "Client DUID";
             }
             leaf client-id-len {
               type int32;
               description "Number of bytes in client id";
             }
             leaf client-id {
               type string;
               description "Four bytes of the client id";
             }
             leaf alt-client-id-len {
               type int32;
               description "Number of bytes in alternate client id";
             }
             leaf alt-client-id {
               type string;
               description "Four byte of the alternate client id";
             }
             leaf lease-state {
               type string;
               description "Status of the address assignment";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf preferred-lease-end-time {
               type string;
               description "Prefferred time when the address assignment should expire, in the format YYYY-MM-DD hh:mm:ss TZ (year, month, date, hour in 24-hour format, minute, second, time zone). The value 'never' indicates that the lease does not expire";
             }
             leaf preferred-lease-expires {
               type int32;
               description "Number of seconds preferred lease will expire in";
             }
             leaf lease-start-time {
               type string;
               description "Time when the client obtained the address assignment, in the format YYYY-MM-DD hh:mm:ss TZ (year, month, date, hour in 24-hour format, minute, second, time zone)";
             }
             leaf lease-time-violated {
               type string;
               description "Status of lease time validation violation";
             }
             leaf last-packet-received-time {
               type string;
               description "Time at which the most recent packet from the client was received, in the format YYYY-MM-DD hh:mm:ss TZ (year, month, date, hour in 24-hour format, minute, second, time zone)";
             }
             leaf interface-name {
               type string;
               description "Name of the interface via which the DHCP server transmitted the address assignment";
             }
             leaf vlan-id {
               type int32;
               description "Vlan id of the client interface";
             }
             leaf svlan-id {
               type int32;
               description "Svlan id of the client interface";
             }
             leaf demux-interface-name {
               type string;
               description "Demux interface name";
             }
             leaf server-ip-address {
               type ipaddr;
               description "IP address of the DHCP server";
             }
             leaf next-hop-server-facing-relay {
               type ipaddr;
               description "IP address of the DHCP Relay one hop closer to the Server";
             }
             leaf server-interface-name {
               type string;
               description "Interface that server was from";
             }
             leaf v6-relay-address {
               type ipaddr;
               description "IPv6 address of the DHCPv6 relay that relayed the address assigned by the DHCPv6 server";
             }
             leaf previous-v6-relay-address {
               type ipaddr;
               description "Previous IPv6 address of the DHCPv6 relay that relayed the address assigned by the DHCPv6 server";
             }
             leaf pool-name {
               type string;
               description "Client pool name";
             }
             leaf profile-name {
               type string;
               description "Client profile name";
             }
             leaf liveness-detection-state {
               type string;
               description "Status of the liveness detection session with the client";
             }
             leaf dual-stack-group {
               type string;
               description "Dual stack group referenece by this client";
             }
             leaf dual-stack-peer-address {
               type ipaddr;
               description "Peer IP or IPV6 address for this dual stack client";
             }
             leaf generated-circuit-id {
               type string;
               description "Generated circuit id";
             }
             leaf generated-remote-id-enterprise-number {
               type int32;
               description "Generated remote id enterprise number";
             }
             leaf generated-remote-id {
               type string;
               description "Generated remote id";
             }
             leaf dhcpv6-server-id {
               type string;
               description "DHCPv6 server id";
             }
             leaf dhcp-lease-binding-type {
               type string;
               description "Type of the address assignment";
             }
             leaf client-option-type {
               type string;
               description "Type option 60 or option 82";
             }
             leaf client-option-len {
               type int32;
               description "Number of bytes in client option 60 / option 82 data";
             }
             leaf client-option-data {
               type string;
               description "Hex dump of client option 60 / option 82 data";
             }
             leaf option-18-length-from-client {
               type int32;
               description "Option 18 length from client";
             }
             leaf option-18-data-from-client {
               type string;
               description "Option 18 data from client";
             }
             leaf hardware-type {
               type string;
               description "Client hardware type";
             }
             leaf logical-system-routing-instance {
               type string;
               description "Client router context logical system and routing instance";
             }
             leaf bridge-domain {
               type string;
               description "Client router context bridge domain";
             }
             leaf authentication-num-servers {
               type int32;
               description "Number of servers in authentication group";
             }
             leaf client-stale-count {
               type int32;
               description "Number of clients in stale list";
             }
             leaf auth-client-limit {
               type int32;
               description "Client limit from authentication daemon";
             }
             leaf auth-relay-server-group {
               type string;
               description "Value of pointer to authentication daemon server group";
             }
             leaf aci-iflset-name {
               type string;
               description "ACI-VLAN iflset name";
             }
             leaf aci-iflset-index {
               type int32;
               description "ACI-VLAN iflset index";
             }
             leaf aci-iflset-session-id {
               type string;
               description "ACI-VLAN iflset Session ID";
             }
           }
         }
       }
     }
   }
   rpc get-dhcpv6-relay-binding-interface {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
           enum "summary" {
             description "Display summary information";
           }
         }
       }
     }
     output {
       container dhcpv6-relay-binding-information {
         container dhcpv6-brief {
           description "Information about the address assigned to each of one or more DHCPv6 clients";
           container dhcpv6-binding-summary {
             leaf dhcpv6-binding-count {
               type int32;
               description "Number of bindings in this routing instance";
             }
             leaf dhcpv6-init-count {
               type int32;
               description "Number of clients in init state";
             }
             leaf dhcpv6-bound-count {
               type int32;
               description "Number of clients in bound state ";
             }
             leaf dhcpv6-selecting-count {
               type int32;
               description "Number of clients in selecting state ";
             }
             leaf dhcpv6-requesting-count {
               type int32;
               description "Number of clients in requesting state ";
             }
             leaf dhcpv6-renewing-count {
               type int32;
               description "Number of clients in renewing state ";
             }
             leaf dhcpv6-rebinding-count {
               type int32;
               description "Number of clients in rebinding state ";
             }
             leaf dhcpv6-releasing-count {
               type int32;
               description "Number of clients in releasing state ";
             }
             leaf dhcpv6-restore-count {
               type int32;
               description "Number of clients waiting to be restored";
             }
           }
           container dhcpv6-binding-internal-states {
             leaf dhcpv6-init {
               type int32;
               description "Number of clients init state";
             }
             leaf dhcpv6-selecting {
               type int32;
               description "Number of clients in selecting state";
             }
             leaf dhcpv6-requesting {
               type int32;
               description "Number of clients in requesting state";
             }
             leaf dhcpv6-bound {
               type int32;
               description "Number of clients in bound state";
             }
             leaf dhcpv6-renewing {
               type int32;
               description "Number of clients in renewing state";
             }
             leaf dhcpv6-rebinding {
               type int32;
               description "Number of clients in rebinding state";
             }
             leaf dhcpv6-wait-cm-add {
               type int32;
               description "Number of clients in wait-cm-add state";
             }
             leaf dhcpv6-wait-cm-add-delete {
               type int32;
               description "Number of clients in wait-cm-add-delete state";
             }
             leaf dhcpv6-wait-cm-delete {
               type int32;
               description "Number of clients in wait-cm-delete state";
             }
             leaf dhcpv6-wait-subscr-add {
               type int32;
               description "Number of clients in wait-subscr-add state";
             }
             leaf dhcpv6-wait-subscr-add-delete {
               type int32;
               description "Number of clients in wait-subscr-add-delete state";
             }
             leaf dhcpv6-wait-subscr-delete {
               type int32;
               description "Number of clients in wait-subscr-delete state";
             }
             leaf dhcpv6-wait-cm-update {
               type int32;
               description "Number of clients in wait-cm-update state";
             }
             leaf dhcpv6-wait-cm-update-delete {
               type int32;
               description "Number of clients in wait-cm-update-delete state";
             }
             leaf dhcpv6-wait-auth-req {
               type int32;
               description "Number of clients in wait-auth-req state";
             }
             leaf dhcpv6-wait-auth-req-delete {
               type int32;
               description "Number of clients in wait-auth-req-delete state";
             }
             leaf dhcpv6-wait-auth-req-release {
               type int32;
               description "Number of clients in wait-auth-req-release state";
             }
             leaf dhcpv6-wait-auth-req-release-terminated {
               type int32;
               description "Number of clients in wait-auth-req-release-terminated state";
             }
             leaf dhcpv6-wait-auth-act-prof {
               type int32;
               description "Number of clients in wait-auth-act-prof state";
             }
             leaf dhcpv6-wait-auth-act-prof-delete {
               type int32;
               description "Number of clients in wait-auth-act-prof-delete state";
             }
             leaf dhcpv6-wait-service-deactivation {
               type int32;
               description "Number of clients in wait-service-deactivation state";
             }
             leaf dhcpv6-wait-dual-stack-peer-logout {
               type int32;
               description "Number of clients in wait-dual-stack-peer-logout state";
             }
             leaf dhcpv6-wait-prof-inst {
               type int32;
               description "Number of clients in wait-prof-inst state";
             }
             leaf dhcpv6-wait-prof-inst-delete {
               type int32;
               description "Number of clients in wait-prof-inst-delete state";
             }
             leaf dhcpv6-wait-prof-delete {
               type int32;
               description "Number of clients in wait-prof-delete state";
             }
             leaf dhcpv6-wait-interface {
               type int32;
               description "Number of clients in wait-interface state";
             }
             leaf dhcpv6-wait-sdb-init-mirror-req {
               type int32;
               description "Number of clients in wait-sdb-init-mirror-req state";
             }
             leaf dhcpv6-wait-sdb-init-mirror-req-delete {
               type int32;
               description "Number of clients in wait-sdb-init-mirror-req-delete state";
             }
             leaf dhcpv6-wait-sdb-active-mirror-req {
               type int32;
               description "Number of clients in wait-sdb-active-mirror-req state";
             }
             leaf dhcpv6-wait-sdb-active-mirror-req-delete {
               type int32;
               description "Number of clients in wait-sdb-active-mirror-req-delete state";
             }
             leaf dhcpv6-wait-sdb-terminated-mirror-req {
               type int32;
               description "Number of clients in wait-sdb-terminated-mirror-req state";
             }
             leaf dhcpv6-wait-sdb-dual-stack-terminating {
               type int32;
               description "Number of clients in wait-sdb-dual-stack-terminating state";
             }
             leaf dhcpv6-wait-sdb-dual-stack-clear {
               type int32;
               description "Number of clients in wait-sdb-dual-stack-clear state";
             }
             leaf dhcpv6-bound-on-intf-delete {
               type int32;
               description "Number of clients in bound-on-intf-delete state";
             }
             leaf dhcpv6-release-wait-server-reply {
               type int32;
               description "Number of clients in release-wait-server-reply state";
             }
           }
           container dhcpv6-binding {
             description "Information about the address assigned to an IPv6 Dynamic Host Configuration Protocol client";
             leaf allocated-address {
               type ipaddr;
               description "IPv4 or IPv6 address assigned to the DHCP client";
             }
             leaf session-id {
               type string;
               description "Session ID of the client";
             }
             leaf lease-expires {
               type int32;
               description "Number of seconds lease will expire in";
             }
             leaf lease-state {
               type string;
               description "Status of the address assignment";
             }
             leaf interface-name {
               type string;
               description "Name of the interface via which the DHCP server transmitted the address assignment";
             }
             leaf client-duid {
               type string;
               description "Client DUID";
             }
           }
         }
         container dhcpv6-detail {
           description "Information about the address assigned to each of one or more DHCPv6 clients";
           container dhcpv6-binding-summary {
             leaf dhcpv6-binding-count {
               type int32;
               description "Number of bindings in this routing instance";
             }
             leaf dhcpv6-init-count {
               type int32;
               description "Number of clients in init state";
             }
             leaf dhcpv6-bound-count {
               type int32;
               description "Number of clients in bound state ";
             }
             leaf dhcpv6-selecting-count {
               type int32;
               description "Number of clients in selecting state ";
             }
             leaf dhcpv6-requesting-count {
               type int32;
               description "Number of clients in requesting state ";
             }
             leaf dhcpv6-renewing-count {
               type int32;
               description "Number of clients in renewing state ";
             }
             leaf dhcpv6-rebinding-count {
               type int32;
               description "Number of clients in rebinding state ";
             }
             leaf dhcpv6-releasing-count {
               type int32;
               description "Number of clients in releasing state ";
             }
             leaf dhcpv6-restore-count {
               type int32;
               description "Number of clients waiting to be restored";
             }
           }
           container dhcpv6-binding-internal-states {
             leaf dhcpv6-init {
               type int32;
               description "Number of clients init state";
             }
             leaf dhcpv6-selecting {
               type int32;
               description "Number of clients in selecting state";
             }
             leaf dhcpv6-requesting {
               type int32;
               description "Number of clients in requesting state";
             }
             leaf dhcpv6-bound {
               type int32;
               description "Number of clients in bound state";
             }
             leaf dhcpv6-renewing {
               type int32;
               description "Number of clients in renewing state";
             }
             leaf dhcpv6-rebinding {
               type int32;
               description "Number of clients in rebinding state";
             }
             leaf dhcpv6-wait-cm-add {
               type int32;
               description "Number of clients in wait-cm-add state";
             }
             leaf dhcpv6-wait-cm-add-delete {
               type int32;
               description "Number of clients in wait-cm-add-delete state";
             }
             leaf dhcpv6-wait-cm-delete {
               type int32;
               description "Number of clients in wait-cm-delete state";
             }
             leaf dhcpv6-wait-subscr-add {
               type int32;
               description "Number of clients in wait-subscr-add state";
             }
             leaf dhcpv6-wait-subscr-add-delete {
               type int32;
               description "Number of clients in wait-subscr-add-delete state";
             }
             leaf dhcpv6-wait-subscr-delete {
               type int32;
               description "Number of clients in wait-subscr-delete state";
             }
             leaf dhcpv6-wait-cm-update {
               type int32;
               description "Number of clients in wait-cm-update state";
             }
             leaf dhcpv6-wait-cm-update-delete {
               type int32;
               description "Number of clients in wait-cm-update-delete state";
             }
             leaf dhcpv6-wait-auth-req {
               type int32;
               description "Number of clients in wait-auth-req state";
             }
             leaf dhcpv6-wait-auth-req-delete {
               type int32;
               description "Number of clients in wait-auth-req-delete state";
             }
             leaf dhcpv6-wait-auth-req-release {
               type int32;
               description "Number of clients in wait-auth-req-release state";
             }
             leaf dhcpv6-wait-auth-req-release-terminated {
               type int32;
               description "Number of clients in wait-auth-req-release-terminated state";
             }
             leaf dhcpv6-wait-auth-act-prof {
               type int32;
               description "Number of clients in wait-auth-act-prof state";
             }
             leaf dhcpv6-wait-auth-act-prof-delete {
               type int32;
               description "Number of clients in wait-auth-act-prof-delete state";
             }
             leaf dhcpv6-wait-service-deactivation {
               type int32;
               description "Number of clients in wait-service-deactivation state";
             }
             leaf dhcpv6-wait-dual-stack-peer-logout {
               type int32;
               description "Number of clients in wait-dual-stack-peer-logout state";
             }
             leaf dhcpv6-wait-prof-inst {
               type int32;
               description "Number of clients in wait-prof-inst state";
             }
             leaf dhcpv6-wait-prof-inst-delete {
               type int32;
               description "Number of clients in wait-prof-inst-delete state";
             }
             leaf dhcpv6-wait-prof-delete {
               type int32;
               description "Number of clients in wait-prof-delete state";
             }
             leaf dhcpv6-wait-interface {
               type int32;
               description "Number of clients in wait-interface state";
             }
             leaf dhcpv6-wait-sdb-init-mirror-req {
               type int32;
               description "Number of clients in wait-sdb-init-mirror-req state";
             }
             leaf dhcpv6-wait-sdb-init-mirror-req-delete {
               type int32;
               description "Number of clients in wait-sdb-init-mirror-req-delete state";
             }
             leaf dhcpv6-wait-sdb-active-mirror-req {
               type int32;
               description "Number of clients in wait-sdb-active-mirror-req state";
             }
             leaf dhcpv6-wait-sdb-active-mirror-req-delete {
               type int32;
               description "Number of clients in wait-sdb-active-mirror-req-delete state";
             }
             leaf dhcpv6-wait-sdb-terminated-mirror-req {
               type int32;
               description "Number of clients in wait-sdb-terminated-mirror-req state";
             }
             leaf dhcpv6-wait-sdb-dual-stack-terminating {
               type int32;
               description "Number of clients in wait-sdb-dual-stack-terminating state";
             }
             leaf dhcpv6-wait-sdb-dual-stack-clear {
               type int32;
               description "Number of clients in wait-sdb-dual-stack-clear state";
             }
             leaf dhcpv6-bound-on-intf-delete {
               type int32;
               description "Number of clients in bound-on-intf-delete state";
             }
             leaf dhcpv6-release-wait-server-reply {
               type int32;
               description "Number of clients in release-wait-server-reply state";
             }
           }
           container dhcpv6-binding {
             description "Information about the address assigned to an IPv6 Dynamic Host Configuration Protocol client";
             leaf session-id {
               type string;
               description "Session ID of the client";
             }
             leaf allocated-address {
               type ipaddr;
               description "IPv4 or IPv6 address assigned to the DHCP client";
             }
             leaf allocated-prefix {
               type ipaddr;
               description "IPv6 prefix address assigned to the DHCP client";
             }
             leaf client-duid {
               type string;
               description "Client DUID";
             }
             leaf client-id-len {
               type int32;
               description "Number of bytes in client id";
             }
             leaf client-id {
               type string;
               description "Four bytes of the client id";
             }
             leaf alt-client-id-len {
               type int32;
               description "Number of bytes in alternate client id";
             }
             leaf alt-client-id {
               type string;
               description "Four byte of the alternate client id";
             }
             leaf lease-state {
               type string;
               description "Status of the address assignment";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf preferred-lease-end-time {
               type string;
               description "Prefferred time when the address assignment should expire, in the format YYYY-MM-DD hh:mm:ss TZ (year, month, date, hour in 24-hour format, minute, second, time zone). The value 'never' indicates that the lease does not expire";
             }
             leaf preferred-lease-expires {
               type int32;
               description "Number of seconds preferred lease will expire in";
             }
             leaf lease-start-time {
               type string;
               description "Time when the client obtained the address assignment, in the format YYYY-MM-DD hh:mm:ss TZ (year, month, date, hour in 24-hour format, minute, second, time zone)";
             }
             leaf lease-time-violated {
               type string;
               description "Status of lease time validation violation";
             }
             leaf last-packet-received-time {
               type string;
               description "Time at which the most recent packet from the client was received, in the format YYYY-MM-DD hh:mm:ss TZ (year, month, date, hour in 24-hour format, minute, second, time zone)";
             }
             leaf interface-name {
               type string;
               description "Name of the interface via which the DHCP server transmitted the address assignment";
             }
             leaf vlan-id {
               type int32;
               description "Vlan id of the client interface";
             }
             leaf svlan-id {
               type int32;
               description "Svlan id of the client interface";
             }
             leaf demux-interface-name {
               type string;
               description "Demux interface name";
             }
             leaf server-ip-address {
               type ipaddr;
               description "IP address of the DHCP server";
             }
             leaf next-hop-server-facing-relay {
               type ipaddr;
               description "IP address of the DHCP Relay one hop closer to the Server";
             }
             leaf server-interface-name {
               type string;
               description "Interface that server was from";
             }
             leaf v6-relay-address {
               type ipaddr;
               description "IPv6 address of the DHCPv6 relay that relayed the address assigned by the DHCPv6 server";
             }
             leaf previous-v6-relay-address {
               type ipaddr;
               description "Previous IPv6 address of the DHCPv6 relay that relayed the address assigned by the DHCPv6 server";
             }
             leaf pool-name {
               type string;
               description "Client pool name";
             }
             leaf profile-name {
               type string;
               description "Client profile name";
             }
             leaf liveness-detection-state {
               type string;
               description "Status of the liveness detection session with the client";
             }
             leaf dual-stack-group {
               type string;
               description "Dual stack group referenece by this client";
             }
             leaf dual-stack-peer-address {
               type ipaddr;
               description "Peer IP or IPV6 address for this dual stack client";
             }
             leaf generated-circuit-id {
               type string;
               description "Generated circuit id";
             }
             leaf generated-remote-id-enterprise-number {
               type int32;
               description "Generated remote id enterprise number";
             }
             leaf generated-remote-id {
               type string;
               description "Generated remote id";
             }
             leaf dhcpv6-server-id {
               type string;
               description "DHCPv6 server id";
             }
             leaf dhcp-lease-binding-type {
               type string;
               description "Type of the address assignment";
             }
             leaf client-option-type {
               type string;
               description "Type option 60 or option 82";
             }
             leaf client-option-len {
               type int32;
               description "Number of bytes in client option 60 / option 82 data";
             }
             leaf client-option-data {
               type string;
               description "Hex dump of client option 60 / option 82 data";
             }
             leaf option-18-length-from-client {
               type int32;
               description "Option 18 length from client";
             }
             leaf option-18-data-from-client {
               type string;
               description "Option 18 data from client";
             }
             leaf hardware-type {
               type string;
               description "Client hardware type";
             }
             leaf logical-system-routing-instance {
               type string;
               description "Client router context logical system and routing instance";
             }
             leaf bridge-domain {
               type string;
               description "Client router context bridge domain";
             }
             leaf authentication-num-servers {
               type int32;
               description "Number of servers in authentication group";
             }
             leaf client-stale-count {
               type int32;
               description "Number of clients in stale list";
             }
             leaf auth-client-limit {
               type int32;
               description "Client limit from authentication daemon";
             }
             leaf auth-relay-server-group {
               type string;
               description "Value of pointer to authentication daemon server group";
             }
             leaf aci-iflset-name {
               type string;
               description "ACI-VLAN iflset name";
             }
             leaf aci-iflset-index {
               type int32;
               description "ACI-VLAN iflset index";
             }
             leaf aci-iflset-session-id {
               type string;
               description "ACI-VLAN iflset Session ID";
             }
           }
         }
       }
     }
   }
   rpc get-dhcpv6-relay-statistics-information {
     description "Show DHCPv6 relay statistics";
     input {
       leaf level {
         default "summary";
         type enumeration {
           enum "summary" {
             description "Display summary information";
           }
           enum "verbose" {
             description "Display verbose information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcpv6-relay-statistics-information {
         leaf v6-dropped-packet-total {
           type uint32;
           description "Total number of packets discarded by the DHCPv6 relay because of errors";
         }
         leaf v6-dropped-packet-no-safd {
           type uint32;
           description "Number of packets discarded for subunit stack address family device match failure";
         }
         leaf v6-dropped-packet-no-routing-instance {
           type uint32;
           description "Number of packets discarded for routing instance match failure";
         }
         leaf v6-dropped-packet-bad-send {
           type uint32;
           description "Number of packets discarded due to send error";
         }
         leaf v6-dropped-packet-short-packet {
           type uint32;
           description "Number of packets discarded because they were too short";
         }
         leaf v6-dropped-packet-bad-msgtype {
           type uint32;
           description "Number of packets discarded due to bad opcode in packet";
         }
         leaf v6-dropped-packet-bad-options {
           type uint32;
           description "Number of packets discarded because they specified invalid options";
         }
         leaf v6-dropped-packet-bad-srcaddress {
           type uint32;
           description "Number of packets discarded because they specified invalid addr family";
         }
         leaf v6-dropped-packet-relay-hop-count {
           type uint32;
           description "Number of packets discarded due to max relays supported";
         }
         leaf v6-dropped-packet-bad-udp-checksum {
           type uint32;
           description "Number of packets discarded due to a bad UDP checksum";
         }
         leaf v6-dropped-packet-no-client-id {
           type uint32;
           description "Number of packets discarded due to missing client id";
         }
         leaf v6-dropped-packet-strict-reconfigure {
           type uint32;
           description "Number of packets discarded due to strict reconfigure";
         }
         leaf v6-dropped-packet-relay-option {
           type uint32;
           description "Number of packets discarded by the DHCPv6 relay due to relay-option processing";
         }
         leaf v6-dropped-packet-option-18 {
           type uint32;
           description "Number of packets discarded for option 18 processing failure";
         }
         leaf v6-dropped-packet-option-37 {
           type uint32;
           description "Number of packets discarded for option 37 processing failure";
         }
         leaf v6-dropped-packet-authentication {
           type uint32;
           description "Number of packets discarded because authentication failed";
         }
         leaf v6-dropped-packet-dynamic-profile {
           type uint32;
           description "Number of packets discarded because a dynamic profile failed";
         }
         leaf v6-dropped-packet-license {
           type uint32;
           description "Number of packets discarded because of a license failure";
         }
         leaf v6-dropped-packet-inactive-vlan {
           type uint32;
           description "Number of packets discarded because of inactive VLAN";
         }
         leaf v6-dropped-packet-event-rate-analyzer {
           type uint32;
           description "Number of packets discarded because of ERA throttling";
         }
         leaf v6-dropped-packet-client-lookup {
           type uint32;
           description "Number of packets discarded because no client binding was found";
         }
         leaf v6-lease-time-violations-drop {
           type uint32;
           description "Packets dropped because of lease time violation";
         }
         leaf v6-dropped-packet-leasequery-repl-no-client-data {
           type uint32;
           description "Packets discarded as no client-data in leasequery replies";
         }
         leaf v6-dropped-packet-leasequery-repl-no-interfaceid {
           type uint32;
           description "Packets discarded as no interface-id in leasequery replies";
         }
         leaf v6-dropped-packet-leasequery-repl-with-client-link {
           type uint32;
           description "Packets discarded as client-link in leasequery replies";
         }
         leaf v6-dropped-packet-leasequery-repl-no-relay-data {
           type uint32;
           description "Packets discarded as no relay-data in leasequery replies";
         }
         leaf v6-dropped-packet-leasequery-repl-with-hop-cnt {
           type uint32;
           description "Packets discarded, leasequery reply with hop count";
         }
         leaf v6-dropped-packet-leasequery-repl-with-error-code {
           type uint32;
           description "Packets discarded, leasequery reply with error code";
         }
         leaf v6-dropped-packet-leasequery-repl-with-query-term {
           type uint32;
           description "Packets discarded, leasequery reply with query term";
         }
         leaf v6-dropped-packet-older-leasequery-repl {
           type uint32;
           description "Packets discarded as older leasequery replies";
         }
         leaf v6-dropped-packet-abort-leasequery-repl {
           type uint32;
           description "Packets discarded due to abort of leasequery reply processing";
         }
         leaf v6-dropped-packet-during-leasequery-repl {
           type uint32;
           description "Packets discarded as received during leasequery reply processing";
         }
         leaf v6-dropped-packet-relay-source-no-lpbk-interface {
           type uint32;
           description "Number of packets discarded as received with relay source config without loopback config";
         }
         leaf v6-dropped-packet-dhcpv6-service-total {
           type uint32;
           description "Number of packets discarded at dhcpv6-service level";
         }
         leaf v6-forwarded-packets-total {
           type uint32;
           description "Total number of packets forwarded";
         }
         leaf v6-forwarded-request-packets {
           type uint32;
           description "Number of request packets forwarded";
         }
         leaf v6-forwarded-reply-packets {
           type uint32;
           description "Number of reply packets forwarded";
         }
         leaf dhcpv6-external-server-response-state {
           type string;
           description "Set if external server is responding otherwise Clear";
         }
         container dhcpv6-message-table {
           description "Information about one or more DHCPv6 messages sent or received by the DHCPv6 Relay";
           leaf dhcpv6-message-direction {
             type string;
             description "Indicator of whether the DHCPv6 Relay sent or received the messages";
           }
           container dhcpv6-message {
             description "Information about a DHCPv6 message";
             leaf dhcpv6-message-name {
               type string;
               description "Name of the message";
             }
             leaf dhcpv6-message-count {
               type uint32;
               description "Number of times the DCHPv6 Relay received or sent the message";
             }
           }
         }
       }
     }
   }
   rpc get-dhcpv6-relay-leasequery-statistics {
     description "Show DHCP relay leasequery statistics";
     input {
       leaf level {
         default "summary";
         type enumeration {
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-relay-leasequery-statistics {
         leaf in-flight-leasequeries {
           type uint32;
           description "Number of in-flight leasequeries";
         }
         leaf total-leasequeries {
           type uint32;
           description "Total Number of leasequeries";
         }
         leaf total-leasequery-attempts {
           type uint32;
           description "Total Number of leasequery attempts";
         }
         leaf total-leasequery-repl-packet-retries {
           type uint32;
           description "Total Number of packet retries";
         }
         leaf total-leasequery-repl-max-retried {
           type uint32;
           description "Total Number of leasequery reply maximum retried";
         }
         container summary {
           description "Leasequery Statistics for DHCP and DHCPv6 Relay";
           container dhcp-leasequery-info-statistics {
           }
         }
         container verbose {
           description "Leasequery Statistics for DHCP and DHCPv6 Relay";
           leaf in-flight-leasequeries {
             type uint32;
             description "Number of in-flight leasequeries";
           }
           leaf total-leasequeries {
             type uint32;
             description "Total Number of leasequeries";
           }
           leaf total-leasequery-attempts {
             type uint32;
             description "Total Number of leasequery attempts";
           }
           leaf total-leasequery-repl-packet-retries {
             type uint32;
             description "Total Number of packet retries";
           }
           leaf total-leasequery-repl-max-retried {
             type uint32;
             description "Total Number of leasequery reply maximum retried";
           }
           container dhcp-leasequery-info-statistics {
             leaf leasequery-xid {
               type uint32;
               description "Leasequery unique XID";
             }
             leaf leasequery-state {
               type string;
               description "Leasequery state";
             }
             leaf leasequery-confirmed-replies {
               type uint32;
               description "Number of confirmed Leasequery replies";
             }
             leaf leasequery-unconfirmed-replies {
               type uint32;
               description "Numnrt of unconfirmed Leasequery replies";
             }
             leaf leasequery-attempts {
               type uint32;
               description "Number of Leasequery attempts";
             }
             container dhcp-leasequery-server-info-statistics {
             }
           }
         }
       }
     }
   }
   rpc get-dhcpv6-relay-bulk-leasequery-conn-statistics {
     description "Show DHCP relay bulk leasequery statistics";
     input {
       leaf level {
         default "summary";
         type enumeration {
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-relay-bulk-leasequery-conn-statistics {
         leaf total-connections-requested {
           type uint32;
           description "Number of TCP connections requested";
         }
         leaf total-connections-attempted {
           type uint32;
           description "Number of TCP connections attempted";
         }
         leaf total-connections-connected {
           type uint32;
           description "Number of connected TCP connections";
         }
         leaf total-connections-terminated-by-server {
           type uint32;
           description "Number of connections terminated by server";
         }
         leaf total-connections-max-attempted {
           type uint32;
           description "Number of requested TCP connections with max attempts reached";
         }
         leaf total-connections-closed-due-to-error {
           type uint32;
           description "Number of TCP connections closed due to error";
         }
         leaf in-flight-connections-connected {
           type uint32;
           description "Number of in-flight TCP connections in connected state";
         }
         leaf total-bulk-leasequery-repl-packet-retries {
           type uint32;
           description "Number of bulk leasequery reply packet retries";
         }
         leaf total-bulk-leasequery-repl-max-retried {
           type uint32;
           description "Number of bulk leasequery reply max retried";
         }
         container summary {
           description "Bulk Leasequery connection statistics for DHCP and DHCPv6 Relay";
           container dhcp-bulk-leasequery-info-statistics {
           }
         }
         container verbose {
           description "Bulk Leasequery connection statistics for DHCP and DHCPv6 Relay";
           leaf total-connections-requested {
             type uint32;
             description "Number of TCP connections requested";
           }
           leaf total-connections-attempted {
             type uint32;
             description "Number of TCP connections attempted";
           }
           leaf total-connections-connected {
             type uint32;
             description "Number of connected TCP connections";
           }
           leaf total-connections-terminated-by-server {
             type uint32;
             description "Number of connections terminated by server";
           }
           leaf total-connections-max-attempted {
             type uint32;
             description "Number of requested TCP connections with max attempts reached";
           }
           leaf total-connections-closed-due-to-error {
             type uint32;
             description "Number of TCP connections closed due to error";
           }
           leaf in-flight-connections-connected {
             type uint32;
             description "Number of in-flight TCP connections in connected state";
           }
           leaf total-bulk-leasequery-repl-packet-retries {
             type uint32;
             description "Number of bulk leasequery reply packet retries";
           }
           leaf total-bulk-leasequery-repl-max-retried {
             type uint32;
             description "Number of bulk leasequery reply max retried";
           }
           container dhcp-bulk-leasequery-info-statistics {
             leaf bulk-leasequery-xid {
               type uint32;
               description "Bulk Leasequery unique XID";
             }
             leaf bulk-leasequery-total-servers {
               type uint32;
               description "Total Bulk Leasequery servers";
             }
             container dhcp-bulk-leasequery-server-info-statistics {
             }
           }
         }
       }
     }
   }
   rpc get-dhcpv6-service-statistics-information {
     description "Show DHCPv6 service statistics";
     input {
       leaf level {
         default "summary";
         type enumeration {
           enum "summary" {
             description "Display summary information";
           }
         }
       }
       leaf interface {
         description "Name of interface";
         type interface-name;
       }
     }
     output {
       container dhcpv6-service-statistics-information {
         leaf v6-dropped-packet-dhcpv6-service-total {
           type uint32;
         }
         leaf v6-dropped-packet-read-error {
           type uint32;
           description "Packets discarded due to read error";
         }
         leaf v6-dropped-packet-bad-ip-header {
           type uint32;
           description "Packets discarded due to bad IP header";
         }
         leaf v6-dropped-packet-short-packet {
           type uint32;
           description "Packets discarded because they were too short";
         }
         leaf v6-dropped-packet-no-interface {
           type uint32;
           description "Packets discarded due to no interface";
         }
         leaf v6-dropped-packet-no-safd {
           type uint32;
           description "Packets discarded for subunit stack address family device match failure";
         }
         leaf v6-dropped-packet-no-routing-instance {
           type uint32;
           description "Packets discarded due to no routing instance";
         }
         leaf v6-dropped-packet-no-mem {
           type uint32;
           description "Packets discarded due to no memory";
         }
         leaf v6-dropped-packet-recovery-in-progress {
           type uint32;
           description "Packets discarded due to switchover recovery in progress";
         }
       }
     }
   }
   rpc get-dhcpv6-server-binding-information {
     description "Show DHCPv6 server client binding information";
     input {
       leaf level {
         default "brief";
         type enumeration {
           enum "brief" {
             description "Display brief information";
           }
           enum "detail" {
             description "Display detailed information";
           }
           enum "summary" {
             description "Display summary information";
           }
         }
       }
       container show-choice {
         choice show-choice_c {
           case address {
             leaf address {
               description "IPv6 Prefix, session-id or CID of DHCPv6 client binding";
               type string;
             }
           }
           case interfaces-wildcard {
             leaf interfaces-wildcard {
               description "Interfaces to show bindings on (can be '*' wildcard)";
               type string {
                 junos:posix-pattern "^( (((ge-)|(xe-)|(et-))( [[:digit:]]+(-([[:digit:]]+))+(-([[:digit:]]+)?)?)?) | (ae))+$";
                 junos:pattern-message "Must be an interface wildcard string";
               }
             }
           }
           case interfaces-vlan {
             leaf interfaces-vlan {
               description "Interface VLAN-ID/SVLAN-ID on which to show bindings";
               type string {
                 junos:posix-pattern "^(( (((ge-)|(xe-)|(et-))( [[:digit:]]+(-([[:digit:]]+))+(-([[:digit:]]+)?)?)?) | (ae))(/:)([[:digit:]]+(-[[:digit:]]+))?)+$";
                 junos:pattern-message "Must be an interface:VLAN string";
               }
             }
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcpv6-server-binding-information {
         container dhcpv6-brief {
           description "Information about the address assigned to each of one or more DHCPv6 clients";
           container dhcpv6-binding-summary {
             leaf dhcpv6-binding-count {
               type int32;
               description "Number of bindings in this routing instance";
             }
             leaf dhcpv6-init-count {
               type int32;
             }
             leaf dhcpv6-bound-count {
               type int32;
             }
             leaf dhcpv6-selecting-count {
               type int32;
             }
             leaf dhcpv6-requesting-count {
               type int32;
             }
             leaf dhcpv6-renewing-count {
               type int32;
             }
             leaf dhcpv6-releasing-count {
               type int32;
             }
             leaf dhcpv6-restore-count {
               type int32;
               description "Number of clients waiting to be restored";
             }
           }
           container dhcpv6-binding {
             description "Information about the address assigned to an IPv6 Dynamic Host Configuration Protocol client";
             leaf allocated-address {
               type ipaddr;
               description "IPv4 or IPv6 address assigned to the DHCP client";
             }
             leaf session-id {
               type string;
               description "Session ID of the client";
             }
             leaf lease-expires {
               type int32;
               description "Number of seconds lease will expire in";
             }
             leaf lease-state {
               type string;
               description "Status of the address assignment";
             }
             leaf interface-name {
               type string;
               description "Name of the interface via which the DHCP server transmitted the address assignment";
             }
             leaf client-duid {
               type string;
               description "Client DUID";
             }
           }
         }
         container dhcpv6-detail {
           description "Information about the address assigned to each of one or more DHCPv6 clients";
           container dhcpv6-binding-summary {
             leaf dhcpv6-binding-count {
               type int32;
               description "Number of bindings in this routing instance";
             }
             leaf dhcpv6-init-count {
               type int32;
             }
             leaf dhcpv6-bound-count {
               type int32;
             }
             leaf dhcpv6-selecting-count {
               type int32;
             }
             leaf dhcpv6-requesting-count {
               type int32;
             }
             leaf dhcpv6-renewing-count {
               type int32;
             }
             leaf dhcpv6-releasing-count {
               type int32;
             }
             leaf dhcpv6-restore-count {
               type int32;
               description "Number of clients waiting to be restored";
             }
           }
           container dhcpv6-binding {
             description "Information about the address assigned to an IPv6 Dynamic Host Configuration Protocol client";
             leaf session-id {
               type string;
               description "Session ID of the client";
             }
             leaf allocated-address {
               type ipaddr;
               description "IPv4 or IPv6 address assigned to the DHCP client";
             }
             leaf allocated-prefix {
               type ipaddr;
               description "IPv6 prefix address assigned to the DHCP client";
             }
             leaf client-duid {
               type string;
               description "Client DUID";
             }
             leaf client-id-len {
               type int32;
               description "Number of bytes in client id";
             }
             leaf client-id {
               type string;
               description "Client id";
             }
             leaf alt-client-id-len {
               type int32;
               description "Number of bytes in alternate client id";
             }
             leaf alt-client-id {
               type string;
               description "Alternate client id";
             }
             leaf lease-state {
               type string;
               description "Status of the address assignment";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf preferred-lease-end-time {
               type string;
               description "Prefferred time when the address assignment should expire, in the format YYYY-MM-DD hh:mm:ss TZ (year, month, date, hour in 24-hour format, minute, second, time zone). The value 'never' indicates that the lease does not expire";
             }
             leaf preferred-lease-expires {
               type int32;
               description "Number of seconds preferred lease will expire in";
             }
             leaf lease-start-time {
               type string;
               description "Time when the client obtained the address assignment, in the format YYYY-MM-DD hh:mm:ss TZ (year, month, date, hour in 24-hour format, minute, second, time zone)";
             }
             leaf lease-time-violated {
               type string;
               description "Status of binding wrt lease time validation";
             }
             leaf last-packet-received-time {
               type string;
               description "Time at which the most recent packet from the client was received, in the format YYYY-MM-DD hh:mm:ss TZ (year, month, date, hour in 24-hour format, minute, second, time zone)";
             }
             leaf interface-name {
               type string;
               description "Name of the interface via which the DHCP server transmitted the address assignment";
             }
             leaf vlan-id {
               type int32;
               description "Vlan id of the client interface";
             }
             leaf svlan-id {
               type int32;
               description "Svlan id of the client interface";
             }
             leaf demux-interface-name {
               type string;
               description "Demux interface name";
             }
             leaf server-ip-address {
               type ipaddr;
               description "IP address of the DHCP server";
             }
             leaf pool-name {
               type string;
               description "Client pool name";
             }
             leaf delegated-pool-name {
               type string;
               description "Client prefix pool name";
             }
             leaf profile-name {
               type string;
               description "Client profile name";
             }
             leaf liveness-detection-state {
               type string;
               description "Status of the liveness detection session with the client";
             }
             leaf dhcpv6-server-id {
               type string;
               description "DHCPv6 server id";
             }
             leaf dhcp-lease-binding-type {
               type string;
               description "Type of the address assignment";
             }
             leaf logical-system-routing-instance {
               type string;
               description "Client router context logical system and routing instance";
             }
             leaf bridge-domain {
               type string;
               description "Client router context bridge domain";
             }
             leaf client-info {
               type string;
               description "General information about the client";
             }
             leaf retail-logical-system-routing-instance {
               type string;
               description "L3 wholesale retail client router context logical system and routing instance";
             }
             leaf retail-bridge-domain {
               type string;
               description "L3 wholesale retail client router context bridge domain";
             }
             leaf wholesale-logical-system-routing-instance {
               type string;
               description "L3 wholesale client router context logical system and routing instance";
             }
             leaf wholesale-bridge-domain {
               type string;
               description "L3 wholesale client router context bridge domain";
             }
             leaf authentication-num-servers {
               type int32;
               description "Number of servers in authentication group";
             }
             leaf client-stale-count {
               type int32;
               description "Number of clients in stale list";
             }
             leaf auth-client-limit {
               type int32;
               description "Client limit from authentication daemon";
             }
             leaf auth-relay-server-group {
               type string;
               description "Value of pointer to authentication daemon server group";
             }
             leaf aci-iflset-name {
               type string;
               description "ACI-VLAN iflset name";
             }
             leaf aci-iflset-index {
               type int32;
               description "ACI-VLAN iflset index";
             }
             leaf aci-iflset-session-id {
               type string;
               description "ACI-VLAN iflset Session ID";
             }
             leaf dhcpv6-relay-id-len {
               type int32;
               description "Number of bytes in client id";
             }
             leaf dhcpv6-relay-id {
               type string;
               description "DHCPv6 relay-id";
             }
           }
         }
       }
     }
   }
   rpc get-dhcpv6-server-binding-ltv-information {
     description "Display lease time violated client bindings";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcpv6-server-binding-information {
         container dhcpv6-brief {
           description "Information about the address assigned to each of one or more DHCPv6 clients";
           container dhcpv6-binding-summary {
             leaf dhcpv6-binding-count {
               type int32;
               description "Number of bindings in this routing instance";
             }
             leaf dhcpv6-init-count {
               type int32;
             }
             leaf dhcpv6-bound-count {
               type int32;
             }
             leaf dhcpv6-selecting-count {
               type int32;
             }
             leaf dhcpv6-requesting-count {
               type int32;
             }
             leaf dhcpv6-renewing-count {
               type int32;
             }
             leaf dhcpv6-releasing-count {
               type int32;
             }
             leaf dhcpv6-restore-count {
               type int32;
               description "Number of clients waiting to be restored";
             }
           }
           container dhcpv6-binding {
             description "Information about the address assigned to an IPv6 Dynamic Host Configuration Protocol client";
             leaf allocated-address {
               type ipaddr;
               description "IPv4 or IPv6 address assigned to the DHCP client";
             }
             leaf session-id {
               type string;
               description "Session ID of the client";
             }
             leaf lease-expires {
               type int32;
               description "Number of seconds lease will expire in";
             }
             leaf lease-state {
               type string;
               description "Status of the address assignment";
             }
             leaf interface-name {
               type string;
               description "Name of the interface via which the DHCP server transmitted the address assignment";
             }
             leaf client-duid {
               type string;
               description "Client DUID";
             }
           }
         }
         container dhcpv6-detail {
           description "Information about the address assigned to each of one or more DHCPv6 clients";
           container dhcpv6-binding-summary {
             leaf dhcpv6-binding-count {
               type int32;
               description "Number of bindings in this routing instance";
             }
             leaf dhcpv6-init-count {
               type int32;
             }
             leaf dhcpv6-bound-count {
               type int32;
             }
             leaf dhcpv6-selecting-count {
               type int32;
             }
             leaf dhcpv6-requesting-count {
               type int32;
             }
             leaf dhcpv6-renewing-count {
               type int32;
             }
             leaf dhcpv6-releasing-count {
               type int32;
             }
             leaf dhcpv6-restore-count {
               type int32;
               description "Number of clients waiting to be restored";
             }
           }
           container dhcpv6-binding {
             description "Information about the address assigned to an IPv6 Dynamic Host Configuration Protocol client";
             leaf session-id {
               type string;
               description "Session ID of the client";
             }
             leaf allocated-address {
               type ipaddr;
               description "IPv4 or IPv6 address assigned to the DHCP client";
             }
             leaf allocated-prefix {
               type ipaddr;
               description "IPv6 prefix address assigned to the DHCP client";
             }
             leaf client-duid {
               type string;
               description "Client DUID";
             }
             leaf client-id-len {
               type int32;
               description "Number of bytes in client id";
             }
             leaf client-id {
               type string;
               description "Client id";
             }
             leaf alt-client-id-len {
               type int32;
               description "Number of bytes in alternate client id";
             }
             leaf alt-client-id {
               type string;
               description "Alternate client id";
             }
             leaf lease-state {
               type string;
               description "Status of the address assignment";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf preferred-lease-end-time {
               type string;
               description "Prefferred time when the address assignment should expire, in the format YYYY-MM-DD hh:mm:ss TZ (year, month, date, hour in 24-hour format, minute, second, time zone). The value 'never' indicates that the lease does not expire";
             }
             leaf preferred-lease-expires {
               type int32;
               description "Number of seconds preferred lease will expire in";
             }
             leaf lease-start-time {
               type string;
               description "Time when the client obtained the address assignment, in the format YYYY-MM-DD hh:mm:ss TZ (year, month, date, hour in 24-hour format, minute, second, time zone)";
             }
             leaf lease-time-violated {
               type string;
               description "Status of binding wrt lease time validation";
             }
             leaf last-packet-received-time {
               type string;
               description "Time at which the most recent packet from the client was received, in the format YYYY-MM-DD hh:mm:ss TZ (year, month, date, hour in 24-hour format, minute, second, time zone)";
             }
             leaf interface-name {
               type string;
               description "Name of the interface via which the DHCP server transmitted the address assignment";
             }
             leaf vlan-id {
               type int32;
               description "Vlan id of the client interface";
             }
             leaf svlan-id {
               type int32;
               description "Svlan id of the client interface";
             }
             leaf demux-interface-name {
               type string;
               description "Demux interface name";
             }
             leaf server-ip-address {
               type ipaddr;
               description "IP address of the DHCP server";
             }
             leaf pool-name {
               type string;
               description "Client pool name";
             }
             leaf delegated-pool-name {
               type string;
               description "Client prefix pool name";
             }
             leaf profile-name {
               type string;
               description "Client profile name";
             }
             leaf liveness-detection-state {
               type string;
               description "Status of the liveness detection session with the client";
             }
             leaf dhcpv6-server-id {
               type string;
               description "DHCPv6 server id";
             }
             leaf dhcp-lease-binding-type {
               type string;
               description "Type of the address assignment";
             }
             leaf logical-system-routing-instance {
               type string;
               description "Client router context logical system and routing instance";
             }
             leaf bridge-domain {
               type string;
               description "Client router context bridge domain";
             }
             leaf client-info {
               type string;
               description "General information about the client";
             }
             leaf retail-logical-system-routing-instance {
               type string;
               description "L3 wholesale retail client router context logical system and routing instance";
             }
             leaf retail-bridge-domain {
               type string;
               description "L3 wholesale retail client router context bridge domain";
             }
             leaf wholesale-logical-system-routing-instance {
               type string;
               description "L3 wholesale client router context logical system and routing instance";
             }
             leaf wholesale-bridge-domain {
               type string;
               description "L3 wholesale client router context bridge domain";
             }
             leaf authentication-num-servers {
               type int32;
               description "Number of servers in authentication group";
             }
             leaf client-stale-count {
               type int32;
               description "Number of clients in stale list";
             }
             leaf auth-client-limit {
               type int32;
               description "Client limit from authentication daemon";
             }
             leaf auth-relay-server-group {
               type string;
               description "Value of pointer to authentication daemon server group";
             }
             leaf aci-iflset-name {
               type string;
               description "ACI-VLAN iflset name";
             }
             leaf aci-iflset-index {
               type int32;
               description "ACI-VLAN iflset index";
             }
             leaf aci-iflset-session-id {
               type string;
               description "ACI-VLAN iflset Session ID";
             }
             leaf dhcpv6-relay-id-len {
               type int32;
               description "Number of bytes in client id";
             }
             leaf dhcpv6-relay-id {
               type string;
               description "DHCPv6 relay-id";
             }
           }
         }
       }
     }
   }
   rpc get-dhcpv6-server-binding-interface {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
           enum "summary" {
             description "Display summary information";
           }
         }
       }
     }
     output {
       container dhcpv6-server-binding-information {
         container dhcpv6-brief {
           description "Information about the address assigned to each of one or more DHCPv6 clients";
           container dhcpv6-binding-summary {
             leaf dhcpv6-binding-count {
               type int32;
               description "Number of bindings in this routing instance";
             }
             leaf dhcpv6-init-count {
               type int32;
             }
             leaf dhcpv6-bound-count {
               type int32;
             }
             leaf dhcpv6-selecting-count {
               type int32;
             }
             leaf dhcpv6-requesting-count {
               type int32;
             }
             leaf dhcpv6-renewing-count {
               type int32;
             }
             leaf dhcpv6-releasing-count {
               type int32;
             }
             leaf dhcpv6-restore-count {
               type int32;
               description "Number of clients waiting to be restored";
             }
           }
           container dhcpv6-binding {
             description "Information about the address assigned to an IPv6 Dynamic Host Configuration Protocol client";
             leaf allocated-address {
               type ipaddr;
               description "IPv4 or IPv6 address assigned to the DHCP client";
             }
             leaf session-id {
               type string;
               description "Session ID of the client";
             }
             leaf lease-expires {
               type int32;
               description "Number of seconds lease will expire in";
             }
             leaf lease-state {
               type string;
               description "Status of the address assignment";
             }
             leaf interface-name {
               type string;
               description "Name of the interface via which the DHCP server transmitted the address assignment";
             }
             leaf client-duid {
               type string;
               description "Client DUID";
             }
           }
         }
         container dhcpv6-detail {
           description "Information about the address assigned to each of one or more DHCPv6 clients";
           container dhcpv6-binding-summary {
             leaf dhcpv6-binding-count {
               type int32;
               description "Number of bindings in this routing instance";
             }
             leaf dhcpv6-init-count {
               type int32;
             }
             leaf dhcpv6-bound-count {
               type int32;
             }
             leaf dhcpv6-selecting-count {
               type int32;
             }
             leaf dhcpv6-requesting-count {
               type int32;
             }
             leaf dhcpv6-renewing-count {
               type int32;
             }
             leaf dhcpv6-releasing-count {
               type int32;
             }
             leaf dhcpv6-restore-count {
               type int32;
               description "Number of clients waiting to be restored";
             }
           }
           container dhcpv6-binding {
             description "Information about the address assigned to an IPv6 Dynamic Host Configuration Protocol client";
             leaf session-id {
               type string;
               description "Session ID of the client";
             }
             leaf allocated-address {
               type ipaddr;
               description "IPv4 or IPv6 address assigned to the DHCP client";
             }
             leaf allocated-prefix {
               type ipaddr;
               description "IPv6 prefix address assigned to the DHCP client";
             }
             leaf client-duid {
               type string;
               description "Client DUID";
             }
             leaf client-id-len {
               type int32;
               description "Number of bytes in client id";
             }
             leaf client-id {
               type string;
               description "Client id";
             }
             leaf alt-client-id-len {
               type int32;
               description "Number of bytes in alternate client id";
             }
             leaf alt-client-id {
               type string;
               description "Alternate client id";
             }
             leaf lease-state {
               type string;
               description "Status of the address assignment";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf preferred-lease-end-time {
               type string;
               description "Prefferred time when the address assignment should expire, in the format YYYY-MM-DD hh:mm:ss TZ (year, month, date, hour in 24-hour format, minute, second, time zone). The value 'never' indicates that the lease does not expire";
             }
             leaf preferred-lease-expires {
               type int32;
               description "Number of seconds preferred lease will expire in";
             }
             leaf lease-start-time {
               type string;
               description "Time when the client obtained the address assignment, in the format YYYY-MM-DD hh:mm:ss TZ (year, month, date, hour in 24-hour format, minute, second, time zone)";
             }
             leaf lease-time-violated {
               type string;
               description "Status of binding wrt lease time validation";
             }
             leaf last-packet-received-time {
               type string;
               description "Time at which the most recent packet from the client was received, in the format YYYY-MM-DD hh:mm:ss TZ (year, month, date, hour in 24-hour format, minute, second, time zone)";
             }
             leaf interface-name {
               type string;
               description "Name of the interface via which the DHCP server transmitted the address assignment";
             }
             leaf vlan-id {
               type int32;
               description "Vlan id of the client interface";
             }
             leaf svlan-id {
               type int32;
               description "Svlan id of the client interface";
             }
             leaf demux-interface-name {
               type string;
               description "Demux interface name";
             }
             leaf server-ip-address {
               type ipaddr;
               description "IP address of the DHCP server";
             }
             leaf pool-name {
               type string;
               description "Client pool name";
             }
             leaf delegated-pool-name {
               type string;
               description "Client prefix pool name";
             }
             leaf profile-name {
               type string;
               description "Client profile name";
             }
             leaf liveness-detection-state {
               type string;
               description "Status of the liveness detection session with the client";
             }
             leaf dhcpv6-server-id {
               type string;
               description "DHCPv6 server id";
             }
             leaf dhcp-lease-binding-type {
               type string;
               description "Type of the address assignment";
             }
             leaf logical-system-routing-instance {
               type string;
               description "Client router context logical system and routing instance";
             }
             leaf bridge-domain {
               type string;
               description "Client router context bridge domain";
             }
             leaf client-info {
               type string;
               description "General information about the client";
             }
             leaf retail-logical-system-routing-instance {
               type string;
               description "L3 wholesale retail client router context logical system and routing instance";
             }
             leaf retail-bridge-domain {
               type string;
               description "L3 wholesale retail client router context bridge domain";
             }
             leaf wholesale-logical-system-routing-instance {
               type string;
               description "L3 wholesale client router context logical system and routing instance";
             }
             leaf wholesale-bridge-domain {
               type string;
               description "L3 wholesale client router context bridge domain";
             }
             leaf authentication-num-servers {
               type int32;
               description "Number of servers in authentication group";
             }
             leaf client-stale-count {
               type int32;
               description "Number of clients in stale list";
             }
             leaf auth-client-limit {
               type int32;
               description "Client limit from authentication daemon";
             }
             leaf auth-relay-server-group {
               type string;
               description "Value of pointer to authentication daemon server group";
             }
             leaf aci-iflset-name {
               type string;
               description "ACI-VLAN iflset name";
             }
             leaf aci-iflset-index {
               type int32;
               description "ACI-VLAN iflset index";
             }
             leaf aci-iflset-session-id {
               type string;
               description "ACI-VLAN iflset Session ID";
             }
             leaf dhcpv6-relay-id-len {
               type int32;
               description "Number of bytes in client id";
             }
             leaf dhcpv6-relay-id {
               type string;
               description "DHCPv6 relay-id";
             }
           }
         }
       }
     }
   }
   rpc get-dhcpv6-server-statistics-information {
     description "Show DHCPv6 server statistics";
     input {
       leaf level {
         default "summary";
         type enumeration {
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcpv6-server-statistics-information {
         leaf v6-dropped-packet-total {
           type uint32;
           description "Total number of packets discarded by the DHCPv6 server because of errors";
         }
         leaf v6-dropped-packet-no-safd {
           type uint32;
           description "Number of packets discarded for subunit stack address family device match failure";
         }
         leaf v6-dropped-packet-no-routing-instance {
           type uint32;
           description "Number of packets discarded for routing instance match failure";
         }
         leaf v6-dropped-packet-bad-send {
           type uint32;
           description "Number of packets discarded due to send error";
         }
         leaf v6-dropped-packet-short-packet {
           type uint32;
           description "Number of packets discarded because they were too short";
         }
         leaf v6-dropped-packet-bad-msgtype {
           type uint32;
           description "Number of packets discarded due to bad opcode in packet";
         }
         leaf v6-dropped-packet-bad-options {
           type uint32;
           description "Number of packets discarded because they specified invalid options";
         }
         leaf v6-dropped-packet-bad-srcaddress {
           type uint32;
           description "Number of packets discarded because they specified invalid addr family";
         }
         leaf v6-dropped-packet-relay-hop-count {
           type uint32;
           description "Number of packets discarded due to max relays supported";
         }
         leaf v6-dropped-packet-bad-udp-checksum {
           type uint32;
           description "Number of packets discarded due to a bad UDP checksum";
         }
         leaf v6-dropped-packet-no-client-id {
           type uint32;
           description "Number of packets discarded due to missing client id";
         }
         leaf v6-dropped-packet-strict-reconfigure {
           type uint32;
           description "Number of packets discarded due to strict reconfigure";
         }
         leaf v6-dropped-packet-option-18 {
           type uint32;
           description "Number of packets discarded for option 18 processing failure";
         }
         leaf v6-dropped-packet-authentication {
           type uint32;
           description "Number of packets discarded because authentication failed";
         }
         leaf v6-dropped-packet-dynamic-profile {
           type uint32;
           description "Number of packets discarded because a dynamic profile failed";
         }
         leaf v6-dropped-packet-license {
           type uint32;
           description "Number of packets discarded because of a license failure";
         }
         leaf v6-dropped-packet-inactive-vlan {
           type uint32;
           description "Number of packets discarded because of inactive VLAN";
         }
         leaf v6-dropped-packet-event-rate-analyzer {
           type uint32;
           description "Number of packets discarded because of ERA throttling";
         }
         leaf v6-dropped-packet-client-lookup {
           type uint32;
           description "Number of packets discarded because no client binding was found";
         }
         leaf v6-lease-time-violations-drop {
           type uint32;
           description "Packets dropped because of lease time violation";
         }
         leaf v6-dropped-packet-dhcpv6-service-total {
           type uint32;
           description "Number of packets discarded at dhcpv6-service level";
         }
         container advertise-delay-info {
           description "Information about offer delay queue status of the DHCP server";
           leaf advertise-delay-string {
             type string;
             description "Indicator of offer delay";
           }
           container advertise-queue {
             description "Information about the Delay Queue status";
             leaf v6-delay-status {
               type string;
               description "Status of packets in delay queue";
             }
             leaf v6-delay-count {
               type uint32;
               description "Number of packets in this status";
             }
           }
         }
         container dhcpv6-message-table {
           description "Information about one or more DHCPv6 messages sent or received by the DHCPv6 server";
           leaf dhcpv6-message-direction {
             type string;
             description "Indicator of whether the DHCPv6 server sent or received the messages";
           }
           container dhcpv6-message {
             description "Information about a DHCPv6 message";
             leaf dhcpv6-message-name {
               type string;
               description "Name of the message";
             }
             leaf dhcpv6-message-count {
               type uint32;
               description "Number of times the DCHPv6 server received or sent the message";
             }
           }
         }
       }
     }
   }
   rpc get-dhcpv6-server-bulk-leasequery-conn-statistics {
     description "Show DHCP server bulk leasequeery conn statistics";
     input {
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-server-bulk-leasequery-conn-statistics {
         leaf total-accepted-tcp-connections {
           type uint32;
           description "Number of accepted TCP connections";
         }
         leaf total-not-accepted-tcp-connections {
           type uint32;
           description "Number of not accepted TCP connections";
         }
         leaf tcp-connections-closed-due-to-error {
           type uint32;
           description "Number of connections closed due to error";
         }
         leaf tcp-connections-closed-due-to-max-empty-replies {
           type uint32;
           description "Number of connections closed due to max-empty-replies";
         }
         leaf in-flight-tcp-connections {
           type uint32;
           description "In-flight TCP connections";
         }
       }
     }
   }
   rpc get-dhcpv6-client-binding-information {
     description "Show DHCPV6 dhcpv6-client binding information";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
   }
   rpc get-dhcpv6-client-binding-information-by-interface {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
         }
       }
     }
   }
   rpc get-dhcpv6-client-statistics-information {
     description "Show DHCPV6 dhcpv6-client statistics";
     input {
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcpv6-client-statistics-information {
         leaf v6-client-dropped-packet-total {
           type uint32;
           description "Total number of packets discarded by the DHCPv6 client because of errors";
         }
         leaf v6-client-dropped-packet-no-safd {
           type uint32;
           description "Number of packets discarded by the DHCPv6 client due to no safd match";
         }
         leaf v6-client-dropped-packet-bad-send {
           type uint32;
           description "Number of packets discarded by the DHCPv6 client due to send error";
         }
         leaf v6-client-dropped-packet-short-packet {
           type uint32;
           description "Number of packets discarded by the DHCPv6 client because they were too short";
         }
         leaf v6-client-dropped-packet-bad-msgtype {
           type uint32;
           description "Number of packets discarded by the DHCPv6 client due to bad opcode in packet";
         }
         leaf v6-client-dropped-packet-bad-options {
           type uint32;
           description "Number of packets discarded by the DHCPv6 client because they specified invalid options";
         }
         leaf v6-client-dropped-packet-bad-srcaddress {
           type uint32;
           description "Number of packets discarded by the DHCPv6 client because they specified invalid addr family";
         }
         leaf v6-client-dropped-packet-relay-hop-count {
           type uint32;
           description "Number of packets discarded by the DHCPv6 client due to max relays supported";
         }
         leaf v6-client-dropped-packet-no-client-id {
           type uint32;
           description "Number of packets discarded by the DHCPv6 client due to missing client id";
         }
         leaf v6-client-dropped-packet-strict-reconfigure {
           type uint32;
           description "Number of packets discarded by the DHCPv6 client due to strict reconfigure";
         }
         container dhcpv6-client-message-table {
           description "Information about one or more DHCPv6 messages sent or received by the DHCPv6 client";
           leaf dhcpv6-client-message-direction {
             type string;
             description "Indicator of whether the DHCPv6 client sent or received the messages";
           }
           container dhcpv6-client-message {
             description "Information about a DHCPv6 client message";
             leaf dhcpv6-client-message-name {
               type string;
               description "Name of the client message";
             }
             leaf dhcpv6-client-message-count {
               type uint32;
               description "Number of times the DCHPv6 client received or sent the message";
             }
           }
         }
       }
     }
   }
 }
