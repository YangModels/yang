/*
 * Copyright (c) 2017 Juniper Networks, Inc.
 * All rights reserved.
 */

 module show-forwarding-options {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-forwarding-options-next-hop-group {
     description "Show next-hop-group information";
     input {
       leaf verbosity {
         default "brief";
         type enumeration {
           enum "terse" {
             description "Display terse output";
           }
           enum "brief" {
             description "Display brief output";
           }
           enum "detail" {
             description "Display detail output";
           }
         }
       }
       leaf group-name {
         description "Name of next-hop-group";
         type string;
       }
     }
     output {
       container smpl-next-hop-group {
         container smpl-nhgroup {
           leaf smpl-nhgroup-name {
             type string;
             description "Name of the next-hop-group";
           }
           leaf smpl-nhgroup-type {
             type string;
             description "Type of the next-hop-group";
           }
           leaf smpl-nhgroup-state {
             type string;
             description "State of the next-hop-group";
           }
           leaf smpl-nhgroup-num-members-configured {
             type int32;
             description "Number of members interfaces that are configured";
           }
           leaf smpl-nhgroup-num-members-up {
             type int32;
             description "Number of members interfaces that are up";
           }
           leaf smpl-nhgroup-subgroups-configured {
             type int32;
             description "Number of subgroups that are configured";
           }
           leaf smpl-nhgroup-subgroups-up {
             type int32;
             description "Number of subgroups that are up";
           }
           leaf smpl-nhgroup-nhid-header {
             type string;
             description "Next-hop index header";
           }
           container terse {
             container smpl-nhgroup-subgroup {
               leaf smpl-nhgroup-nexthop-state {
                 type string;
                 description "State of the next-hop";
               }
             }
           }
           container brief {
             leaf smpl-nhgroup-name {
               type string;
               description "Name of the next-hop-group";
             }
             leaf smpl-nhgroup-type {
               type string;
               description "Type of the next-hop-group";
             }
             leaf smpl-nhgroup-state {
               type string;
               description "State of the next-hop-group";
             }
             container smpl-nhgroup-member-list {
               leaf smpl-nhgroup-member-interface {
                 type string;
                 description "Name of the next-hop-group member interface";
               }
               leaf smpl-nhgroup-nexthop-address {
                 type string;
                 description "Nexthop address of the next-hop-group member interface";
               }
             }
             container smpl-nhgroup-subgroup {
               leaf smpl-nhgroup-name {
                 type string;
                 description "Name of the next-hop-group";
               }
               leaf smpl-nhgroup-nexthop-state {
                 type string;
                 description "State of the next-hop";
               }
               container smpl-subgroup-member-list {
                 leaf smpl-nhgroup-member-interface {
                   type string;
                   description "Name of the next-hop-group member interface";
                 }
                 leaf smpl-nhgroup-nexthop-address {
                   type string;
                   description "Nexthop address of the next-hop-group member interface";
                 }
               }
             }
           }
           container detail {
             leaf smpl-nhgroup-name {
               type string;
               description "Name of the next-hop-group";
             }
             leaf smpl-nhgroup-type {
               type string;
               description "Type of the next-hop-group";
             }
             leaf smpl-nhgroup-state {
               type string;
               description "State of the next-hop-group";
             }
             leaf smpl-nhgroup-num-members-configured {
               type int32;
               description "Number of members interfaces that are configured";
             }
             leaf smpl-nhgroup-num-members-up {
               type int32;
               description "Number of members interfaces that are up";
             }
             leaf smpl-nhgroup-subgroups-configured {
               type int32;
               description "Number of subgroups that are configured";
             }
             leaf smpl-nhgroup-subgroups-up {
               type int32;
               description "Number of subgroups that are up";
             }
             leaf smpl-nhgroup-nhid-header {
               type string;
               description "Next-hop index header";
             }
             container smpl-nhgroup-member-list {
               leaf smpl-nhgroup-member-interface {
                 type string;
                 description "Name of the next-hop-group member interface";
               }
               leaf smpl-nhgroup-nexthop-address {
                 type string;
                 description "Nexthop address of the next-hop-group member interface";
               }
               leaf smpl-nhgroup-nexthop-state {
                 type string;
                 description "State of the next-hop";
               }
               leaf smpl-nexthop-index {
                 type string;
                 description "Next-hop index value";
               }
             }
             container smpl-nhgroup-subgroup {
               leaf smpl-nhgroup-name {
                 type string;
                 description "Name of the next-hop-group";
               }
               leaf smpl-nhgroup-state {
                 type string;
                 description "State of the next-hop-group";
               }
               leaf smpl-nexthop-index {
                 type string;
                 description "Next-hop index value";
               }
               leaf smpl-subgroup-num-members-configured {
                 type int32;
                 description "Number of subgroup members interfaces that are configured";
               }
               leaf smpl-subgroup-num-members-up {
                 type int32;
                 description "Number of subgroup members interfaces that are up";
               }
               leaf smpl-nhgroup-nhid-header {
                 type string;
                 description "Next-hop index header";
               }
               leaf smpl-nhgroup-nexthop-state {
                 type string;
                 description "State of the next-hop";
               }
               container smpl-subgroup-member-list {
                 leaf smpl-nhgroup-member-interface {
                   type string;
                   description "Name of the next-hop-group member interface";
                 }
                 leaf smpl-nhgroup-nexthop-address {
                   type string;
                   description "Nexthop address of the next-hop-group member interface";
                 }
               }
             }
           }
         }
       }
     }
   }
   rpc get-forwarding-options-port-mirroring {
     description "Show port-mirroring information";
     input {
       leaf verbosity {
         default "detail";
         type enumeration {
           enum "terse" {
             description "Display terse output";
           }
           enum "detail" {
             description "Display detail output";
           }
         }
       }
       leaf instance-name {
         description "Name of port-mirroring instance";
         type string;
       }
     }
     output {
       container smpl-port-mirroring {
         container smpl-port-mirroring-instance {
           leaf smpl-instance-name {
             type string;
             description "Name of the instance";
           }
           leaf smpl-instance-id {
             type int32;
             description "Instance identifier";
           }
           leaf smpl-instance-input-rate {
             type int32;
             description "Ratio of packets to be sampled (1 out of N)";
           }
           leaf smpl-instance-input-run-length {
             type int32;
             description "Number of samples after initial trigger";
           }
           leaf smpl-instance-input-maximum-packet-length {
             type int32;
             description "Maximum length of the mirrored packet";
           }
           leaf smpl-instance-nhid-header {
             type string;
             description "Next-hop index header";
           }
           container terse {
             leaf smpl-instance-state {
               type string;
               description "State of the instance";
             }
             container smpl-port-mirror-output-family-list {
             }
           }
           container detail {
             leaf smpl-instance-name {
               type string;
               description "Name of the instance";
             }
             leaf smpl-instance-id {
               type int32;
               description "Instance identifier";
             }
             leaf smpl-instance-input-rate {
               type int32;
               description "Ratio of packets to be sampled (1 out of N)";
             }
             leaf smpl-instance-input-run-length {
               type int32;
               description "Number of samples after initial trigger";
             }
             leaf smpl-instance-input-maximum-packet-length {
               type int32;
               description "Maximum length of the mirrored packet";
             }
             leaf smpl-instance-nhid-header {
               type string;
               description "Next-hop index header";
             }
             leaf smpl-instance-state {
               type string;
               description "State of the instance";
             }
             container smpl-port-mirror-output-family-list {
               leaf smpl-output-family-name {
                 type string;
                 description "Family of the desintation";
               }
               leaf smpl-output-family-state {
                 type string;
                 description "State of desintation";
               }
               leaf smpl-output-family-destination {
                 type string;
                 description "Desintation interface/group of the family";
               }
               leaf smpl-nexthop-index {
                 type string;
                 description "Next-hop index value";
               }
               container smpl-nhgroup-member-list {
                 leaf smpl-nhgroup-member-interface {
                   type string;
                   description "Name of the next-hop-group member interface";
                 }
                 leaf smpl-nhgroup-nexthop-address {
                   type string;
                   description "Nexthop address of the next-hop-group member interface";
                 }
               }
             }
           }
         }
       }
     }
   }
 }
