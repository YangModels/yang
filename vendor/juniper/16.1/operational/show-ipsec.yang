/*
 * Copyright (c) 2017 Juniper Networks, Inc.
 * All rights reserved.
 */

 module show-ipsec {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-certificates-information {
     description "Show IPSec digital certificate information";
     status deprecated;
     input {
       leaf level {
         default "brief";
         type enumeration {
           enum "brief" {
             description "Display brief output";
           }
           enum "detail" {
             description "Display detailed output";
           }
         }
       }
       leaf serial-number {
         description "Serial number of certificate";
         type string {
           length "1 .. 255";
         }
       }
     }
   }
   rpc get-crl-information {
     description "Show IPSec digital certificate revocation lists";
     input {
       leaf level {
         default "brief";
         type enumeration {
           enum "brief" {
             description "Display brief output";
           }
           enum "detail" {
             description "Display detailed output";
           }
         }
       }
       leaf crl-name {
         description "Name of CRL";
         type string {
           length "1 .. 255";
         }
       }
     }
     output {
       container crl-information {
         container brief {
           container crl {
             leaf cert-issuer {
               type string;
             }
           }
         }
         container detail {
           container crl {
             leaf cert-id {
               type int32;
             }
             leaf cert-references {
               type int32;
             }
             leaf cert-issuer {
               type string;
             }
             container crl-list {
               description "Information about a single CRL entry";
               leaf serial {
                 type int32;
               }
               leaf revocation-date {
                 type string;
               }
             }
           }
         }
       }
     }
   }
   rpc get-security-associations-information {
     description "Show IPSec security association information";
     input {
       leaf level {
         default "brief";
         type enumeration {
           enum "brief" {
             description "Display brief output";
           }
           enum "detail" {
             description "Display detailed output";
           }
         }
       }
       leaf sa-name {
         description "Name of security association";
         type string {
           length "1 .. 32";
         }
       }
       leaf hex {
         description "Display SPI in hexadecimal format";
         type empty;
       }
     }
     output {
       container security-associations-information {
         container brief {
           container security-associations-block {
             description "Information about a single security association block";
             leaf sa-name {
               type string;
               description "Name of the security association";
             }
             leaf sa-block-state {
               type string;
               description "Status of the SA configuration block";
             }
             container sa-tunnel-information {
               leaf sa-no-information {
                 type empty;
                 description "Output string when there are no security associations present";
               }
             }
             container security-associations {
               description "Information about a single security association";
               leaf sa-direction {
                 type string;
                 description "Direction of the security association";
               }
               leaf sa-spi {
                 type string;
                 description "Security Parameter Index";
               }
               leaf sa-aux-spi {
                 type string;
                 description "Auxiliary Security Parameter Index";
               }
               leaf sa-mode {
                 type string;
                 description "Mode of the security association";
               }
               leaf sa-type {
                 type string;
               }
               leaf sa-protocol {
                 type string;
                 description "IPSec security protocol";
               }
             }
           }
         }
         container detail {
           container security-associations-block {
             description "Information about a single security association block";
             leaf sa-name {
               type string;
               description "Name of the security association";
             }
             leaf sa-block-state {
               type string;
               description "Status of the SA configuration block";
             }
             container sa-tunnel-information {
               leaf sa-local-gateway-interface {
                 type string;
                 description "Local gateway  interface";
               }
               leaf sa-local-gateway {
                 type ipaddr;
                 description "Local gateway address";
               }
               leaf sa-remote-gateway {
                 type ipaddr;
                 description "Remote gateway address";
               }
               leaf sa-local-identity {
                 type string;
                 description "Local identity information";
               }
               leaf sa-remote-identity {
                 type string;
                 description "Remote identity information";
               }
               leaf sa-inside-interface {
                 type string;
                 description "Name of IPSec interface to internal network";
               }
               leaf sa-tunnel-mtu {
                 type int32;
                 description "MTU of the IPSec Tunnel";
               }
               leaf sa-udp-encapsulate {
                 type string;
                 description "UDP encapsulation related information";
               }
               leaf sa-udp-dst-port {
                 type string;
                 description "UDP encapsulation port related information";
               }
               leaf sa-no-information {
                 type empty;
                 description "Output string when there are no security associations present";
               }
             }
             container security-associations {
               description "Information about a single security association";
               leaf sa-direction {
                 type string;
                 description "Direction of the security association";
               }
               leaf sa-spi {
                 type string;
                 description "Security Parameter Index";
               }
               leaf sa-aux-spi {
                 type string;
                 description "Auxiliary Security Parameter Index";
               }
               leaf sa-mode {
                 type string;
                 description "Mode of the security association";
               }
               leaf sa-type {
                 type string;
               }
               leaf sa-state {
                 type string;
                 description "Status of the SA";
               }
               leaf sa-protocol {
                 type string;
                 description "IPSec security protocol";
               }
               leaf sa-authentication-algorithm {
                 type string;
                 description "Authentication algorithm";
               }
               leaf sa-encryption-algorithm {
                 type string;
                 description "Encryption algorithm";
               }
               leaf sa-soft-lifetime {
                 type string;
                 description "Remaining lifetime, in seconds or kilobytes, before soft lifetime expires";
               }
               leaf sa-hard-lifetime {
                 type string;
                 description "Remaining lifetime, in seconds or kilobytes, before hard lifetime expires";
               }
               leaf sa-anti-replay-service {
                 type string;
                 description "Anti-replay service";
               }
               leaf sa-replay-window-size {
                 type int32;
                 description "Replay window size";
               }
               leaf sa-copy-tos-from-inner-ip-header {
                 type string;
                 description "Copy ToS from inner ip header";
               }
               leaf sa-tos-value {
                 type int32;
                 description "ToS value";
               }
               leaf sa-copy-ttl-from-inner-ip-header {
                 type string;
                 description "Copy TTL from inner ip header";
               }
               leaf sa-ttl-value {
                 type int32;
                 description "TTL value";
               }
               leaf sa-authentication-key {
                 type string;
                 description "Authentication key in hexadecimal format";
               }
               leaf sa-encryption-key {
                 type string;
                 description "Encryption key in hexadecimal format";
               }
             }
           }
         }
       }
     }
   }
   rpc get-ipsec-tunnel-redundancy-information {
     description "Show remote tunnel redundancy information";
     input {
       leaf security-association-name {
         description "Name of security association";
         type string;
       }
     }
     output {
       container ipsec-tunnel-redundancy-information {
         container ipsec-tunnel-redundancy {
           description "Information about ipsec tunnel redundancy";
           leaf sa-name {
             type string;
             description "Name of the security association";
           }
           leaf ipsec-redundancy-counter {
             type int32;
             description "Failover counter";
           }
           leaf ipsec-tunnel-redundancy-local-address {
             type ipaddr;
             description "Address of local gateway";
           }
           leaf ipsec-tunnel-redundancy-primary-remote-address {
             type ipaddr;
             description "Address of primary remote gateway";
           }
           leaf ipsec-redundancy-primary-state {
             type string;
             description "State of primary remote gateway";
           }
           leaf ipsec-tunnel-redundancy-backup-remote-address {
             type ipaddr;
             description "Address of backup remote gateway";
           }
           leaf ipsec-redundancy-backup-state {
             type string;
             description "State of backup remote gateway";
           }
           leaf ipsec-redundancy-tunnel-no-information {
             type empty;
             description "Output string when tunnel redundancy is not configured";
           }
         }
       }
     }
   }
   rpc get-ipsec-pic-redundancy-information {
     description "Show ES PIC redundancy information";
     input {
       leaf interface-name {
         description "Name of ES interface";
         type string;
       }
     }
     output {
       container ipsec-pic-redundancy-information {
         container ipsec-pic-redundancy {
           description "Information about ipsec pic redundancy";
           leaf ipsec-redundancy-counter {
             type int32;
             description "Failover counter";
           }
           leaf ipsec-pic-redundancy-primary-interface {
             type string;
             description "Primary ES interface";
           }
           leaf ipsec-redundancy-primary-state {
             type string;
             description "State of primary remote gateway";
           }
           leaf ipsec-pic-redundancy-backup-interface {
             type string;
             description "Backup ES interface";
           }
           leaf ipsec-redundancy-backup-state {
             type string;
             description "State of backup remote gateway";
           }
           leaf ipsec-redundancy-pic-no-information {
             type empty;
             description "Output string when there are no pic redundancy present";
           }
         }
       }
     }
   }
 }
