/*
 * Copyright (c) 2017 Juniper Networks, Inc.
 * All rights reserved.
 */

 module show-bridge {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-bridge-instance-information {
     description "Show bridge domain information";
     input {
       leaf instance {
         description "Display information for a specified instance";
         default "all";
         type string;
       }
       leaf bridge-domain {
         description "Display information for a specified bridge domain";
         status deprecated;
         default "all";
         type string;
       }
       leaf bridge-domain-name {
         description "Display information for a specified bridge domain";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       container interface-choice {
         choice interface-choice_c {
           case interface {
             leaf interface {
               description "Name of interface for which to display table";
               type interface-unit;
             }
           }
         }
       }
       leaf verbosity {
         default "brief";
         type enumeration {
           enum "detail" {
             description "Display detailed output";
           }
           enum "brief" {
             description "Display brief output";
           }
           enum "extensive" {
             description "Display extensive output";
           }
         }
       }
     }
     output {
       container l2ald-bridge-instance-information {
         container operational {
           description "Operational bridge instances that can be passed to netapp commands";
           container l2ald-bridge-instance-group {
             leaf l2rtb-name {
               type string;
               description "Name of the routing instance";
             }
             leaf l2rtb-bridging-domain {
               type string;
               description "Name of the bridging domain";
             }
             leaf l2rtb-instance-description {
               type string;
             }
             leaf l2rtb-instance-type {
               type string;
               description "Type of instance (routing instance/bridge domain)";
             }
             leaf l2rtb-instance-restart-state {
               type string;
             }
             leaf l2rtb-instance-pathse1-timeout {
               type int32;
             }
           }
         }
         container brief {
           description "Operational bridge instances that can be passed to netapp commands";
           container l2ald-bridge-instance-group {
             leaf l2rtb-brief-summary {
               type empty;
             }
             leaf l2rtb-name {
               type string;
               description "Name of the routing instance";
             }
             leaf l2rtb-bridging-domain {
               type string;
               description "Name of the bridging domain";
             }
             leaf l2rtb-bridge-vlan {
               type string;
             }
             leaf l2rtb-interface-name {
               type string;
             }
             leaf l2rtb-instance-description {
               type string;
             }
             leaf l2rtb-instance-type {
               type string;
               description "Type of instance (routing instance/bridge domain)";
             }
             leaf l2rtb-instance-restart-state {
               type string;
             }
             leaf l2rtb-instance-pathse1-timeout {
               type int32;
             }
           }
         }
         container detail {
           description "Operational bridge instances that can be passed to netapp commands";
           container l2ald-bridge-instance-group {
             leaf l2rtb-name {
               type string;
               description "Name of the routing instance";
             }
             leaf l2rtb-bridging-domain {
               type string;
               description "Name of the bridging domain";
             }
             leaf l2rtb-instance-state {
               type string;
             }
             leaf l2rtb-bridge-vlan {
               type string;
             }
             leaf l2rtb-bridge-evpn-extension {
               type string;
             }
             leaf l2rtb-pvlan-type {
               type string;
             }
             leaf l2rtb-pvlan {
               type string;
             }
             leaf l2rtb-bridge-vlan-scope {
               type string;
             }
             leaf l2rtb-instance-flags {
               type string;
             }
             leaf l2rtb-isid-list {
               type string;
             }
             leaf l2rtb-interface-name {
               type string;
             }
             leaf l2rtb-macs-learned {
               type uint32;
               description "Number of configured static and dynamic MACs that are learned on this routing instance";
             }
             leaf l2rtb-instance-description {
               type string;
             }
             leaf l2rtb-instance-type {
               type string;
               description "Type of instance (routing instance/bridge domain)";
             }
             leaf l2rtb-instance-restart-state {
               type string;
             }
             leaf l2rtb-instance-pathse1-timeout {
               type int32;
             }
             container l2rtb-pvlan-secondary-bridge-domain {
               leaf l2rtb-secondary-bridge-domain-id {
                 type uint32;
               }
               leaf l2rtb-secondary-bridge-domain-name {
                 type string;
               }
             }
           }
         }
       }
     }
   }
   rpc get-operational-bridge-instance-information {
     description "Show operational bridging instance";
     output {
       container l2ald-bridge-instance-information {
         container operational {
           description "Operational bridge instances that can be passed to netapp commands";
           container l2ald-bridge-instance-group {
             leaf l2rtb-name {
               type string;
               description "Name of the routing instance";
             }
             leaf l2rtb-bridging-domain {
               type string;
               description "Name of the bridging domain";
             }
             leaf l2rtb-instance-description {
               type string;
             }
             leaf l2rtb-instance-type {
               type string;
               description "Type of instance (routing instance/bridge domain)";
             }
             leaf l2rtb-instance-restart-state {
               type string;
             }
             leaf l2rtb-instance-pathse1-timeout {
               type int32;
             }
           }
         }
         container brief {
           description "Operational bridge instances that can be passed to netapp commands";
           container l2ald-bridge-instance-group {
             leaf l2rtb-brief-summary {
               type empty;
             }
             leaf l2rtb-name {
               type string;
               description "Name of the routing instance";
             }
             leaf l2rtb-bridging-domain {
               type string;
               description "Name of the bridging domain";
             }
             leaf l2rtb-bridge-vlan {
               type string;
             }
             leaf l2rtb-interface-name {
               type string;
             }
             leaf l2rtb-instance-description {
               type string;
             }
             leaf l2rtb-instance-type {
               type string;
               description "Type of instance (routing instance/bridge domain)";
             }
             leaf l2rtb-instance-restart-state {
               type string;
             }
             leaf l2rtb-instance-pathse1-timeout {
               type int32;
             }
           }
         }
         container detail {
           description "Operational bridge instances that can be passed to netapp commands";
           container l2ald-bridge-instance-group {
             leaf l2rtb-name {
               type string;
               description "Name of the routing instance";
             }
             leaf l2rtb-bridging-domain {
               type string;
               description "Name of the bridging domain";
             }
             leaf l2rtb-instance-state {
               type string;
             }
             leaf l2rtb-bridge-vlan {
               type string;
             }
             leaf l2rtb-bridge-evpn-extension {
               type string;
             }
             leaf l2rtb-pvlan-type {
               type string;
             }
             leaf l2rtb-pvlan {
               type string;
             }
             leaf l2rtb-bridge-vlan-scope {
               type string;
             }
             leaf l2rtb-instance-flags {
               type string;
             }
             leaf l2rtb-isid-list {
               type string;
             }
             leaf l2rtb-interface-name {
               type string;
             }
             leaf l2rtb-macs-learned {
               type uint32;
               description "Number of configured static and dynamic MACs that are learned on this routing instance";
             }
             leaf l2rtb-instance-description {
               type string;
             }
             leaf l2rtb-instance-type {
               type string;
               description "Type of instance (routing instance/bridge domain)";
             }
             leaf l2rtb-instance-restart-state {
               type string;
             }
             leaf l2rtb-instance-pathse1-timeout {
               type int32;
             }
             container l2rtb-pvlan-secondary-bridge-domain {
               leaf l2rtb-secondary-bridge-domain-id {
                 type uint32;
               }
               leaf l2rtb-secondary-bridge-domain-name {
                 type string;
               }
             }
           }
         }
       }
     }
   }
   rpc get-satellite-control-bridge-domain {
     description "Show satellite bridge domain details";
     input {
       leaf verbosity_level {
         default "brief";
         type enumeration {
           enum "brief" {
             description "Display brief output (default)";
           }
           enum "detail" {
             description "Display detailed output";
           }
           enum "extensive" {
             description "Display extensive output";
           }
         }
       }
       leaf bridge-domain-name {
         description "Name of the bridge domain";
         type string;
       }
       leaf vswitch-name {
         description "VSwitch name";
         type string;
       }
       leaf fpc {
         description "FPC slot number";
         type uint32 {
           range "65 .. 254";
         }
       }
     }
   }
   rpc get-bridge-statistics-information {
     description "Show bridge statistics information";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf bridge-domain {
         description "Display information for a specified bridge domain";
         default "all";
         type string;
       }
     }
     output {
       container bridge-statistics-information {
         container l2ald-rtb-entry {
           container brief {
             leaf l2rtb-instance-type {
               type string;
               description "Type of instance (routing instance/bridge domain)";
             }
             leaf l2rtb-logical-system {
               type string;
               description "Logical system name";
             }
             leaf l2rtb-name {
               type string;
               description "Name of the routing instance";
             }
             leaf l2rtb-bridging-domain {
               type string;
               description "Name of the bridging domain";
             }
             leaf l2rtb-id {
               type uint32;
               description "Routing instance identifier";
             }
             leaf l2rtb-l2irb-ifl-index {
               type uint32;
             }
             leaf l2rtb-flags {
               type string;
               description "Attributes associated with this routing instance";
             }
             leaf l2bd-vlan-id {
               type string;
               description "Bridge domain VLAN";
             }
           }
           container extensive {
             leaf l2rtb-logical-system {
               type string;
               description "Logical system name";
             }
             leaf l2rtb-name {
               type string;
               description "Name of the routing instance";
             }
             leaf l2rtb-bridging-domain {
               type string;
               description "Name of the bridging domain";
             }
             leaf l2rtb-id {
               type uint32;
               description "Routing instance identifier";
             }
             leaf l2bd-id {
               type uint32;
               description "Bridge domain identifier";
             }
             leaf l2bd-generation {
               type uint32;
               description "Bridge domain generation identifier";
             }
             leaf l2rtb-mac-limit {
               type uint32;
               description "Maximum number of MAC addresses that can be learned on this routing instance";
             }
             leaf l2rtb-macs-learned {
               type uint32;
               description "Number of configured static and dynamic MACs that are learned on this routing instance";
             }
             leaf l2rtb-config-smacs-learned {
               type uint32;
               description "Number of configured static MACs that are learned on this routing instance";
             }
             leaf l2rtb-non-config-smacs-learned {
               type uint32;
               description "Number of non configured static MACs that are learned on this routing instance";
             }
             leaf l2rtb-irb-interface {
               type string;
               description "Name of the IRB interface associated with this routing instance";
             }
             leaf l2rtb-irb-interface-index {
               type uint32;
               description "IRB interface index associated with this routing instance";
             }
             leaf l2rtb-sequence-number {
               type uint32;
               description "Current routing instance sequence number";
             }
             leaf l2rtb-handle {
               type uint32;
               description "Handle associated with this routing instance";
             }
             leaf l2bd-vlan-id {
               type string;
               description "Bridge domain VLAN";
             }
             leaf l2rtb-flags {
               type string;
               description "Attributes associated with this routing instance";
             }
             leaf l2rtb-peer-pbbn-rtb-id {
               type uint32;
               description "Peer PBBN RTB index";
             }
             leaf l2rtb-configured-service-id {
               type uint32;
               description "Configured Service-id attributes associated with this routing instance";
             }
             leaf l2rtb-active-service-id {
               type uint32;
               description "Service-id attributes associated with this routing instance/bridge domain";
             }
             leaf l2rtb-config-bd-vlan {
               type string;
               description "Vlan configured for the givn bridge domain on routing instance";
             }
             leaf l2rtb-config-operation {
               type string;
               description "Configuration notify operation on bridge domain/routing instance";
             }
             leaf l2rtb-config-smac-count {
               type uint32;
               description "Configured Static MAC on the BD";
             }
             leaf l2rtb-config-params {
               type string;
               description "Configured attributes associated with this routing instance/bridge domain";
             }
             leaf l2rtb-config-flags {
               type string;
               description "Configured flags associated with this routing instance/bridge domain";
             }
             leaf l2rtb-configured-rg-id {
               type uint32;
               description "Config Redundancy Group ID";
             }
             leaf l2rtb-active-rg-id {
               type uint32;
               description "Active Redundancy Group ID";
             }
             leaf l2rtb-configured-bd-service-id {
               type uint32;
               description "Configured Service-id attributes associated with this bridge domain";
             }
             leaf l2rtb-active-bd-service-id {
               type uint32;
               description "Service-id attributes associated with this bridge domain";
             }
             leaf l2rtb-configured-bd-vnid {
               type uint32;
               description "Configured VXLAN identifier";
             }
             leaf l2rtb-active-bd-vnid {
               type uint32;
               description "Active VXLAN identifier";
             }
             leaf l2rtb-configured-bd-vxgrp {
               type string;
               description "Configured VXLAN multicast group IP address";
             }
             leaf l2rtb-active-bd-vxgrp {
               type string;
               description "Active VXLAN multicast group IP address";
             }
             leaf l2rtb-configured-decap-accept-inner-vlan {
               type uint32;
               description "Configured VXLAN Decap accept inner vlan";
             }
             leaf l2rtb-configured-encap-inner-vlan {
               type uint32;
               description "Configured VXLAN Encap inner vlan";
             }
             leaf l2rtb-configured-unreachable-rvtep-timer {
               type uint32;
               description "Configured VXLAN Unreachable rvtep timer";
             }
             leaf l2rtb-configured-ovsdb-enabled {
               type string;
               description "Configured VXLAN OVSDB Enabled";
             }
             leaf l2rtb-active-bd-l3rtt {
               type uint32;
               description "Active VXLAN Layer-3 routing instance index";
             }
             leaf l2rtb-active-bd-svtep-ip {
               type string;
               description "Active VXLAN source tunnel endpoint IP address";
             }
             leaf l2rtb-config-ownership-flags {
               type string;
               description "Configured ownership flags on attributes associated with this routing instance/bridge domain";
             }
             leaf l2rtb-ownership-flags {
               type string;
               description "Kernel ownership flags on attributes associated with this routing instance";
             }
             leaf l2rtb-config-mvrp-ref-count {
               type uint32;
               description " Number of join count on the bridge domain";
             }
             leaf l2rtb-rtsock-write-errors {
               type uint32;
               description "Number of times kernel write has failed.";
             }
           }
         }
         container interface-statistics {
           leaf remote-pe {
             type ipaddr;
           }
           leaf broadcast-packets {
             type uint64;
             description "Broadcast packets";
           }
           leaf broadcast-bytes {
             type uint64;
             description "Broadcast bytes";
           }
           leaf multicast-packets {
             type uint64;
             description "Multicast packets";
           }
           leaf multicast-bytes {
             type uint64;
             description "Multicast bytes";
           }
           leaf flooded-packets {
             type uint64;
             description "Flooded packets";
           }
           leaf flooded-bytes {
             type uint64;
             description "Flooded bytes";
           }
           leaf unicast-packets {
             type uint64;
             description "Unicast packets";
           }
           leaf unicast-bytes {
             type uint64;
             description "Unicast bytes";
           }
           leaf num-mac-count {
             type int32;
             description "Number of addresses learned on the interface";
           }
           leaf mac-limit {
             type int32;
             description "Limit of number of addresses learned on interface";
           }
           container interface {
             leaf interface-name {
               type string;
               description "Bridging media access control address interface";
             }
             leaf local-interface-index {
               type int32;
             }
             leaf interface-flags {
               type int32;
             }
           }
         }
       }
     }
   }
   rpc get-bridge-mac-table {
     description "Show media access control table";
     input {
       leaf instance {
         description "Display information for a specified instance";
         default "all";
         type string;
       }
       leaf bridge-domain {
         description "Name of bridging domain, or 'all'";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Display MAC address learned on a specified VLAN";
         type string;
       }
       leaf isid {
         description "Display Information for specified ISID or all ISID(s)";
         type string;
       }
       leaf address {
         description "MAC address";
         default "all";
         type mac-addr;
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "summary" {
             description "Display summary output";
           }
         }
       }
     }
     output {
       container l2ald-rtb-macdb {
         leaf l2ald-macdb-rtb-name {
           type string;
           description "Bridging MAC database for a routing instance";
         }
         container l2ald-mac-entry {
           container brief {
             leaf l2-mac-address {
               type mac-addr;
               description "Media access control address learned from another source";
             }
             leaf l2-mac-logical-interface {
               type string;
               description "Name of logical interface on which MAC address was learned";
             }
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-rtb {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-mac-fwd-next-hop {
               type uint32;
               description "Forwarding next hop for Control MAC to be routed to";
             }
             leaf l2-mac-property {
               type string;
               description "Property of MAC route";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-pvlan {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-mac-fwd-next-hop {
               type uint32;
               description "Forwarding next hop for Control MAC to be routed to";
             }
             leaf l2-mac-property {
               type string;
               description "Property of MAC route";
             }
             leaf l2-mac-pvlan-port-role {
               type string;
               description "The PVLAN port role for interface associated with these MAC addresses";
             }
             leaf l2-mac-pvlan-vlan-id {
               type string;
               description "The PVLAN vlan ID associated with these MAC addresses";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-pbn-rtb {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-isid {
               type uint32;
               description "ISID for the bridging domain";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-remote-beb-mac-address {
               type mac-addr;
               description "Media access control address of remote backbone edge bridge (BEB)";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container extensive {
             leaf l2-mac-address {
               type mac-addr;
               description "Media access control address learned from another source";
             }
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-isid {
               type uint32;
               description "ISID for the bridging domain";
             }
             leaf l2-bridge-vlan {
               type string;
               description "Vlan for the bridging domain";
             }
             leaf l2-mac-logical-interface {
               type string;
               description "Name of logical interface on which MAC address was learned";
             }
             leaf l2-mac-base-logical-interface {
               type string;
               description "Name of logical interface on which MAC address was learnt first";
             }
             leaf l2-remote-beb-mac-address {
               type mac-addr;
               description "Media access control address of remote backbone edge bridge (BEB)";
             }
             leaf l2-mac-entry-flags {
               type string;
               description "Forwarding entry flags associated with these MAC addresses";
             }
             leaf l2-mac-epoch {
               type uint32;
               description "Spanning Tree Protocol (STP) epoch number when MAC address was learned";
             }
             leaf l2-mac-sequence-number {
               type uint32;
               description "Sequence number assigned to this MAC address";
             }
             leaf l2-mac-learn-mask {
               type string;
               description "Mask of Packet Forwarding Engines where this MAC address was learned";
             }
             leaf l2-mac-pvlan-port-role {
               type string;
               description "The PVLAN port role for interface associated with these MAC addresses";
             }
             leaf l2-mac-pvlan-vlan-id {
               type string;
               description "The PVLAN vlan ID associated with these MAC addresses";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
             container l2ald-mac-source-address-statistics {
               description "MAC source address statistics";
               leaf packet-count {
                 type uint64;
                 description "Packet count";
               }
               leaf byte-count {
                 type uint64;
                 description "Byte count";
               }
             }
             container l2ald-mac-destination-address-statistics {
               description "MAC destination address statistics";
               leaf packet-count {
                 type uint64;
                 description "Packet count";
               }
               leaf byte-count {
                 type uint64;
                 description "Byte count";
               }
             }
           }
           container brief-rvtep {
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-remote-vtep-address {
               type string;
               description "Remote VXLAN tunnel endpoint ip address";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-vxlan-evpn {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-active-source {
               type string;
               description "Remote VXLAN tunnel endpoint ip address or ESI value";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
         }
       }
     }
   }
   rpc get-bridge-interface-mac-table {
     description "Display MAC table for a specified interface";
     input {
       container interface-choice {
         choice interface-choice_c {
           case interface-name {
             leaf interface-name {
               description "Name of interface for which to display table";
               type string;
             }
           }
           case all {
             leaf all {
               description "Display MAC table for all the interfaces";
               type empty;
             }
           }
         }
       }
       leaf remote-beb-mac-address {
         description "Remote backbone edge bridge MAC address";
         default "all";
         type mac-addr;
       }
       leaf vlan-id {
         description "Display MAC address learned on a specified VLAN";
         type string;
       }
       leaf isid {
         description "Display Information for specified ISID or all ISID(s)";
         type string;
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "summary" {
             description "Display summary output";
           }
         }
       }
     }
     output {
       container l2ald-interface-macdb {
         leaf l2ald-macdb-if-name {
           type string;
         }
         container l2ald-mac-entry {
           container brief {
             leaf l2-mac-address {
               type mac-addr;
               description "Media access control address learned from another source";
             }
             leaf l2-mac-logical-interface {
               type string;
               description "Name of logical interface on which MAC address was learned";
             }
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-rtb {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-mac-fwd-next-hop {
               type uint32;
               description "Forwarding next hop for Control MAC to be routed to";
             }
             leaf l2-mac-property {
               type string;
               description "Property of MAC route";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-pvlan {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-mac-fwd-next-hop {
               type uint32;
               description "Forwarding next hop for Control MAC to be routed to";
             }
             leaf l2-mac-property {
               type string;
               description "Property of MAC route";
             }
             leaf l2-mac-pvlan-port-role {
               type string;
               description "The PVLAN port role for interface associated with these MAC addresses";
             }
             leaf l2-mac-pvlan-vlan-id {
               type string;
               description "The PVLAN vlan ID associated with these MAC addresses";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-pbn-rtb {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-isid {
               type uint32;
               description "ISID for the bridging domain";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-remote-beb-mac-address {
               type mac-addr;
               description "Media access control address of remote backbone edge bridge (BEB)";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container extensive {
             leaf l2-mac-address {
               type mac-addr;
               description "Media access control address learned from another source";
             }
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-isid {
               type uint32;
               description "ISID for the bridging domain";
             }
             leaf l2-bridge-vlan {
               type string;
               description "Vlan for the bridging domain";
             }
             leaf l2-mac-logical-interface {
               type string;
               description "Name of logical interface on which MAC address was learned";
             }
             leaf l2-mac-base-logical-interface {
               type string;
               description "Name of logical interface on which MAC address was learnt first";
             }
             leaf l2-remote-beb-mac-address {
               type mac-addr;
               description "Media access control address of remote backbone edge bridge (BEB)";
             }
             leaf l2-mac-entry-flags {
               type string;
               description "Forwarding entry flags associated with these MAC addresses";
             }
             leaf l2-mac-epoch {
               type uint32;
               description "Spanning Tree Protocol (STP) epoch number when MAC address was learned";
             }
             leaf l2-mac-sequence-number {
               type uint32;
               description "Sequence number assigned to this MAC address";
             }
             leaf l2-mac-learn-mask {
               type string;
               description "Mask of Packet Forwarding Engines where this MAC address was learned";
             }
             leaf l2-mac-pvlan-port-role {
               type string;
               description "The PVLAN port role for interface associated with these MAC addresses";
             }
             leaf l2-mac-pvlan-vlan-id {
               type string;
               description "The PVLAN vlan ID associated with these MAC addresses";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
             container l2ald-mac-source-address-statistics {
               description "MAC source address statistics";
               leaf packet-count {
                 type uint64;
                 description "Packet count";
               }
               leaf byte-count {
                 type uint64;
                 description "Byte count";
               }
             }
             container l2ald-mac-destination-address-statistics {
               description "MAC destination address statistics";
               leaf packet-count {
                 type uint64;
                 description "Packet count";
               }
               leaf byte-count {
                 type uint64;
                 description "Byte count";
               }
             }
           }
           container brief-rvtep {
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-remote-vtep-address {
               type string;
               description "Remote VXLAN tunnel endpoint ip address";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-vxlan-evpn {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-active-source {
               type string;
               description "Remote VXLAN tunnel endpoint ip address or ESI value";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
         }
       }
     }
   }
   rpc get-satellite-control-bridge-mac-table {
     description "Show satellite bridge mac table";
     input {
       leaf verbosity_level {
         default "brief";
         type enumeration {
           enum "brief" {
             description "Display brief output (default)";
           }
           enum "detail" {
             description "Display detailed output";
           }
           enum "extensive" {
             description "Display extensive output";
           }
         }
       }
       leaf bridge-domain-name {
         description "Name of the bridge domain";
         type string;
       }
       leaf vswitch-name {
         description "VSwitch name";
         type string;
       }
       leaf interface-name {
         description "Name of bridge logical interface";
         type interface-unit;
       }
       leaf fpc {
         description "FPC slot number";
         type uint32 {
           range "65 .. 254";
         }
       }
     }
   }
   rpc get-bridge-flood-information {
     description "Show bridging flooding information";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf bridge-domain {
         description "Display information for a specified bridge domain";
         default "all";
         type string;
       }
       leaf verbosity {
         default "detail";
         type enumeration {
           enum "detail" {
             description "Display detailed output";
           }
           enum "brief" {
             description "Display brief output";
           }
           enum "extensive" {
             description "Display extensive output";
           }
         }
       }
     }
     output {
       container l2ald-vpls-flood-instance {
         container l2ald-vpls-lr-information {
           container logical-system-info {
             leaf logical-system-name {
               type string;
               description "Logical System";
             }
           }
           container l2ald-vpls-flood-instance-information {
             container brief {
               leaf instance-name {
                 type string;
               }
               leaf num-active-ce-iffs {
                 type int32;
               }
               leaf num-active-ve-iffs {
                 type int32;
               }
               leaf bridging-domain {
                 type string;
               }
               container flood-route {
                 container detail {
                   leaf route-prefix {
                     type string;
                   }
                   leaf route-type {
                     type string;
                   }
                   leaf owner {
                     type string;
                   }
                   leaf nhtype {
                     type string;
                   }
                   leaf nhindex {
                     type int32;
                   }
                   container flood-nh-components {
                     container group {
                       leaf interface-name {
                         type string;
                         description "Bridging media access control address interface";
                       }
                       leaf interface-type {
                         type string;
                       }
                       leaf interface-esi {
                         type string;
                         description "ESI";
                       }
                     }
                   }
                   container flood-nh-group {
                     container extensive {
                       leaf flood-nh-group-name {
                         type string;
                       }
                       leaf flood-nh-group-type {
                         type string;
                       }
                       leaf nhtype {
                         type string;
                       }
                       leaf nhindex {
                         type int32;
                       }
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
                 container extensive {
                   leaf route-prefix {
                     type string;
                   }
                   leaf route-type {
                     type string;
                   }
                   leaf owner {
                     type string;
                   }
                   leaf route-flood-group-name {
                     type string;
                   }
                   leaf route-flood-group-index {
                     type int32;
                   }
                   leaf nhtype {
                     type string;
                   }
                   leaf nhindex {
                     type int32;
                   }
                   leaf make-before-break {
                     type string;
                   }
                   leaf make-before-break-state {
                     type string;
                   }
                   container flood-nh-evpn-core-components {
                     leaf component-nhindex {
                       type int32;
                     }
                     leaf peer {
                       type string;
                     }
                     leaf nh-type {
                       type string;
                     }
                     leaf interface-esi {
                       type string;
                       description "ESI";
                     }
                   }
                   container flood-nh-p2mp-components {
                     leaf component-nhindex {
                       type int32;
                     }
                   }
                   container flood-nh-components {
                     leaf interface-name {
                       type string;
                       description "Bridging media access control address interface";
                     }
                     leaf interface-type {
                       type string;
                     }
                     leaf nhtype {
                       type string;
                     }
                     leaf nhindex {
                       type int32;
                     }
                     leaf interface-esi {
                       type string;
                       description "ESI";
                     }
                     container group {
                     }
                   }
                   container flood-nh-group {
                     leaf flood-nh-group-name {
                       type string;
                     }
                     leaf flood-nh-group-type {
                       type string;
                     }
                     leaf nhtype {
                       type string;
                     }
                     leaf nhindex {
                       type int32;
                     }
                     container extensive {
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
               }
             }
             container detail {
               leaf instance-name {
                 type string;
               }
               leaf num-active-ce-iffs {
                 type int32;
               }
               leaf num-active-ve-iffs {
                 type int32;
               }
               leaf bridge-domain-name {
                 type string;
                 description "Name of the bridging domain";
               }
               leaf bridge-domain-evpn-extension {
                 type string;
                 description "EVPN extension for the BD";
               }
               leaf bridging-domain {
                 type string;
               }
               container flood-route {
                 leaf route-prefix {
                   type string;
                 }
                 leaf route-type {
                   type string;
                 }
                 leaf owner {
                   type string;
                 }
                 leaf nhtype {
                   type string;
                 }
                 leaf nhindex {
                   type int32;
                 }
                 container brief {
                   container flood-nh-components {
                     container group {
                       leaf interface-name {
                         type string;
                         description "Bridging media access control address interface";
                       }
                       leaf interface-type {
                         type string;
                       }
                       leaf interface-esi {
                         type string;
                         description "ESI";
                       }
                     }
                   }
                   container flood-nh-group {
                     container extensive {
                       leaf flood-nh-group-name {
                         type string;
                       }
                       leaf flood-nh-group-type {
                         type string;
                       }
                       leaf nhtype {
                         type string;
                       }
                       leaf nhindex {
                         type int32;
                       }
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
                 container detail {
                   leaf route-prefix {
                     type string;
                   }
                   leaf route-type {
                     type string;
                   }
                   leaf owner {
                     type string;
                   }
                   leaf nhtype {
                     type string;
                   }
                   leaf nhindex {
                     type int32;
                   }
                   container flood-nh-components {
                     container group {
                       leaf interface-name {
                         type string;
                         description "Bridging media access control address interface";
                       }
                       leaf interface-type {
                         type string;
                       }
                       leaf interface-esi {
                         type string;
                         description "ESI";
                       }
                     }
                   }
                   container flood-nh-group {
                     container extensive {
                       leaf flood-nh-group-name {
                         type string;
                       }
                       leaf flood-nh-group-type {
                         type string;
                       }
                       leaf nhtype {
                         type string;
                       }
                       leaf nhindex {
                         type int32;
                       }
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
                 container extensive {
                   leaf route-prefix {
                     type string;
                   }
                   leaf route-type {
                     type string;
                   }
                   leaf owner {
                     type string;
                   }
                   leaf route-flood-group-name {
                     type string;
                   }
                   leaf route-flood-group-index {
                     type int32;
                   }
                   leaf nhtype {
                     type string;
                   }
                   leaf nhindex {
                     type int32;
                   }
                   leaf make-before-break {
                     type string;
                   }
                   leaf make-before-break-state {
                     type string;
                   }
                   container flood-nh-evpn-core-components {
                     leaf component-nhindex {
                       type int32;
                     }
                     leaf peer {
                       type string;
                     }
                     leaf nh-type {
                       type string;
                     }
                     leaf interface-esi {
                       type string;
                       description "ESI";
                     }
                   }
                   container flood-nh-p2mp-components {
                     leaf component-nhindex {
                       type int32;
                     }
                   }
                   container flood-nh-components {
                     leaf interface-name {
                       type string;
                       description "Bridging media access control address interface";
                     }
                     leaf interface-type {
                       type string;
                     }
                     leaf nhtype {
                       type string;
                     }
                     leaf nhindex {
                       type int32;
                     }
                     leaf interface-esi {
                       type string;
                       description "ESI";
                     }
                     container group {
                     }
                   }
                   container flood-nh-group {
                     leaf flood-nh-group-name {
                       type string;
                     }
                     leaf flood-nh-group-type {
                       type string;
                     }
                     leaf nhtype {
                       type string;
                     }
                     leaf nhindex {
                       type int32;
                     }
                     container extensive {
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
               }
             }
             container extensive {
               leaf instance-name {
                 type string;
               }
               leaf num-active-ce-iffs {
                 type int32;
               }
               leaf num-active-ve-iffs {
                 type int32;
               }
               leaf bridge-domain-name {
                 type string;
                 description "Name of the bridging domain";
               }
               leaf bridge-domain-evpn-extension {
                 type string;
                 description "EVPN extension for the BD";
               }
               leaf bridging-domain {
                 type string;
               }
               container flood-route {
                 container brief {
                   leaf route-prefix {
                     type string;
                   }
                   leaf route-type {
                     type string;
                   }
                   leaf owner {
                     type string;
                   }
                   leaf nhtype {
                     type string;
                   }
                   leaf nhindex {
                     type int32;
                   }
                   container flood-nh-components {
                     container group {
                       leaf interface-name {
                         type string;
                         description "Bridging media access control address interface";
                       }
                       leaf interface-type {
                         type string;
                       }
                       leaf interface-esi {
                         type string;
                         description "ESI";
                       }
                     }
                   }
                   container flood-nh-group {
                     container extensive {
                       leaf flood-nh-group-name {
                         type string;
                       }
                       leaf flood-nh-group-type {
                         type string;
                       }
                       leaf nhtype {
                         type string;
                       }
                       leaf nhindex {
                         type int32;
                       }
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
                 container detail {
                   leaf route-prefix {
                     type string;
                   }
                   leaf route-type {
                     type string;
                   }
                   leaf owner {
                     type string;
                   }
                   leaf nhtype {
                     type string;
                   }
                   leaf nhindex {
                     type int32;
                   }
                   container flood-nh-components {
                     container group {
                       leaf interface-name {
                         type string;
                         description "Bridging media access control address interface";
                       }
                       leaf interface-type {
                         type string;
                       }
                       leaf interface-esi {
                         type string;
                         description "ESI";
                       }
                     }
                   }
                   container flood-nh-group {
                     container extensive {
                       leaf flood-nh-group-name {
                         type string;
                       }
                       leaf flood-nh-group-type {
                         type string;
                       }
                       leaf nhtype {
                         type string;
                       }
                       leaf nhindex {
                         type int32;
                       }
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
                 container extensive {
                   leaf route-prefix {
                     type string;
                   }
                   leaf route-type {
                     type string;
                   }
                   leaf owner {
                     type string;
                   }
                   leaf route-flood-group-name {
                     type string;
                   }
                   leaf route-flood-group-index {
                     type int32;
                   }
                   leaf nhtype {
                     type string;
                   }
                   leaf nhindex {
                     type int32;
                   }
                   leaf make-before-break {
                     type string;
                   }
                   leaf make-before-break-state {
                     type string;
                   }
                   container flood-nh-evpn-core-components {
                     leaf component-nhindex {
                       type int32;
                     }
                     leaf peer {
                       type string;
                     }
                     leaf nh-type {
                       type string;
                     }
                     leaf interface-esi {
                       type string;
                       description "ESI";
                     }
                   }
                   container flood-nh-p2mp-components {
                     leaf component-nhindex {
                       type int32;
                     }
                   }
                   container flood-nh-components {
                     leaf interface-name {
                       type string;
                       description "Bridging media access control address interface";
                     }
                     leaf interface-type {
                       type string;
                     }
                     leaf nhtype {
                       type string;
                     }
                     leaf nhindex {
                       type int32;
                     }
                     leaf interface-esi {
                       type string;
                       description "ESI";
                     }
                     container group {
                     }
                   }
                   container flood-nh-group {
                     leaf flood-nh-group-name {
                       type string;
                     }
                     leaf flood-nh-group-type {
                       type string;
                     }
                     leaf nhtype {
                       type string;
                     }
                     leaf nhindex {
                       type int32;
                     }
                     container extensive {
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
               }
             }
           }
         }
       }
     }
   }
   rpc get-bridge-domain-bd-flood-route-information {
     description "Show route for flooding traffic of a bridge domain if no-local-switching is not enabled";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf bridge-domain {
         description "Display information for a specified bridge domain";
         default "all";
         type string;
       }
     }
     output {
       container l2ald-bridge-domain-flood-route-information {
         container flood-route {
           container brief {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container detail {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container extensive {
             leaf route-prefix {
               type string;
             }
             leaf route-type {
               type string;
             }
             leaf owner {
               type string;
             }
             leaf route-flood-group-name {
               type string;
             }
             leaf route-flood-group-index {
               type int32;
             }
             leaf nhtype {
               type string;
             }
             leaf nhindex {
               type int32;
             }
             leaf make-before-break {
               type string;
             }
             leaf make-before-break-state {
               type string;
             }
             container flood-nh-evpn-core-components {
               leaf component-nhindex {
                 type int32;
               }
               leaf peer {
                 type string;
               }
               leaf nh-type {
                 type string;
               }
               leaf interface-esi {
                 type string;
                 description "ESI";
               }
             }
             container flood-nh-p2mp-components {
               leaf component-nhindex {
                 type int32;
               }
             }
             container flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               container group {
               }
             }
             container flood-nh-group {
               leaf flood-nh-group-name {
                 type string;
               }
               leaf flood-nh-group-type {
                 type string;
               }
               leaf nhtype {
                 type string;
               }
               leaf nhindex {
                 type int32;
               }
               container extensive {
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
         }
       }
     }
   }
   rpc get-show-bridge-domain-all-ce-flood-route-information {
     description "Show route for flooding traffic to all CE routers if no-local-switching is enabled";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf bridge-domain {
         description "Display information for a specified bridge domain";
         default "all";
         type string;
       }
     }
     output {
       container l2ald-bridge-domain-flood-route-information {
         container flood-route {
           container brief {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container detail {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container extensive {
             leaf route-prefix {
               type string;
             }
             leaf route-type {
               type string;
             }
             leaf owner {
               type string;
             }
             leaf route-flood-group-name {
               type string;
             }
             leaf route-flood-group-index {
               type int32;
             }
             leaf nhtype {
               type string;
             }
             leaf nhindex {
               type int32;
             }
             leaf make-before-break {
               type string;
             }
             leaf make-before-break-state {
               type string;
             }
             container flood-nh-evpn-core-components {
               leaf component-nhindex {
                 type int32;
               }
               leaf peer {
                 type string;
               }
               leaf nh-type {
                 type string;
               }
               leaf interface-esi {
                 type string;
                 description "ESI";
               }
             }
             container flood-nh-p2mp-components {
               leaf component-nhindex {
                 type int32;
               }
             }
             container flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               container group {
               }
             }
             container flood-nh-group {
               leaf flood-nh-group-name {
                 type string;
               }
               leaf flood-nh-group-type {
                 type string;
               }
               leaf nhtype {
                 type string;
               }
               leaf nhindex {
                 type int32;
               }
               container extensive {
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
         }
       }
     }
   }
   rpc get-show-bridge-domain-ve-flood-route-information {
     description "Show route for flooding traffic to all VE routers if no-local-switching is enabled";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf bridge-domain {
         description "Display information for a specified bridge domain";
         default "all";
         type string;
       }
     }
     output {
       container l2ald-bridge-domain-flood-route-information {
         container flood-route {
           container brief {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container detail {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container extensive {
             leaf route-prefix {
               type string;
             }
             leaf route-type {
               type string;
             }
             leaf owner {
               type string;
             }
             leaf route-flood-group-name {
               type string;
             }
             leaf route-flood-group-index {
               type int32;
             }
             leaf nhtype {
               type string;
             }
             leaf nhindex {
               type int32;
             }
             leaf make-before-break {
               type string;
             }
             leaf make-before-break-state {
               type string;
             }
             container flood-nh-evpn-core-components {
               leaf component-nhindex {
                 type int32;
               }
               leaf peer {
                 type string;
               }
               leaf nh-type {
                 type string;
               }
               leaf interface-esi {
                 type string;
                 description "ESI";
               }
             }
             container flood-nh-p2mp-components {
               leaf component-nhindex {
                 type int32;
               }
             }
             container flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               container group {
               }
             }
             container flood-nh-group {
               leaf flood-nh-group-name {
                 type string;
               }
               leaf flood-nh-group-type {
                 type string;
               }
               leaf nhtype {
                 type string;
               }
               leaf nhindex {
                 type int32;
               }
               container extensive {
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
         }
       }
     }
   }
   rpc get-bridge-domain-re-flood-route-information {
     description "Show route for Routing Engine flooding to all interfaces";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf bridge-domain {
         description "Display information for a specified bridge domain";
         default "all";
         type string;
       }
     }
     output {
       container l2ald-bridge-domain-flood-route-information {
         container flood-route {
           container brief {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container detail {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container extensive {
             leaf route-prefix {
               type string;
             }
             leaf route-type {
               type string;
             }
             leaf owner {
               type string;
             }
             leaf route-flood-group-name {
               type string;
             }
             leaf route-flood-group-index {
               type int32;
             }
             leaf nhtype {
               type string;
             }
             leaf nhindex {
               type int32;
             }
             leaf make-before-break {
               type string;
             }
             leaf make-before-break-state {
               type string;
             }
             container flood-nh-evpn-core-components {
               leaf component-nhindex {
                 type int32;
               }
               leaf peer {
                 type string;
               }
               leaf nh-type {
                 type string;
               }
               leaf interface-esi {
                 type string;
                 description "ESI";
               }
             }
             container flood-nh-p2mp-components {
               leaf component-nhindex {
                 type int32;
               }
             }
             container flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               container group {
               }
             }
             container flood-nh-group {
               leaf flood-nh-group-name {
                 type string;
               }
               leaf flood-nh-group-type {
                 type string;
               }
               leaf nhtype {
                 type string;
               }
               leaf nhindex {
                 type int32;
               }
               container extensive {
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
         }
       }
     }
   }
   rpc get-bridge-domain-mlp-flood-route-information {
     description "Show route for flooding traffic to MAC learning chips";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf bridge-domain {
         description "Display information for a specified bridge domain";
         default "all";
         type string;
       }
     }
     output {
       container l2ald-bridge-domain-flood-route-information {
         container flood-route {
           container brief {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container detail {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container extensive {
             leaf route-prefix {
               type string;
             }
             leaf route-type {
               type string;
             }
             leaf owner {
               type string;
             }
             leaf route-flood-group-name {
               type string;
             }
             leaf route-flood-group-index {
               type int32;
             }
             leaf nhtype {
               type string;
             }
             leaf nhindex {
               type int32;
             }
             leaf make-before-break {
               type string;
             }
             leaf make-before-break-state {
               type string;
             }
             container flood-nh-evpn-core-components {
               leaf component-nhindex {
                 type int32;
               }
               leaf peer {
                 type string;
               }
               leaf nh-type {
                 type string;
               }
               leaf interface-esi {
                 type string;
                 description "ESI";
               }
             }
             container flood-nh-p2mp-components {
               leaf component-nhindex {
                 type int32;
               }
             }
             container flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               container group {
               }
             }
             container flood-nh-group {
               leaf flood-nh-group-name {
                 type string;
               }
               leaf flood-nh-group-type {
                 type string;
               }
               leaf nhtype {
                 type string;
               }
               leaf nhindex {
                 type int32;
               }
               container extensive {
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
         }
       }
     }
   }
   rpc get-bridge-domain-alt-root-flood-route-information {
     description "Show STP alt-root flooding route used for interface";
     input {
       leaf interface {
         description "Interface for which to show alternate-root flooding route";
         type interface-unit;
         mandatory true;
       }
     }
     output {
       container l2ald-bridge-domain-flood-route-information {
         container flood-route {
           container brief {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container detail {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container extensive {
             leaf route-prefix {
               type string;
             }
             leaf route-type {
               type string;
             }
             leaf owner {
               type string;
             }
             leaf route-flood-group-name {
               type string;
             }
             leaf route-flood-group-index {
               type int32;
             }
             leaf nhtype {
               type string;
             }
             leaf nhindex {
               type int32;
             }
             leaf make-before-break {
               type string;
             }
             leaf make-before-break-state {
               type string;
             }
             container flood-nh-evpn-core-components {
               leaf component-nhindex {
                 type int32;
               }
               leaf peer {
                 type string;
               }
               leaf nh-type {
                 type string;
               }
               leaf interface-esi {
                 type string;
                 description "ESI";
               }
             }
             container flood-nh-p2mp-components {
               leaf component-nhindex {
                 type int32;
               }
             }
             container flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               container group {
               }
             }
             container flood-nh-group {
               leaf flood-nh-group-name {
                 type string;
               }
               leaf flood-nh-group-type {
                 type string;
               }
               leaf nhtype {
                 type string;
               }
               leaf nhindex {
                 type int32;
               }
               container extensive {
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
         }
       }
     }
   }
   rpc get-bridge-domain-event-queue-information {
     description "Show queue of pending bridge flood events";
     output {
       container l2ald-bridge-domain-flood-event-queue {
         container l2ald-bridge-domain-flood-next-event {
           container l2ald-bridge-domain-flood-event-info {
             leaf event-name {
               type string;
             }
             leaf event-owner {
               type string;
             }
             leaf event-type {
               type string;
             }
             leaf event-op {
               type string;
             }
             leaf event-error {
               type string;
             }
             container detail {
             }
             container brief {
               leaf event-name {
                 type string;
               }
               leaf event-type {
                 type string;
               }
               leaf event-op {
                 type string;
               }
               leaf event-owner {
                 type string;
               }
             }
           }
         }
         container l2ald-bridge-domain-flood-event-list {
           container l2ald-bridge-domain-flood-event-info {
             leaf event-name {
               type string;
             }
             leaf event-type {
               type string;
             }
             leaf event-op {
               type string;
             }
             leaf event-owner {
               type string;
             }
             container detail {
               leaf event-error {
                 type string;
               }
             }
             container brief {
               leaf event-name {
                 type string;
               }
               leaf event-type {
                 type string;
               }
               leaf event-op {
                 type string;
               }
               leaf event-owner {
                 type string;
               }
             }
           }
         }
       }
     }
   }
   rpc get-satellite-control-flood {
     description "Show the satellite bridge flooding information";
     input {
       leaf verbosity_level {
         default "brief";
         type enumeration {
           enum "brief" {
             description "Display brief output (default)";
           }
           enum "detail" {
             description "Display detailed output";
           }
           enum "extensive" {
             description "Display extensive output";
           }
         }
       }
       leaf vswitch-name {
         description "Virtual switch name";
         type string;
       }
       leaf bridge-domain-name {
         description "Bridge domain name";
         type string;
       }
     }
   }
   rpc get-satellite-control-composite-next-hop {
     description "Show satellite flood next-hops";
     input {
       leaf verbosity_level {
         default "brief";
         type enumeration {
           enum "brief" {
             description "Display brief output (default)";
           }
           enum "detail" {
             description "Display detailed output";
           }
           enum "extensive" {
             description "Display extensive output";
           }
         }
       }
       leaf nexthop-id {
         description "Next-hop ID";
         type int32;
       }
     }
   }
   rpc get-bridge-peer-gateway-mac {
     description "Show MAC addresses installed as gateway MACs";
     input {
       leaf instance {
         description "Display information for a specified instance";
         default "all";
         type string;
       }
       leaf bridge-domain {
         description "Name of bridging domain, or 'all'";
         default "all";
         type string;
       }
       leaf address {
         description "MAC address";
         default "all";
         type mac-addr;
       }
     }
     output {
       container l2rtb-peer-gateway-macdb {
         container l2rtb-peer-gateway-mac-entry {
           container brief {
             leaf l2-gateway-mac-routing-instance {
               type string;
               description "Routing instance in which the GW MAC address is installed";
             }
             leaf l2-gateway-mac-bridge-domain {
               type string;
               description "Bridging domain in which the GW MAC address is installed";
             }
             leaf l2-gateway-mac-bridge-vlan {
               type string;
               description "Vlan for the bridging domain";
             }
             leaf l2-gateway-mac-address {
               type mac-addr;
               description "MAC address Installed as gateway (route-able) MAC";
             }
           }
         }
       }
     }
   }
   rpc get-bridge-evpn-arp-table {
     description "Show INET entries associated with MACs learned via ARP";
     input {
       leaf instance {
         description "Display information for a specified instance";
         default "all";
         type string;
       }
       leaf bridge-domain {
         description "Name of bridging domain, or 'all'";
         default "all";
         type string;
       }
       leaf address {
         description "MAC address";
         default "all";
         type mac-addr;
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "summary" {
             description "Display summary output";
           }
         }
       }
     }
     output {
       container l2rtb-evpn-arp-db {
         leaf l2rtb-evpn-arp-db-rtb-name {
           type string;
           description "Bridging MAC INET database for a routing instance";
         }
         container l2rtb-evpn-arp-entry {
           container brief {
             leaf l2-evpn-arp-inet-address {
               type ipaddr;
               description "INET addresses learned via ARP";
             }
             leaf l2-mac-address {
               type mac-addr;
               description "Media access control address learned from another source";
             }
             leaf l2-mac-logical-interface {
               type string;
               description "Name of logical interface on which MAC address was learned";
             }
             leaf l2-mac-routing-instance {
               type string;
               description "Routing instance in which the MAC address was learned";
             }
             leaf l2-mac-bridging-domain {
               type string;
               description "Bridging domain in which the MAC address was learned";
             }
             leaf l2-mac-interface-device {
               type string;
               description "Name of interface device on which MAC address was learned";
             }
           }
           container brief-rtb {
             leaf l2-mac-routing-instance {
               type string;
               description "Routing instance in which the MAC address was learned";
             }
             leaf l2-mac-bridging-domain {
               type string;
               description "Bridging domain in which the MAC address was learned";
             }
             leaf l2-evpn-arp-inet-address {
               type ipaddr;
               description "INET addresses learned via ARP";
             }
             leaf l2-mac-address {
               type mac-addr;
               description "Media access control address learned from another source";
             }
             leaf l2-mac-logical-interface {
               type string;
               description "Name of logical interface on which MAC address was learned";
             }
             leaf l2-mac-interface-device {
               type string;
               description "Name of interface device on which MAC address was learned";
             }
           }
           container extensive {
             leaf l2-evpn-arp-inet-address {
               type ipaddr;
               description "INET addresses learned via ARP";
             }
             leaf l2-mac-address {
               type mac-addr;
               description "Media access control address learned from another source";
             }
             leaf l2-mac-routing-instance {
               type string;
               description "Routing instance in which the MAC address was learned";
             }
             leaf l2-mac-bridging-domain {
               type string;
               description "Bridging domain in which the MAC address was learned";
             }
             leaf l2-mac-logical-interface {
               type string;
               description "Name of logical interface on which MAC address was learned";
             }
             leaf l2-mac-interface-device {
               type string;
               description "Name of interface device on which MAC address was learned";
             }
             container l2ald-mac-destination-address-statistics {
               description "MAC destination address statistics";
               leaf packet-count {
                 type uint64;
                 description "Packet count";
               }
               leaf byte-count {
                 type uint64;
                 description "Byte count";
               }
             }
             container l2ald-mac-source-address-statistics {
               description "MAC source address statistics";
               leaf packet-count {
                 type uint64;
                 description "Packet count";
               }
               leaf byte-count {
                 type uint64;
                 description "Byte count";
               }
             }
           }
         }
       }
     }
   }
   rpc get-satellite-control-bridge-interface {
     description "Show satellite bridge interfaces details";
     input {
       leaf verbosity_level {
         default "brief";
         type enumeration {
           enum "brief" {
             description "Display brief output (default)";
           }
           enum "detail" {
             description "Display detailed output";
           }
           enum "extensive" {
             description "Display extensive output";
           }
         }
       }
       leaf interface-name {
         description "Name of bridge logical interface";
         type interface-unit;
       }
       leaf fpc {
         description "FPC slot number";
         type uint32 {
           range "65 .. 254";
         }
       }
     }
   }
   rpc get-satellite-device-db {
     description "Show satellite device information";
     input {
       leaf verbosity_level {
         default "brief";
         type enumeration {
           enum "brief" {
             description "Display brief output (default)";
           }
           enum "detail" {
             description "Display detailed output";
           }
           enum "extensive" {
             description "Display extensive output";
           }
         }
       }
       leaf device-id {
         description "Device ID";
         type int32;
       }
     }
   }
   rpc get-satellite-control-history-information {
     description "Show satellite bridge event information";
     input {
       leaf verbosity_level {
         default "brief";
         type enumeration {
           enum "brief" {
             description "Display brief output (default)";
           }
           enum "detail" {
             description "Display detailed output";
           }
         }
       }
     }
   }
   rpc get-satellite-control-logging-information {
     description "Show the internal logging information";
     input {
       leaf verbosity_level {
         default "brief";
         type enumeration {
           enum "brief" {
             description "Display brief output (default)";
           }
           enum "detail" {
             description "Display detailed output";
           }
         }
       }
     }
   }
   rpc get-satellite-control-bridge-summary {
     description "Show bridge summary";
     input {
       leaf verbosity_level {
         default "brief";
         type enumeration {
           enum "brief" {
             description "Display brief output (default)";
           }
           enum "detail" {
             description "Display detailed output";
           }
           enum "extensive" {
             description "Display extensive output";
           }
         }
       }
     }
   }
 }
