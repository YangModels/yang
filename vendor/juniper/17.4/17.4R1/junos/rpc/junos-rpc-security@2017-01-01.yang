/*
 * Copyright (c) 2017 Juniper Networks, Inc.
 * All rights reserved.
 */
 module junos-rpc-security {
   namespace "http://yang.juniper.net/junos/rpc/security";

   prefix security;

   import junos-common-types {
     prefix jt;
   }

   organization "Juniper Networks, Inc.";

   contact "yang-support@juniper.net";

   description "Junos RPC YANG module for security command(s)";

   revision 2017-01-01 {
     description "Junos: 17.4R1.16";
   }

   rpc get-security-alarm-information {
     description "Show active security alarm information";
     input {
       leaf alarm-id {
         description "Alarm ID filter";
         type union {
           type uint32;
           type string {
             pattern "<.*>|$.*";
           }
         }
       }
       leaf-list alarm-type {
         description "Alarm type filter";
         type enumeration {
           enum "authentication" {
             description "Authentication alarms";
           }
           enum "cryptographic-self-test" {
             description "Cryptographic self-test alarms";
           }
           enum "decryption-failures" {
             description "Decryption failure alarms";
           }
           enum "encryption-failures" {
             description "Encryption failure alarms";
           }
           enum "ike-phase1-failures" {
             description "IKE Phase 1 failure alarms";
           }
           enum "ike-phase2-failures" {
             description "IKE Phase 2 failure alarms";
           }
           enum "key-generation-self-test" {
             description "Key generation self-test alarms";
           }
           enum "non-cryptographic-self-test" {
             description "Non-cryptographic self-test alarms";
           }
           enum "policy" {
             description "Policy alarms";
           }
           enum "replay-attacks" {
             description "Replay attack alarms";
           }
           enum "idp" {
             description "IDP attack alarms";
           }
         }
       }
       leaf newer-than {
         description "Alarms newer than filter (YYYY-MM-DD.HH:MM:SS)";
         type jt:time;
       }
       leaf older-than {
         description "Alarms older than filter (YYYY-MM-DD.HH:MM:SS)";
         type jt:time;
       }
       leaf process {
         description "Process that generated the alarm filter";
         type string;
       }
       leaf severity {
         description "Severity of the alarm filter";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf style {
         type enumeration {
           enum "detail" {
             description "Show detail alarm information";
           }
         }
       }
     }
     output {
       choice output_c {
         case output-tag {
           leaf output {
             type string;
           }
         }
         case actual-tag {
           anyxml security-alarm-information;
         }
         case multichassis-tag {
           anyxml multi-routing-engine-results;
         }
       }
     }
   }
   rpc get-security-log-information {
     description "Show auditable security log information";
     input {
       leaf destination-address {
         description "Destination address and optional prefix length";
         type jt:ipprefix-optional;
       }
       leaf destination-port {
         description "Destination port";
         type union {
           type uint32;
           type string {
             pattern "<.*>|$.*";
           }
         }
       }
       leaf event-id {
         description "Event ID filter";
         type string;
       }
       leaf interface-name {
         description "Name of interface";
         type string;
       }
       leaf older-than {
         description "Events older than filter (YYYY-MM-DD.HH:MM:SS)";
         type jt:time;
       }
       leaf policy-name {
         description "Policy name filter";
         type string;
       }
       leaf process {
         description "Process that generated the event";
         type string;
       }
       leaf protocol {
         description "Protocol filter";
         type string;
       }
       leaf newer-than {
         description "Events newer than filter (YYYY-MM-DD.HH:MM:SS)";
         type jt:time;
       }
       leaf result {
         type enumeration {
           enum "failure" {
             description "Event was a failure";
           }
           enum "success" {
             description "Event was successful";
           }
         }
       }
       leaf severity {
         description "Severity of the event";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf source-address {
         description "Source address and optional prefix length";
         type jt:ipprefix-optional;
       }
       leaf source-port {
         description "Source port";
         type union {
           type uint32;
           type string {
             pattern "<.*>|$.*";
           }
         }
       }
       leaf username {
         description "Username filter";
         type string;
       }
       leaf sort-by {
         description "Sort by selected field";
         default "time";
         type enumeration {
           enum "destination-address" {
             description "Sort by destination address";
           }
           enum "destination-port" {
             description "Sort by destination port";
           }
           enum "interface-name" {
             description "Sort by interface name";
           }
           enum "policy-name" {
             description "Sort by policy name";
           }
           enum "protocol" {
             description "Sort by protocol";
           }
           enum "source-address" {
             description "Sort by source address";
           }
           enum "source-port" {
             description "Sort by source port";
           }
           enum "time" {
             description "Sort by time of event arrival";
           }
           enum "username" {
             description "Sort by event user name ";
           }
         }
       }
       leaf direction {
         default "ascending";
         type enumeration {
           enum "ascending" {
             description "Sort in ascending order";
           }
           enum "descending" {
             description "Sort in descending order";
           }
         }
       }
       leaf style {
         type enumeration {
           enum "detail" {
             description "Show detail alarm information";
           }
         }
       }
     }
     output {
       choice output_c {
         case output-tag {
           leaf output {
             type string;
           }
         }
         case actual-tag {
           anyxml security-log-information;
         }
         case multichassis-tag {
           anyxml multi-routing-engine-results;
         }
       }
     }
   }
   rpc get-hakr-keychain-information {
     description "Show all protocols keychain";
     input {
       leaf verbosity {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml hakr-keychain-information;
         }
         case multichassis-tag {
           anyxml multi-routing-engine-results;
         }
       }
     }
   }
   rpc get-pki-certificate-request {
     description "Show PKCS-10 certificate request information";
     input {
       uses command-forwarding;
       leaf certificate-id {
         description "Certificate identifier";
         type string {
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-pki-ca-certificate {
     description "Show certificate-authority certificate information";
     input {
       uses command-forwarding;
       choice ca-cert-choice {
         case ca-profile {
           leaf ca-profile {
             description "Certificate authority profile";
             type string {
             }
           }
         }
         case ca-profile-group {
           leaf ca-profile-group {
             description "Show CA profile group";
             type string {
             }
           }
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-pki-local-certificate {
     description "Show router certificate information";
     input {
       uses command-forwarding;
       choice certificate-choice {
         case certificate-id {
           leaf certificate-id {
             description "Certificate identifier";
             type string {
             }
           }
         }
         case system-generated {
           leaf system-generated {
             description "Autogenerated self-signed certificate";
             type empty;
           }
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-pki-crl {
     description "Show certificate revocation list information";
     input {
       uses command-forwarding;
       leaf ca-profile {
         description "Certificate authority profile";
         type string {
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pkid-crl-information-list;
         }
         case multichassis-tag {
           anyxml multi-routing-engine-results;
         }
       }
     }
   }
   rpc get-idp-application-system-cache {
     description "Show IDP application system cache";
     output {
       choice output_c {
         case output-tag {
           leaf output {
             type string;
           }
         }
         case actual-tag {
           anyxml idp-application-system-cache-information;
         }
         case multichassis-tag {
           anyxml multi-routing-engine-results;
         }
       }
     }
   }
   rpc get-idp-active-policy {
     description "Show active IDP policy";
     status deprecated;
     output {
       choice output_c {
         case output-tag {
           leaf output {
             type string;
           }
         }
         case actual-tag {
           anyxml idp-version-information;
         }
         case multichassis-tag {
           anyxml multi-routing-engine-results;
         }
       }
     }
   }
   rpc get-idp-policy-commit-status {
     description "Show the status of ongoing policy compilation and load";
     input {
       uses command-forwarding;
       choice re-selector-idpd {
         case re0 {
         }
         case re1 {
         }
       }
       leaf clear {
         description "Clears the policy commit status";
         type empty;
       }
     }
     output {
       choice output_c {
         case output-tag {
           leaf output {
             type string;
           }
         }
         case actual-tag {
           anyxml idp-policy-commit-status;
         }
         case multichassis-tag {
           anyxml multi-routing-engine-results;
         }
       }
     }
   }
   rpc get-idp-security-package-information {
     description "Show the version of currently installed security-package";
     input {
       uses command-forwarding;
       choice re-selector-idpd {
         case re0 {
         }
         case re1 {
         }
       }
     }
     output {
       choice output_c {
         case output-tag {
           leaf output {
             type string;
           }
         }
         case actual-tag {
           anyxml idp-security-package-information;
         }
         case multichassis-tag {
           anyxml multi-routing-engine-results;
         }
       }
     }
   }
   rpc get-idp-recent-security-package-information {
     description "List ten most recent security package versions";
     input {
       uses command-forwarding;
       choice re-selector-idpd {
         case re0 {
         }
         case re1 {
         }
       }
     }
     output {
       choice output_c {
         case output-tag {
           leaf output {
             type string;
           }
         }
         case actual-tag {
           anyxml idp-recent-security-package-information;
         }
         case multichassis-tag {
           anyxml multi-routing-engine-results;
         }
       }
     }
   }
   rpc get-idp-memory-information {
     description "Show IDP data plane memory statistics";
     output {
       choice output_c {
         case output-tag {
           leaf output {
             type string;
           }
         }
         case actual-tag {
           anyxml idp-memory-information;
         }
         case multichassis-tag {
           anyxml multi-routing-engine-results;
         }
       }
     }
   }
   rpc get-idp-subscriber-policy-list {
     description "Show the list of currently installed policies";
     output {
       choice output_c {
         case output-tag {
           leaf output {
             type string;
           }
         }
         case actual-tag {
           anyxml idp-subscriber-policy-list;
         }
         case multichassis-tag {
           anyxml multi-routing-engine-results;
         }
       }
     }
   }
   rpc get-idp-policy-template-information {
     description "Show available policy templates";
     output {
       choice output_c {
         case output-tag {
           leaf output {
             type string;
           }
         }
         case actual-tag {
           anyxml idp-policy-template-information;
         }
         case multichassis-tag {
           anyxml multi-routing-engine-results;
         }
       }
     }
   }
   rpc get-idp-status-information {
     description "Show IDP status";
     output {
       choice output_c {
         case output-tag {
           leaf output {
             type string;
           }
         }
         case actual-tag {
           anyxml idp-status-information;
         }
         case multichassis-tag {
           anyxml multi-routing-engine-results;
         }
       }
     }
   }
   rpc get-idp-detail-status-information {
     description "Show IDP detail status";
     output {
       choice output_c {
         case output-tag {
           leaf output {
             type string;
           }
         }
         case actual-tag {
           anyxml idp-detail-status-information;
         }
         case multichassis-tag {
           anyxml multi-routing-engine-results;
         }
       }
     }
   }
   rpc get-idp-predefined-attack-groups {
     description "Show predefined attack groups";
     output {
       choice output_c {
         case output-tag {
           leaf output {
             type string;
           }
         }
         case actual-tag {
           anyxml idp-predefined-attack-groups;
         }
         case multichassis-tag {
           anyxml multi-routing-engine-results;
         }
       }
     }
   }
   rpc get-idp-predefined-attack-group-filters {
     description "Configure filters";
     input {
       uses command-forwarding;
       choice re-selector-idpd {
         case re0 {
         }
         case re1 {
         }
       }
       leaf category {
         description "Category of attack group";
         type string;
       }
     }
     output {
       choice output_c {
         case output-tag {
           leaf output {
             type string;
           }
         }
         case actual-tag {
           anyxml idp-predefined-attack-group-filters;
         }
         case multichassis-tag {
           anyxml multi-routing-engine-results;
         }
       }
     }
   }
   rpc get-idp-predefined-attacks {
     description "Show predefined attacks";
     output {
       choice output_c {
         case output-tag {
           leaf output {
             type string;
           }
         }
         case actual-tag {
           anyxml idp-predefined-attacks;
         }
         case multichassis-tag {
           anyxml multi-routing-engine-results;
         }
       }
     }
   }
   rpc get-idp-predefined-attack-filters {
     description "Configure filters";
     input {
       uses command-forwarding;
       choice re-selector-idpd {
         case re0 {
         }
         case re1 {
         }
       }
       leaf category {
         description "Category of attack";
         type string;
       }
       leaf severity {
         description "Severity of attack";
         type enumeration {
           enum "info" {
             description "Provide information of attack when it matches";
           }
           enum "warning" {
             description "The attack is a minor one";
           }
           enum "minor" {
             description "The attack is a minor one";
           }
           enum "major" {
             description "The attack is a major one";
           }
           enum "critical" {
             description "The attack is a critical one";
           }
         }
       }
       leaf direction {
         description "Direction of attack";
         type enumeration {
           enum "client-to-server" {
             description "Select attacks from client to server";
           }
           enum "server-to-client" {
             description "Select attacks from server to client";
           }
           enum "any" {
             description "Select attacks which are in any direction";
           }
           enum "exclude-client-to-server" {
             description "Filter out attacks from client to server";
           }
           enum "exclude-server-to-client" {
             description "Filter out attacks from server to client";
           }
           enum "exclude-any" {
             description "Filter out attacks which are in any direction";
           }
         }
       }
     }
     output {
       choice output_c {
         case output-tag {
           leaf output {
             type string;
           }
         }
         case actual-tag {
           anyxml idp-predefined-attack-filters;
         }
         case multichassis-tag {
           anyxml multi-routing-engine-results;
         }
       }
     }
   }
   rpc get-idp-counter-information {
     description "Show IDP counters";
     output {
       choice output_c {
         case output-tag {
           leaf output {
             type string;
           }
         }
         case actual-tag {
           anyxml idp-counter-information;
         }
         case multichassis-tag {
           anyxml multi-routing-engine-results;
         }
       }
     }
   }
   rpc get-idp-counters-packet {
     description "Show IDP Packet counters";
     output {
       leaf output {
         type string;
       }
     }
   }
   rpc get-idp-counters-tcp-reass {
     description "Show IDP Reassembler counters";
     output {
       leaf output {
         type string;
       }
     }
   }
   rpc get-idp-counters-ips {
     description "Show IPS counters";
     output {
       leaf output {
         type string;
       }
     }
   }
   rpc get-idp-counters-flow {
     description "Show IDP Flow counters";
     output {
       leaf output {
         type string;
       }
     }
   }
   rpc get-idp-counters-dfa {
     description "Show IDP DFA counters";
     output {
       leaf output {
         type string;
       }
     }
   }
   rpc get-idp-counters-log {
     description "Show IDP Log counters";
     output {
       leaf output {
         type string;
       }
     }
   }
   rpc get-idp-counters-pol-mngr {
     description "Show IDP Policy counters";
     output {
       leaf output {
         type string;
       }
     }
   }
   rpc get-idp-counters-packet-log {
     description "Show IDP Packet capture counters";
     output {
       leaf output {
         type string;
       }
     }
   }
   rpc get-idp-counters-appid {
     description "Show Application Identification counters";
     output {
       leaf output {
         type string;
       }
     }
   }
   rpc get-idp-counters-memory {
     description "Show IDP memory counters";
     output {
       leaf output {
         type string;
       }
     }
   }
   rpc get-idp-counters-action {
     description "Show IDP policy action counters";
     output {
       leaf output {
         type string;
       }
     }
   }
   rpc get-idp-counters-pdf-decoder {
     description "Show the PDF decoder counters";
     output {
       leaf output {
         type string;
       }
     }
   }
   rpc get-idp-counters-http-decoder {
     description "Show the HTTP decoder counters";
     output {
       leaf output {
         type string;
       }
     }
   }
   rpc get-idp-applications-information {
     description "Show IDP application statistics";
     output {
       choice output_c {
         case output-tag {
           leaf output {
             type string;
           }
         }
         case actual-tag {
           anyxml idp-applications-information;
         }
         case multichassis-tag {
           anyxml multi-routing-engine-results;
         }
       }
     }
   }
   rpc get-idp-attack-table-information {
     description "Show IDP attack table";
     output {
       choice output_c {
         case output-tag {
           leaf output {
             type string;
           }
         }
         case actual-tag {
           anyxml idp-attack-table-information;
         }
         case multichassis-tag {
           anyxml multi-routing-engine-results;
         }
       }
     }
   }
   rpc get-idp-attack-description-information {
     description "Show description of specified attack";
     input {
       leaf attack-name {
         description "Attack name";
         type string;
         mandatory true;
       }
     }
     output {
       choice output_c {
         case output-tag {
           leaf output {
             type string;
           }
         }
         case actual-tag {
           anyxml idp-attack-description-information;
         }
         case multichassis-tag {
           anyxml multi-routing-engine-results;
         }
       }
     }
   }
   rpc get-idp-attack-detail-information {
     description "Show details of specified attack";
     input {
       leaf attack-name {
         description "Attack name";
         type string;
         mandatory true;
       }
     }
     output {
       choice output_c {
         case output-tag {
           leaf output {
             type string;
           }
         }
         case actual-tag {
           anyxml idp-attack-detail-information;
         }
         case multichassis-tag {
           anyxml multi-routing-engine-results;
         }
       }
     }
   }
   rpc get-mka-session-information {
     description "Show MKA sessions information";
     output {
       choice output_c {
         case output-tag {
           leaf output {
             type string;
           }
         }
         case actual-tag {
           anyxml mka-session-information;
         }
         case multichassis-tag {
           anyxml multi-routing-engine-results;
         }
       }
     }
   }
   rpc get-mka-session-interface-information {
     description "Show MKA session on this interface";
     input {
       leaf interface-name {
         description "Show MKA session for this interface";
         default "all";
         type union {
           type jt:interface-name;
           type string {
             pattern "<.*>|$.*";
           }
         }
       }
     }
     output {
       choice output_c {
         case output-tag {
           leaf output {
             type string;
           }
         }
         case actual-tag {
           anyxml mka-session-interface-information;
         }
         case multichassis-tag {
           anyxml multi-routing-engine-results;
         }
       }
     }
   }
   rpc get-mka-statistics {
     description "Show MKA statistics";
     output {
       choice output_c {
         case output-tag {
           leaf output {
             type string;
           }
         }
         case actual-tag {
           anyxml mka-statistics;
         }
         case multichassis-tag {
           anyxml multi-routing-engine-results;
         }
       }
     }
   }
   rpc get-mka-interface-statistics {
     description "Show MKA statistics on this interface";
     input {
       leaf interface-name {
         description "Show MKA statistics for this interface";
         default "all";
         type union {
           type jt:interface-name;
           type string {
             pattern "<.*>|$.*";
           }
         }
       }
     }
     output {
       choice output_c {
         case output-tag {
           leaf output {
             type string;
           }
         }
         case actual-tag {
           anyxml mka-interface-statistics;
         }
         case multichassis-tag {
           anyxml multi-routing-engine-results;
         }
       }
     }
   }
   rpc get-macsec-connection-information {
     description "Show MAC Security connections information";
     output {
       choice output_c {
         case output-tag {
           leaf output {
             type string;
           }
         }
         case actual-tag {
           anyxml macsec-connection-information;
         }
         case multichassis-tag {
           anyxml multi-routing-engine-results;
         }
       }
     }
   }
   rpc get-macsec-connection-interface-information {
     description "Show MAC security connections on this interface";
     input {
       leaf interface-name {
         description "Show MAC security connections for this interface";
         default "all";
         type union {
           type jt:interface-name;
           type string {
             pattern "<.*>|$.*";
           }
         }
       }
     }
     output {
       choice output_c {
         case output-tag {
           leaf output {
             type string;
           }
         }
         case actual-tag {
           anyxml macsec-connection-interface-information;
         }
         case multichassis-tag {
           anyxml multi-routing-engine-results;
         }
       }
     }
   }
   rpc get-macsec-statistics {
     description "Show MAC Security statistics";
     input {
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml macsec-statistics;
         }
         case multichassis-tag {
           anyxml multi-routing-engine-results;
         }
       }
     }
   }
   rpc get-macsec-interface-statistics {
     description "Show MAC security statistics on this interface";
     input {
       leaf verbosity_level {
         default "brief";
         type enumeration {
           enum "brief" {
             description "Display brief output (default)";
           }
           enum "detail" {
             description "Display detailed output";
           }
         }
       }
       leaf interface-name {
         description "Show MAC security statistics for this interface";
         default "all";
         type union {
           type jt:interface-name;
           type string {
             pattern "<.*>|$.*";
           }
         }
       }
     }
     output {
       choice output_c {
         case output-tag {
           leaf output {
             type string;
           }
         }
         case actual-tag {
           anyxml macsec-interface-statistics;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
