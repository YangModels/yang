/*
 * Copyright (c) 2017 Juniper Networks, Inc.
 * All rights reserved.
 */
 module junos-ex-conf-chassis {
   namespace "http://yang.juniper.net/junos-ex/conf/chassis";

   prefix jc-chassis;

   import junos-common-ddl-extensions {
     prefix junos;
   }

   import junos-common-types {
     prefix jt;
   }

   import junos-ex-conf-root {
     prefix jc;
   }

   organization "Juniper Networks, Inc.";

   contact "yang-support@juniper.net";

   description "Junos chassis configuration module";

   revision 2017-01-01 {
     description "Junos: 17.4R1.16";
   }

   augment /jc:configuration {
     uses chassis-group;
   }
   augment /jc:configuration/jc:groups {
     uses chassis-group;
   }
   grouping chassis-group {
     container chassis {
       description "Chassis configuration";
       uses chassis_type;
     }
   }
   grouping chassis_type {
     uses apply-advanced;
     container nssu {
       presence "enable nssu";
       description "Nonstop Software Upgrade settings";
       uses apply-advanced;
       list upgrade-group {
         key name;
         ordered-by user;
         description "Nonstop Software Upgrade group";
         leaf name {
           type string {
             length "1 .. 254";
           }
         }
         uses apply-advanced;
         leaf-list fpcs {
           description "FPCs associated with update-group";
           type union {
             type string {
               pattern "<.*>|$.*";
             }
             type uint32;
           }
           max-elements 16;
         }
         list member {
           key name;
           description "Member of virtual chassis configuration";
           uses upgrade-group-fpcs;
         }
       }
       leaf rcp-count {
         description "Parallel rcp count";
         type union {
           type string {
             pattern "<.*>|$.*";
           }
           type int32 {
             range "1 .. 8";
           }
         }
       }
     }
     container psu {
       description "Power Supply Unit redundancy configuration";
       uses apply-advanced;
       container redundancy {
         description "PSU Redundancy settings";
         uses apply-advanced;
         leaf n-plus-n {
           description "PSU redundancy: N+N configuration";
           type empty;
         }
       }
     }
     leaf craft-lockout {
       description "Disable craft interface input";
       type empty;
     }
     choice source-route-choice {
       leaf source-route {
         description "Enable IP source-route processing";
         status deprecated;
         type empty;
       }
       leaf no-source-route {
         description "Don't enable IP source-route processing";
         status deprecated;
         type empty;
       }
     }
     choice packet-scheduling-choice {
       leaf packet-scheduling {
         description "Enable DX2.0 packet scheduling";
         type empty;
       }
       leaf no-packet-scheduling {
         description "Don't enable DX2.0 packet scheduling";
         type empty;
       }
     }
     leaf vrf-mtu-check {
       description "Enable Internet Processor II-based MTU check";
       type empty;
     }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
       }
     }
     container redundancy {
       description "Redundancy settings";
       uses chassis_redundancy_type;
     }
     container routing-engine {
       description "Routing Engine settings";
       uses chassis_routing_engine_type;
     }
     container aggregated-devices {
       description "Aggregated devices configuration";
       uses chassis_agg_dev_type;
     }
     list disk-partition {
       key name;
       ordered-by user;
       description "Chassis disk monitor configuration";
       leaf name {
         description "Choose disk partition to monitor";
         type enumeration {
           enum "/var" {
             description "Monitor /var partition";
           }
           enum "/config" {
             description "Monitor /config partition";
           }
         }
       }
       uses apply-advanced;
       list level {
         key name;
         ordered-by user;
         description "Threshold level";
         leaf name {
           type enumeration {
             enum "high" {
               description "Set high level of threshold";
             }
             enum "full" {
               description "Set full level of threshold";
             }
           }
         }
         uses apply-advanced;
         container free-space {
           description "Enter threshold value & choose the metric";
           leaf thres-free {
             description "Enter free space threshold value";
             type union {
               type string {
                 pattern "<.*>|$.*";
               }
               type uint32 {
                 range "0 .. 100";
               }
             }
           }
           choice thres-metric {
             case case_1 {
               leaf percent {
                 description "Free space threshold in %";
                 type empty;
               }
             }
             case case_2 {
               leaf mb {
                 description "Free space threshold in MB";
                 type empty;
               }
             }
           }
         }
       }
     }
     container container-devices {
       description "Container devices configuration";
       uses chassisd_agg_container_type;
     }
     container pseudowire-service {
       description "Pseudowire L3 termination device configuration";
       uses chassis-pw-type;
     }
     container provider-instance-devices {
       description "Provider instance devices configuration";
       uses chassisd_provider_instance_type;
     }
     container fabric {
       description "Switch fabric settings";
       uses chassis_fabric_type;
     }
     list fpc {
       key name;
       description "Flexible PIC Concentrator parameters";
       junos:must "((!(any \". <*> vpn-localization\") || !(\"virtual-chassis\")))";
       junos:must-message "vpn-localization cannot be configured on virtual-chassis";
       uses chassis_fpc_type;
     }
     container fpc-feb-connectivity {
       description "Connectivity between Flexible PIC Concentrators and Forwarding Engine Boards";
       uses apply-advanced;
       list fpc {
         key name;
         leaf name {
           description "FPC slot number";
           type union {
             type string {
               pattern "<.*>|$.*";
             }
             type uint32;
           }
         }
         uses apply-advanced;
         container feb {
           description "FEB slot number";
           choice feb-slot-choice {
             case case_1 {
               leaf none {
                 description "FPC not connected to any FEB";
                 type empty;
               }
             }
             case case_2 {
               leaf feb-slot {
                 description "FEB slot number";
                 type union {
                   type string {
                     pattern "<.*>|$.*";
                   }
                   type uint32;
                 }
               }
             }
           }
         }
       }
     }
     container sib {
       description "Switch Interface Board parameters";
       uses chassis_sib_type;
     }
     container tfeb {
       description "Taz Forwarding Engine Board parameters";
       uses chassis_feb_type;
     }
     container alarm {
       description "Global alarm settings";
       uses chassis_alarm_type;
     }
     leaf slow-pfe-alarm {
       description "Enable slow (potential) PFE alarm";
       type empty;
     }
     leaf network-services {
       description "Chassis network services configuration";
       type enumeration {
         enum "ip" {
           description "IP network services";
         }
         enum "ethernet" {
           description "Ethernet network services";
           junos:must "((!(any \"interfaces <*> unit <*> family inet accounting source-class-usage\") && (!(any \"interfaces <*> unit <*> family inet accounting destination-class-usage\") && (!(any \"interfaces <*> unit <*> family inet6 accounting source-class-usage\") && (!(any \"interfaces <*> unit <*> family inet6 accounting destination-class-usage\") && (!(any \"logical-systems <*> interfaces <*> unit <*> family inet accounting source-class-usage\") && (!(any \"logical-systems <*> interfaces <*> unit <*> family inet accounting destination-class-usage\") && (!(any \"logical-systems <*> interfaces <*> unit <*> family inet6 accounting source-class-usage\") && !(any \"logical-systems <*> interfaces <*> unit <*> family inet6 accounting destination-class-usage\")))))))))";
           junos:must-message "Cannot configure 'accounting source-class-usage or destination-class-usage' under network-services ethernet";
           junos:must "((!(\"routing-options forwarding-table unicast-reverse-path\") && (!(any \"routing-instances <*> routing-options forwarding-table unicast-reverse-path\") && (!(any \"logical-systems <*> routing-options forwarding-table unicast-reverse-path\") && !(any \"logical-systems <*> routing-instances <*> routing-options forwarding-table unicast-reverse-path\")))))";
           junos:must-message "Cannot configure 'unicast-reverse-path' under network-services ethernet";
           junos:must "((!(any \"interfaces <*> unit <*> family inet rpf-check\") && (!(any \"interfaces <*> unit <*> family inet6 rpf-check\") && (!(any \"logical-systems <*> interfaces <*> unit <*> family inet rpf-check\") && !(any \"logical-systems <*> interfaces <*> unit <*> family inet6 rpf-check\")))))";
           junos:must-message "Cannot configure 'rpf-check' under network-services ethernet";
           junos:must "((!(any \"policy-options policy-statement <*> then source-class\") && (!(any \"policy-options policy-statement <*> term <*> then source-class\") && (!(any \"policy-options policy-statement <*> then destination-class\") && (!(any \"policy-options policy-statement <*> term <*> then destination-class\") && (!(any \"policy-options policy-statement <*> from route-filter <*> <*>  source-class\") && (!(any \"policy-options policy-statement <*> term <*> from route-filter <*> <*>  source-class\") && (!(any \"policy-options policy-statement <*> from route-filter <*> <*> destination-class\") && (!(any \"policy-options policy-statement <*> term <*> from route-filter <*> <*>  destination-class\") && (!(any \"logical-systems <*> policy-options policy-statement <*> then source-class\") && (!(any \"logical-systems <*> policy-options policy-statement <*> term <*> then source-class\") && (!(any \"logical-systems <*> policy-options policy-statement <*> then destination-class\") && (!(any \"logical-systems <*> policy-options policy-statement <*> term <*> then destination-class\") && (!(any \"logical-systems <*> policy-options policy-statement <*> from route-filter <*> <*>  source-class\") && (!(any \"logical-systems <*> policy-options policy-statement <*> term <*> from route-filter <*> <*>  source-class\") && (!(any \"logical-systems <*> policy-options policy-statement <*> from route-filter <*> <*> destination-class\") && !(any \"logical-systems <*> policy-options policy-statement <*> term <*> from route-filter <*> <*>  destination-class\")))))))))))))))))";
           junos:must-message "Cannot configure 'destination-class|source-class' under network-services ethernet";
           junos:must "((!(\"protocols bgp family inet any\") && (!(\"protocols bgp family inet flow\") && (!(\"protocols bgp family inet multicast\") && (!(any \"protocols bgp group <*> family inet any\") && (!(any \"protocols bgp group <*> family inet flow\") && (!(any \"protocols bgp group <*> family inet multicast\") && (!(any \"protocols bgp group <*> neighbor <*> family inet any\") && (!(any \"protocols bgp group <*> neighbor <*> family inet flow\") && (!(any \"protocols bgp group <*> neighbor <*> family inet multicast\") && (!(\"protocols bgp family inet-vpn any\") && (!(\"protocols bgp family inet-vpn flow\") && (!(\"protocols bgp family inet-vpn multicast\") && (!(any \"protocols bgp group <*> family inet-vpn any\") && (!(any \"protocols bgp group <*> family inet-vpn flow\") && (!(any \"protocols bgp group <*> family inet-vpn multicast\") && (!(any \"protocols bgp group <*> neighbor <*> family inet-vpn any\") && (!(any \"protocols bgp group <*> neighbor <*> family inet-vpn flow\") && (!(any \"protocols bgp group <*> neighbor <*> family inet-vpn multicast\") && (!(\"protocols bgp family inet6\") && (!(any \"protocols bgp group <*> family inet6\") && (!(any \"protocols bgp group <*> neighbor <*> family inet6\") && (!(\"protocols bgp family inet6-vpn\") && (!(any \"protocols bgp group <*> family inet6-vpn\") && (!(any \"protocols bgp group <*> neighbor <*> family inet6-vpn\") && (!(\"protocols bgp family inet-mvpn\") && (!(any \"protocols bgp group <*> family inet-mvpn\") && (!(any \"protocols bgp group <*> neighbor <*> family inet-mvpn\") && (!(\"protocols bgp family inet6-mvpn\") && (!(any \"protocols bgp group <*> family inet6-mvpn\") && (!(any \"protocols bgp group <*> neighbor <*> family inet6-mvpn\") && (!(\"protocols bgp family iso\") && (!(any \"protocols bgp group <*> family iso\") && (!(any \"protocols bgp group <*> neighbor <*> family iso\") && (!(\"protocols bgp family iso-vpn\") && (!(any \"protocols bgp group <*> family iso-vpn\") && (!(any \"protocols bgp group <*> neighbor <*> family iso-vpn\") && (!(\"protocols bgp family atmvpn\") && (!(any \"protocols bgp group <*> family atmvpn\") && (!(any \"protocols bgp group <*> neighbor <*> family atmvpn\") && (!(any \"logical-systems <*> protocols bgp family inet any\") && (!(any \"logical-systems <*> protocols bgp family inet flow\") && (!(any \"logical-systems <*> protocols bgp family inet multicast\") && (!(any \"logical-systems <*> protocols bgp group <*> family inet any\") && (!(any \"logical-systems <*> protocols bgp group <*> family inet flow\") && (!(any \"logical-systems <*> protocols bgp group <*> family inet multicast\") && (!(any \"logical-systems <*> protocols bgp group <*> neighbor <*> family inet any\") && (!(any \"logical-systems <*> protocols bgp group <*> neighbor <*> family inet flow\") && (!(any \"logical-systems <*> protocols bgp group <*> neighbor <*> family inet multicast\") && (!(any \"logical-systems <*> protocols bgp family inet-vpn any\") && (!(any \"logical-systems <*> protocols bgp family inet-vpn flow\") && (!(any \"logical-systems <*> protocols bgp family inet-vpn multicast\") && (!(any \"logical-systems <*> protocols bgp group <*> family inet-vpn any\") && (!(any \"logical-systems <*> protocols bgp group <*> family inet-vpn flow\") && (!(any \"logical-systems <*> protocols bgp group <*> family inet-vpn multicast\") && (!(any \"logical-systems <*> protocols bgp group <*> neighbor <*> family inet-vpn any\") && (!(any \"logical-systems <*> protocols bgp group <*> neighbor <*> family inet-vpn flow\") && (!(any \"logical-systems <*> protocols bgp group <*> neighbor <*> family inet-vpn multicast\") && (!(any \"logical-systems <*> protocols bgp family inet6\") && (!(any \"logical-systems <*> protocols bgp group <*> family inet6\") && (!(any \"logical-systems <*> protocols bgp group <*> neighbor <*> family inet6\") && (!(any \"logical-systems <*> protocols bgp family inet6-vpn\") && (!(any \"logical-systems <*> protocols bgp group <*> family inet6-vpn\") && (!(any \"protocols bgp group <*> neighbor <*> family inet6-vpn\") && (!(any \"logical-systems <*> protocols bgp family inet-mvpn\") && (!(any \"logical-systems <*> protocols bgp group <*> family inet-mvpn\") && (!(any \"protocols bgp group <*> neighbor <*> family inet-mvpn\") && (!(any \"logical-systems <*> protocols bgp family inet6-mvpn\") && (!(any \"logical-systems <*> protocols bgp group <*> family inet6-mvpn\") && (!(any \"logical-systems <*> protocols bgp group <*> neighbor <*> family inet6-mvpn\") && (!(any \"logical-systems <*> protocols bgp family iso\") && (!(any \"logical-systems <*> protocols bgp group <*> family iso\") && (!(any \"protocols bgp group <*> neighbor <*> family iso\") && (!(any \"logical-systems <*> protocols bgp family iso-vpn\") && (!(any \"logical-systems <*> protocols bgp group <*> family iso-vpn\") && (!(any \"logical-systems <*> protocols bgp group <*> neighbor <*> family iso-vpn\") && (!(any \"logical-systems <*> protocols bgp family atmvpn\") && (!(any \"logical-systems <*> protocols bgp group <*> family atmvpn\") && !(any \"protocols bgp group <*> neighbor <*> family atmvpn\")))))))))))))))))))))))))))))))))))))))))))))))))))))))))))))))))))))))))))))))";
           junos:must-message "Only BGP groups with 'family inet unicast, inet labeled-unicast, inet-vpn unicast, l2vpn and route-target' are supported under network-services ethernet";
         }
         enum "enhanced-ip" {
           description "Enhanced IP network services";
         }
         enum "enhanced-ethernet" {
           description "Enhanced ethernet network services";
         }
         enum "enhanced-mode" {
           description "Enhanced network services";
         }
         enum "lan" {
           description "Ethernet LAN services";
         }
       }
     }
     container usb {
       description "USB control flags";
       uses apply-advanced;
       container storage {
         description "USB storage flags";
         uses apply-advanced;
         leaf disable {
           description "Disable USB storage";
           type empty;
         }
       }
     }
     list lcc {
       key name;
       description "Line-card chassis configuration";
       leaf name {
         description "LCC number";
         type union {
           type string {
             pattern "<.*>|$.*";
           }
           type uint32;
         }
       }
       uses apply-advanced;
       list fpc {
         key name;
         description "Flexible PIC Concentrator parameters";
         junos:must "((!(any \". <*> vpn-localization\") || !(\"virtual-chassis\")))";
         junos:must-message "vpn-localization cannot be configured on virtual-chassis";
         uses chassis_fpc_type;
       }
       choice state {
         case case_1 {
           leaf online-expected {
             description "LCC is expected to be online";
             type empty;
           }
         }
         case case_2 {
           leaf offline {
             description "LCC is expected to be offline";
             type empty;
           }
         }
       }
     }
     container lcd {
       description "Chassis LCD";
       status deprecated;
       uses apply-advanced;
       list fpc {
         key name;
         ordered-by user;
         leaf name {
           description "FPC slot number";
           type union {
             type string {
               pattern "<.*>|$.*";
             }
             type uint32;
           }
         }
         choice menu-item {
           case case_1 {
             leaf maintenance-menu {
               description "LCD maintenance menu";
               type empty;
             }
           }
         }
         choice enable-disable {
           case case_1 {
             leaf disable {
               description "Disable maintenance-menu";
               type empty;
             }
           }
         }
       }
       choice menu-item {
         case case_1 {
           leaf maintenance-menu {
             description "LCD maintenance menu";
             type empty;
           }
         }
       }
       choice enable-disable {
         case case_1 {
           leaf disable {
             description "Disable maintenance-menu";
             type empty;
           }
         }
       }
     }
     container lcd-menu {
       junos:must "(!(\"..  lcd\"))";
       junos:must-message "Cannot mix 'lcd-menu' and 'lcd maintenance-menu' configurations";
       description "Chassis LCD menu";
       uses apply-advanced;
       list fpc {
         key name;
         ordered-by user;
         leaf name {
           description "FPC slot number";
           type union {
             type string {
               pattern "<.*>|$.*";
             }
             type uint32;
           }
         }
         uses apply-advanced;
         list menu-item {
           key name;
           ordered-by user;
           description "LCD menu item";
           leaf name {
             description "LCD menu name";
             type string;
           }
           leaf disable {
             description "Disable LCD menu";
             type empty;
           }
         }
       }
       list menu-item {
         key name;
         ordered-by user;
         description "LCD menu item";
         leaf name {
           description "LCD menu name";
           type string;
         }
         leaf disable {
           description "Disable LCD menu";
           type empty;
         }
       }
     }
     leaf fru-poweron-sequence {
       description "FRUs power on sequence like 0 1 2 3 ... within double quotes";
       type string {
         junos:posix-pattern "^[0-9 ]+$";
         junos:pattern-message "FRU in fru poweron sequence must be a number";
       }
     }
     leaf auto-image-upgrade {
       description "Auto image upgrade using DHCP";
       type empty;
     }
     container multicast-loadbalance {
       description "Multicast load balancing settings";
       uses chassis_ae_lb_type;
     }
     container oss-map {
       description "Translate Operation Supported System's requirements";
       uses apply-advanced;
       leaf model-name {
         description "Override chassis model name for specific show/snmp output";
         type enumeration {
           enum "t640" {
             description "Set to T640's model";
           }
           enum "t1600" {
             description "Set to T1600's model";
           }
         }
       }
     }
     list satellite {
       key name;
       ordered-by user;
       description "List of available satellite configurations";
       leaf name {
         description "Satellite name";
         type string {
           junos:posix-pattern "^[a-zA-Z0-9_-]{1,63}$";
           junos:pattern-message "Satellite name is a string consisting of up to 63 letters, numbers, dashes and underscores";
         }
       }
       uses apply-advanced;
     }
     container system-domains {
       presence "enable system-domains";
       description "Root and protected system domain configuration";
       uses apply-advanced;
       leaf root-domain-id {
         description "Root domain identifier";
         type union {
           type string {
             pattern "<.*>|$.*";
           }
           type uint32 {
             range "1 .. 3";
           }
         }
       }
       list protected-system-domains {
         key name;
         description "Protected system domain configuration";
         uses juniper-protected-system-domain;
       }
       container traceoptions {
         description "Protected system domain traceoptions";
         uses juniper-protected-system-domain-traceoptions;
       }
     }
   }
   grouping apply-advanced {
     description "Apply advanced configuration logic";
     leaf-list apply-groups {
       description "Groups from which to inherit configuration data";
       type string;
     }
     leaf-list apply-groups-except {
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping chassis-pw-type {
     uses apply-advanced;
     leaf device-count {
       description "Number of pseudo-wire ps devices";
       type union {
         type string {
           pattern "<.*>|$.*";
         }
         type uint32 {
           range "1 .. 7000";
         }
       }
     }
   }
   grouping chassis_ae_lb_type {
     uses apply-advanced;
     leaf disable {
       description "Disable Multicast load balancing";
       type empty;
     }
     leaf hash-mode {
       description "PFE hash mode";
       type enumeration {
         enum "crc-sgip" {
           description "CRC of Source IP and Group IP";
         }
         enum "crc-gip" {
           description "CRC of Group IP only";
         }
         enum "crc-sip" {
           description "CRC of Source IP only";
         }
         enum "simple-sgip" {
           description "Simple hash of Source IP and Group IP";
         }
         enum "simple-gip" {
           description "Simple hash of Group IP";
         }
         enum "simple-sip" {
           description "Simple hash of Source IP";
         }
         enum "balanced" {
           description "Round-Robin balancing";
         }
       }
     }
   }
   grouping chassis_agg_dev_type {
     uses apply-advanced;
     container ethernet {
       description "Aggregated device options for Ethernet";
       uses chassisd_agg_enet_type;
     }
     container sonet {
       description "Aggregated device options for SONET";
       uses chassisd_agg_pos_type;
     }
     leaf maximum-links {
       description "Maximum links limit for aggregated devices (16, 32, or 64)";
       type union {
         type int32;
         type string {
           pattern "<.*>|$.*";
         }
       }
     }
   }
   grouping chassis_alarm_type {
     uses apply-advanced;
     container management-ethernet {
       description "Management Ethernet alarms";
       uses chassis_alarm_ethernet_type;
     }
     container otn-odu {
       description "OTN ODU alarms";
       uses chassis_alarm_otn_odu_type;
     }
     container otn-otu {
       description "OTN OTU alarms";
       uses chassis_alarm_otn_otu_type;
     }
     container sonet {
       description "SONET alarms";
       uses chassis_alarm_sonet_type;
     }
     container t3 {
       description "DS3 alarms";
       uses chassis_alarm_ds3_type;
     }
     container ds1 {
       description "DS1 alarms";
       uses chassis_alarm_ds1_type;
     }
     container ethernet {
       description "Ethernet alarms";
       uses chassis_alarm_ethernet_type;
     }
     container integrated-services {
       description "Integrated services alarms";
       uses chassis_alarm_integrated_services_type;
     }
     container services {
       description "Services PIC alarms";
       uses chassis_alarm_services_type;
     }
     container serial {
       description "Serial alarms";
       uses chassis_alarm_serial_type;
     }
     container fibre-channel {
       description "Fibre Channel alarms";
       uses chassis_alarm_fibre-channel_type;
     }
   }
   grouping chassis_alarm_ds1_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ds3_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf exz {
       description "Excessive zeros";
       type enumeration {
         enum "red" {
           description "Assert red system alarm";
         }
         enum "yellow" {
           description "Assert yellow system alarm";
         }
         enum "ignore" {
           description "Do not assert any alarm signals";
         }
       }
     }
     leaf ferf {
       description "Far-end failure";
       type enumeration {
         enum "red" {
           description "Assert red system alarm";
         }
         enum "yellow" {
           description "Assert yellow system alarm";
         }
         enum "ignore" {
           description "Do not assert any alarm signals";
         }
       }
     }
     leaf idle {
       description "Idle alarm";
       type enumeration {
         enum "red" {
           description "Assert red system alarm";
         }
         enum "yellow" {
           description "Assert yellow system alarm";
         }
         enum "ignore" {
           description "Do not assert any alarm signals";
         }
       }
     }
     leaf lcv {
       description "Line code violation";
       type enumeration {
         enum "red" {
           description "Assert red system alarm";
         }
         enum "yellow" {
           description "Assert yellow system alarm";
         }
         enum "ignore" {
           description "Do not assert any alarm signals";
         }
       }
     }
     leaf lof {
       description "Loss of frame";
       type enumeration {
         enum "red" {
           description "Assert red system alarm";
         }
         enum "yellow" {
           description "Assert yellow system alarm";
         }
         enum "ignore" {
           description "Do not assert any alarm signals";
         }
       }
     }
     leaf los {
       description "Loss of signal";
       type enumeration {
         enum "red" {
           description "Assert red system alarm";
         }
         enum "yellow" {
           description "Assert yellow system alarm";
         }
         enum "ignore" {
           description "Do not assert any alarm signals";
         }
       }
     }
     leaf pll {
       description "Phase-locked loop out of lock";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ethernet_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_fibre-channel_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_integrated_services_type {
     uses apply-advanced;
     leaf failure {
       description "Integrated Services failure";
       type enumeration {
         enum "red" {
           description "Assert red system alarm";
         }
         enum "yellow" {
           description "Assert yellow system alarm";
         }
         enum "ignore" {
           description "Do not assert any alarm signals";
         }
       }
     }
   }
   grouping chassis_alarm_otn_odu_type {
     uses apply-advanced;
     leaf odu-bdi {
       description "ODU backward-defect-indicator, ODU-BDI failure";
       type enumeration {
         enum "red" {
           description "Assert red system alarm";
         }
         enum "yellow" {
           description "Assert yellow system alarm";
         }
         enum "ignore" {
           description "Do not assert any alarm signals";
         }
       }
     }
     leaf odu-ttim {
       description "ODU trail-trace-identifier-mismatch, ODU-TTIM failure";
       type enumeration {
         enum "red" {
           description "Assert red system alarm";
         }
         enum "yellow" {
           description "Assert yellow system alarm";
         }
         enum "ignore" {
           description "Do not assert any alarm signals";
         }
       }
     }
     leaf odu-ptim {
       description "ODU payload-type-mismatch, ODU-PTIM failure";
       type enumeration {
         enum "red" {
           description "Assert red system alarm";
         }
         enum "yellow" {
           description "Assert yellow system alarm";
         }
         enum "ignore" {
           description "Do not assert any alarm signals";
         }
       }
     }
   }
   grouping chassis_alarm_otn_otu_type {
     uses apply-advanced;
     leaf oc-los {
       description "Loss of signal, LOS failure";
       type enumeration {
         enum "red" {
           description "Assert red system alarm";
         }
         enum "yellow" {
           description "Assert yellow system alarm";
         }
         enum "ignore" {
           description "Do not assert any alarm signals";
         }
       }
     }
     leaf oc-lof {
       description "Loss of framing, LOF failure";
       type enumeration {
         enum "red" {
           description "Assert red system alarm";
         }
         enum "yellow" {
           description "Assert yellow system alarm";
         }
         enum "ignore" {
           description "Do not assert any alarm signals";
         }
       }
     }
     leaf oc-lom {
       description "Loss of multiframe, LOM failure";
       type enumeration {
         enum "red" {
           description "Assert red system alarm";
         }
         enum "yellow" {
           description "Assert yellow system alarm";
         }
         enum "ignore" {
           description "Do not assert any alarm signals";
         }
       }
     }
     leaf wavelength-lock {
       description "Wavelength lock alarm";
       type enumeration {
         enum "red" {
           description "Assert red system alarm";
         }
         enum "yellow" {
           description "Assert yellow system alarm";
         }
         enum "ignore" {
           description "Do not assert any alarm signals";
         }
       }
     }
     leaf otu-bdi {
       description "OTU backward-defect-indicator, OTU-BDI failure";
       type enumeration {
         enum "red" {
           description "Assert red system alarm";
         }
         enum "yellow" {
           description "Assert yellow system alarm";
         }
         enum "ignore" {
           description "Do not assert any alarm signals";
         }
       }
     }
     leaf otu-iae {
       description "OTU incoming-alignment-error, OTU-IAE failure";
       type enumeration {
         enum "red" {
           description "Assert red system alarm";
         }
         enum "yellow" {
           description "Assert yellow system alarm";
         }
         enum "ignore" {
           description "Do not assert any alarm signals";
         }
       }
     }
     leaf otu-ttim {
       description "OTU trail-trace-identifier-mismatch, OTU-TTIM failure";
       type enumeration {
         enum "red" {
           description "Assert red system alarm";
         }
         enum "yellow" {
           description "Assert yellow system alarm";
         }
         enum "ignore" {
           description "Do not assert any alarm signals";
         }
       }
     }
     leaf otu-fec-excessive-errs {
       description "OTU fec-excessive-errors, OTU-FEC_EXE failure";
       type enumeration {
         enum "red" {
           description "Assert red system alarm";
         }
         enum "yellow" {
           description "Assert yellow system alarm";
         }
         enum "ignore" {
           description "Do not assert any alarm signals";
         }
       }
     }
   }
   grouping chassis_alarm_serial_type {
     uses apply-advanced;
     leaf loss-of-rx-clock {
       description "RX clock absent";
       type enumeration {
         enum "red" {
           description "Assert red system alarm";
         }
         enum "yellow" {
           description "Assert yellow system alarm";
         }
         enum "ignore" {
           description "Do not assert any alarm signals";
         }
       }
     }
     leaf loss-of-tx-clock {
       description "TX clock absent";
       type enumeration {
         enum "red" {
           description "Assert red system alarm";
         }
         enum "yellow" {
           description "Assert yellow system alarm";
         }
         enum "ignore" {
           description "Do not assert any alarm signals";
         }
       }
     }
     leaf dcd-absent {
       description "DCD signal absent";
       type enumeration {
         enum "red" {
           description "Assert red system alarm";
         }
         enum "yellow" {
           description "Assert yellow system alarm";
         }
         enum "ignore" {
           description "Do not assert any alarm signals";
         }
       }
     }
     leaf cts-absent {
       description "CTS signal absent";
       type enumeration {
         enum "red" {
           description "Assert red system alarm";
         }
         enum "yellow" {
           description "Assert yellow system alarm";
         }
         enum "ignore" {
           description "Do not assert any alarm signals";
         }
       }
     }
     leaf dsr-absent {
       description "DSR signal absent";
       type enumeration {
         enum "red" {
           description "Assert red system alarm";
         }
         enum "yellow" {
           description "Assert yellow system alarm";
         }
         enum "ignore" {
           description "Do not assert any alarm signals";
         }
       }
     }
     leaf tm-absent {
       description "TM signal absent";
       type enumeration {
         enum "red" {
           description "Assert red system alarm";
         }
         enum "yellow" {
           description "Assert yellow system alarm";
         }
         enum "ignore" {
           description "Do not assert any alarm signals";
         }
       }
     }
   }
   grouping chassis_alarm_services_type {
     uses apply-advanced;
     leaf pic-reset {
       description "Services PIC reset";
       type enumeration {
         enum "red" {
           description "Assert red system alarm";
         }
         enum "yellow" {
           description "Assert yellow system alarm";
         }
         enum "ignore" {
           description "Do not assert any alarm signals";
         }
       }
     }
     leaf pic-hold-reset {
       description "Services PIC held in reset";
       type enumeration {
         enum "red" {
           description "Assert red system alarm";
         }
         enum "yellow" {
           description "Assert yellow system alarm";
         }
         enum "ignore" {
           description "Do not assert any alarm signals";
         }
       }
     }
     leaf linkdown {
       description "Services PIC linkdown";
       type enumeration {
         enum "red" {
           description "Assert red system alarm";
         }
         enum "yellow" {
           description "Assert yellow system alarm";
         }
         enum "ignore" {
           description "Do not assert any alarm signals";
         }
       }
     }
     leaf rx-errors {
       description "Services PIC excessive rx errors";
       type enumeration {
         enum "red" {
           description "Assert red system alarm";
         }
         enum "yellow" {
           description "Assert yellow system alarm";
         }
         enum "ignore" {
           description "Do not assert any alarm signals";
         }
       }
     }
     leaf tx-errors {
       description "Services PIC excessive tx errors";
       type enumeration {
         enum "red" {
           description "Assert red system alarm";
         }
         enum "yellow" {
           description "Assert yellow system alarm";
         }
         enum "ignore" {
           description "Do not assert any alarm signals";
         }
       }
     }
     leaf sw-down {
       description "Services PIC software problem";
       type enumeration {
         enum "red" {
           description "Assert red system alarm";
         }
         enum "yellow" {
           description "Assert yellow system alarm";
         }
         enum "ignore" {
           description "Do not assert any alarm signals";
         }
       }
     }
     leaf hw-down {
       description "Services PIC hardware problem";
       type enumeration {
         enum "red" {
           description "Assert red system alarm";
         }
         enum "yellow" {
           description "Assert yellow system alarm";
         }
         enum "ignore" {
           description "Do not assert any alarm signals";
         }
       }
     }
   }
   grouping chassis_alarm_sonet_type {
     uses apply-advanced;
     leaf lol {
       description "Loss of light";
       type enumeration {
         enum "red" {
           description "Assert red system alarm";
         }
         enum "yellow" {
           description "Assert yellow system alarm";
         }
         enum "ignore" {
           description "Do not assert any alarm signals";
         }
       }
     }
     leaf pll {
       description "Phase locked loop out of lock";
       type enumeration {
         enum "red" {
           description "Assert red system alarm";
         }
         enum "yellow" {
           description "Assert yellow system alarm";
         }
         enum "ignore" {
           description "Do not assert any alarm signals";
         }
       }
     }
     leaf lof {
       description "Loss of framing, LOF failure";
       type enumeration {
         enum "red" {
           description "Assert red system alarm";
         }
         enum "yellow" {
           description "Assert yellow system alarm";
         }
         enum "ignore" {
           description "Do not assert any alarm signals";
         }
       }
     }
     leaf los {
       description "Loss of signal, LOS failure";
       type enumeration {
         enum "red" {
           description "Assert red system alarm";
         }
         enum "yellow" {
           description "Assert yellow system alarm";
         }
         enum "ignore" {
           description "Do not assert any alarm signals";
         }
       }
     }
     leaf ais-l {
       description "Line alarm indication signal, AIS-L failure";
       type enumeration {
         enum "red" {
           description "Assert red system alarm";
         }
         enum "yellow" {
           description "Assert yellow system alarm";
         }
         enum "ignore" {
           description "Do not assert any alarm signals";
         }
       }
     }
     leaf ais-p {
       description "Path alarm indication signal, AIS-P failure";
       type enumeration {
         enum "red" {
           description "Assert red system alarm";
         }
         enum "yellow" {
           description "Assert yellow system alarm";
         }
         enum "ignore" {
           description "Do not assert any alarm signals";
         }
       }
     }
     leaf lop-p {
       description "Loss of pointer, LOP-P failure";
       type enumeration {
         enum "red" {
           description "Assert red system alarm";
         }
         enum "yellow" {
           description "Assert yellow system alarm";
         }
         enum "ignore" {
           description "Do not assert any alarm signals";
         }
       }
     }
     leaf ber-sd {
       description "Signal Degrade (SD), bit error rate > 1E-6";
       type enumeration {
         enum "red" {
           description "Assert red system alarm";
         }
         enum "yellow" {
           description "Assert yellow system alarm";
         }
         enum "ignore" {
           description "Do not assert any alarm signals";
         }
       }
     }
     leaf ber-sf {
       description "Signal Fail (SF), bit error rate > 1E-3";
       type enumeration {
         enum "red" {
           description "Assert red system alarm";
         }
         enum "yellow" {
           description "Assert yellow system alarm";
         }
         enum "ignore" {
           description "Do not assert any alarm signals";
         }
       }
     }
     leaf rfi-l {
       description "Line remote failure indication, RFI-L, line FERF";
       type enumeration {
         enum "red" {
           description "Assert red system alarm";
         }
         enum "yellow" {
           description "Assert yellow system alarm";
         }
         enum "ignore" {
           description "Do not assert any alarm signals";
         }
       }
     }
     leaf rfi-p {
       description "Path remote failure indication, RFI-P, STS path yellow";
       type enumeration {
         enum "red" {
           description "Assert red system alarm";
         }
         enum "yellow" {
           description "Assert yellow system alarm";
         }
         enum "ignore" {
           description "Do not assert any alarm signals";
         }
       }
     }
     leaf uneq-p {
       description "STS Path (C2) unequipped, UNEQ-P failure";
       type enumeration {
         enum "red" {
           description "Assert red system alarm";
         }
         enum "yellow" {
           description "Assert yellow system alarm";
         }
         enum "ignore" {
           description "Do not assert any alarm signals";
         }
       }
     }
     leaf locd {
       description "Loss of cell delineation (ATM only)";
       type enumeration {
         enum "red" {
           description "Assert red system alarm";
         }
         enum "yellow" {
           description "Assert yellow system alarm";
         }
         enum "ignore" {
           description "Do not assert any alarm signals";
         }
       }
     }
     leaf plm-p {
       description "STS payload label (C2) mismatch, PLM-P failure";
       type enumeration {
         enum "red" {
           description "Assert red system alarm";
         }
         enum "yellow" {
           description "Assert yellow system alarm";
         }
         enum "ignore" {
           description "Do not assert any alarm signals";
         }
       }
     }
   }
   grouping chassis_fabric_type {
     uses apply-advanced;
     container redundancy-mode {
       description "Fabric redundancy mode";
       uses apply-advanced;
       choice mode {
         case case_1 {
           leaf redundant {
             description "Fabric is configured in redundant mode";
             type empty;
           }
         }
         case case_2 {
           leaf increased-bandwidth {
             description "Fabric is configured in increased bandwidth mode";
             type empty;
           }
         }
       }
     }
   }
   grouping chassis_feb_type {
     uses apply-advanced;
   }
   grouping chassis_fpc_type {
     leaf name {
       description "FPC slot number";
       type union {
         type string {
           pattern "<.*>|$.*";
         }
         type uint32;
       }
     }
     uses apply-advanced;
     list pic {
       key name;
       description "Physical Interface Card number";
       uses chassis_pic_type;
     }
     leaf power {
       description "Power FPCs on or off";
       type enumeration {
         enum "off" {
           description "Do not provide power to FPCs";
         }
         enum "on" {
           description "Provide power to FPCs";
         }
       }
     }
     leaf power-budget-priority {
       description "FPC priority number";
       type union {
         type string {
           pattern "<.*>|$.*";
         }
         type uint32;
       }
     }
     choice mode {
       case case_1 {
         leaf disable-power {
           description "Do not provide power to the card";
           status deprecated;
           type empty;
         }
       }
       case case_2 {
         leaf allow-sram-parity-errors {
           description "Do not power cycle FPC when SRAM parity errors occur";
           type empty;
         }
       }
     }
     choice riot-mode {
       case case_1 {
       }
       case case_2 {
       }
     }
     leaf offline {
       description "Keep FPC offline";
       type empty;
     }
     list port-mirror-instance {
       key name;
       ordered-by user;
       max-elements 2;
       leaf name {
         description "Associate a port mirroring instance with the FPC";
         junos:must "(!(\"forwarding-options port-mirroring instance $$ input-parameters-instance\"))";
         junos:must-message "Derived instance cannot be binded";
         junos:must "(((!(\"chassis network-services lan\") && (\"forwarding-options port-mirroring instance $$\" || \"forwarding-options analyzer $$\")) || \"chassis network-services lan\"))";
         junos:must-message "Referenced port-mirroring instance does not exist";
         junos:must "((\"forwarding-options port-mirroring instance $$\" || \"forwarding-options analyzer $$\"))";
         junos:must-message "Referenced port-mirroring/analyzer instance does not exist";
         type string {
           length "1 .. 64";
         }
       }
       uses apply-advanced;
     }
     list sampling-instance {
       key name;
       ordered-by user;
       max-elements 1;
       leaf name {
         description "Associate a sampling instance with the FPC";
         junos:must "(\"forwarding-options sampling instance $$\")";
         junos:must-message "Referenced sampling instance does not exist";
         type string {
           length "1 .. 64";
         }
       }
       uses apply-advanced;
     }
     container inline-services {
       uses apply-advanced;
       leaf report-zero-oif-gw-on-discard {
         description "Jflow reports value zero in OIF and GW when traffic is not forwarded";
         type empty;
       }
       leaf flex-flow-sizing {
         description "No fixed size allocation of flow tables for proto families";
         junos:must "(!((\".. flow-table-size ipv4-flow-table-size\" || (\".. flow-table-size ipv6-flow-table-size\" || (\".. flow-table-size vpls-flow-table-size\" || \".. flow-table-size mpls-flow-table-size\")))))";
         junos:must-message "flex-flow-sizing and flow-table-size are mutually exclusive";
         type empty;
       }
       leaf use-extended-flow-memory {
         description "Use extended memory for flow records";
         type empty;
       }
       container flow-table-size {
         uses apply-advanced;
         leaf ipv4-flow-table-size {
           description "IPv4 flow table size in units of 256k";
           junos:must "(!(\".. .. flex-flow-sizing\"))";
           junos:must-message "flex-flow-sizing and flow-table-size are mutually exclusive";
           type union {
             type string {
               pattern "<.*>|$.*";
             }
             type uint32 {
               range "1 .. 245";
             }
           }
         }
         leaf ipv6-flow-table-size {
           description "IPv6 flow table size in units of 256k";
           junos:must "(!(\".. .. flex-flow-sizing\"))";
           junos:must-message "flex-flow-sizing and flow-table-size are mutually exclusive";
           type union {
             type string {
               pattern "<.*>|$.*";
             }
             type uint32 {
               range "1 .. 245";
             }
           }
         }
         leaf vpls-flow-table-size {
           description "VPLS flow table size in units of 256k";
           junos:must "(!(\".. .. flex-flow-sizing\"))";
           junos:must-message "flex-flow-sizing and flow-table-size are mutually exclusive";
           type union {
             type string {
               pattern "<.*>|$.*";
             }
             type uint32 {
               range "1 .. 245";
             }
           }
         }
         leaf ipv6-extended-attrib {
           description "Enable extended flow attribute";
           type empty;
         }
         leaf mpls-flow-table-size {
           description "MPLS flow table size in units of 256k";
           junos:must "(!(\".. .. flex-flow-sizing\"))";
           junos:must-message "flex-flow-sizing and flow-table-size are mutually exclusive";
           type union {
             type string {
               pattern "<.*>|$.*";
             }
             type uint32 {
               range "1 .. 245";
             }
           }
         }
       }
     }
     container inline-video-monitoring {
       uses apply-advanced;
       leaf maximum-flows-count {
         description "Maximum number of inline video monitoring flows per PFE instance.";
         status deprecated;
         type union {
           type string {
             pattern "<.*>|$.*";
           }
           type uint32 {
             range "16 .. 8192";
           }
         }
       }
       leaf flow-table-size {
         description "Size of flow table size per PFE instance";
         type union {
           type string {
             pattern "<.*>|$.*";
           }
           type uint32 {
             range "16 .. 8192";
           }
         }
       }
     }
     container slamon-services {
       description "SLA monitoring services";
       uses apply-advanced;
     }
     list pfe {
       key name;
       description "Packet forwarding engine parameters";
       uses chassis_pfe_type;
     }
     container openflow {
       description "Openflow configuration";
       uses apply-advanced;
       leaf access-list-partition {
         description "Space reserved for openflow access-list rules";
         units "percents";
         type union {
           type string {
             pattern "<.*>|$.*";
           }
           type uint32 {
             range "0 .. 100";
           }
         }
       }
     }
   }
   grouping chassis_pfe_type {
     description "PFE(Packet forwarding engine)";
     leaf name {
       description "PFE(Packet forwarding engine) identifier";
       type union {
         type string {
           pattern "<.*>|$.*";
         }
         type uint32 {
           range "0 .. 31";
         }
       }
     }
     uses apply-advanced;
     container forwarding-packages {
       description "Associated forwarding package configuration";
       uses apply-advanced;
       container mobility {
         description "Mobility related PFE configuration";
         uses apply-advanced;
         choice package-type {
           case case_1 {
             leaf ggsn-pgw {
               description "GGSN packet gateway";
               type empty;
             }
           }
           case case_2 {
             leaf sgw {
               description "Serving gateway";
               type empty;
             }
           }
         }
       }
     }
     leaf tunnel-services {
       description "Tunnel services configuration";
       type empty;
     }
   }
   grouping chassis_pic_type {
     leaf name {
       description "PIC slot number";
       type union {
         type string {
           pattern "<.*>|$.*";
         }
         type uint32;
       }
     }
     uses apply-advanced;
     list tunnel-port {
       key name;
       description "Tunnel port number";
       uses chassis_port_type;
     }
     container tunnel-services {
       presence "enable tunnel-services";
       junos:must "(!(\".. traffic-manager single-stream\"))";
       junos:must-message "Cannot configure tunnel-services if single-stream is configured";
       description "Tunnel services configuration";
       uses apply-advanced;
       leaf bandwidth {
         description "Amount of bandwidth reserved for tunnel service";
         type string;
       }
       leaf tunnel-only {
         description "Support only tunnel traffic";
         type empty;
       }
     }
     choice adaptive-or-monitoring {
       case case_1 {
       }
       case case_2 {
         container monitoring-services {
           description "Monitoring services configuration";
           uses apply-advanced;
           leaf application {
             description "Application mode";
             type enumeration {
               enum "dynamic-flow-capture" {
                 description "Dynamic flow capture mode";
               }
               enum "flow-collector" {
                 description "Flow collector mode";
               }
               enum "monitor" {
                 description "Monitor mode";
               }
             }
           }
         }
       }
     }
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
         enum "lan" {
           description "LAN mode";
         }
       }
     }
     leaf vtmapping {
       description "Virtual tunnel mapping mode";
       type enumeration {
         enum "klm" {
           description "KLM mode";
         }
         enum "itu-t" {
           description "ITU-T mode";
         }
       }
     }
     leaf no-concatenate {
       description "Do not concatenate channels";
       type empty;
     }
     leaf no-multi-rate {
       description "Disable multi-rate mode";
       type empty;
     }
     leaf aggregate-ports {
       description "Aggregate multiple ports on a PIC as a single port";
       type empty;
     }
     leaf sparse-dlcis {
       description "Run in sparse data-link connection identifier mode";
       type empty;
     }
     container q-pic-large-buffer {
       presence "enable q-pic-large-buffer";
       description "Run in large delay buffer mode";
       uses apply-advanced;
       choice buffer-type {
         case case_1 {
           leaf small-scale {
             description "Supports less number of interfaces";
             type empty;
           }
         }
         case case_2 {
           leaf large-scale {
             description "Supports large number of interfaces";
             type empty;
           }
         }
       }
     }
     container red-buffer-occupancy {
       description "Computation type for RED buffer occupancy";
       uses apply-advanced;
       container weighted-averaged {
         presence "enable weighted-averaged";
         description "Weighted-average computation";
         uses apply-advanced;
         leaf instant-usage-weight-exponent {
           description "Weight for instant buffer usage (negative exponent of 2)";
           type union {
             type uint8;
             type string {
               pattern "<.*>|$.*";
             }
           }
         }
       }
     }
     container traffic-manager {
       description "Configure traffic manager attributes";
       uses apply-advanced;
       leaf ingress-shaping-overhead {
         description "Number of CoS shaping overhead bytes in ingress";
         units "bytes";
         type union {
           type string {
             pattern "<.*>|$.*";
           }
           type int32 {
             range "-62 .. 192";
           }
         }
       }
       leaf egress-shaping-overhead {
         description "Number of CoS shaping overhead bytes in egress";
         units "bytes";
         type union {
           type string {
             pattern "<.*>|$.*";
           }
           type int32 {
             range "-62 .. 192";
           }
         }
       }
       leaf mode {
         description "Configure traffic manager mode";
         type enumeration {
           enum "egress-only" {
             description "Egress traffic manager enabled, ingress traffic manager disabled";
           }
           enum "session-shaping" {
             description "Enable egress session shaping";
           }
           enum "ingress-and-egress" {
             description "Enable the ingress and egress traffic managers";
           }
         }
       }
     }
     container idle-cell-format {
       description "ATM idle cell configuration";
       uses apply-advanced;
       leaf itu-t {
         description "ITU-T idle cell header format";
         type empty;
       }
       leaf payload-pattern {
         description "Payload pattern byte (0x00-0xff)";
         type string;
       }
     }
     container atm-l2circuit-mode {
       description "Enable ATM Layer 2 circuit transport mode";
       uses apply-advanced;
       choice mode_choice {
         case case_1 {
           leaf aal5 {
             description "ATM Layer 2 circuit AAL5 mode";
             type empty;
           }
         }
         case case_2 {
           leaf cell {
             description "ATM Layer 2 circuit cell mode";
             type empty;
           }
         }
         case case_3 {
           container trunk {
             presence "enable trunk";
             description "Set ATM Layer 2 circuit trunk mode";
             uses apply-advanced;
             choice trunk-mode {
               case case_1 {
                 container uni {
                   presence "enable uni";
                   description "ATM Layer 2 circuit user-to-network interface trunk mode";
                   uses apply-advanced;
                 }
               }
               case case_2 {
                 container nni {
                   presence "enable nni";
                   description "ATM Layer 2 circuit network-to-network interface trunk mode";
                   uses apply-advanced;
                 }
               }
             }
           }
         }
       }
     }
     leaf atm-cell-relay-accumulation {
       description "Enable ATM cell-relay accumulation mode";
       type empty;
     }
     leaf mlfr-uni-nni-bundles {
       description "Number of multilink Frame Relay UNI NNI (FRF.16) bundles to allocate on PIC";
       type union {
         type string {
           pattern "<.*>|$.*";
         }
         type uint32 {
           range "1 .. 255";
         }
       }
     }
     leaf mlfr-uni-nni-bundles-inline {
       description "Number of inline multilink frame relay UNI NNI bundles";
       type union {
         type string {
           pattern "<.*>|$.*";
         }
         type uint32 {
           range "1 .. 255";
         }
       }
     }
     container ct3 {
       description "CT3 NxDS0 PIC configuration";
       uses apply-advanced;
       list port {
         key name;
         description "CT3 port";
         uses ct3_port_type;
       }
     }
     container ce1 {
       description "CE1 NxDS0 PIC configuration";
       uses apply-advanced;
       list e1 {
         key name;
         description "E1 link";
         uses ce1_channel_type;
       }
     }
     leaf max-queues-per-interface {
       description "Maximum number of queues per interface on QOS-capable PIC";
       type enumeration {
         enum "4" {
           description "Maximum 4 queues per interface";
         }
         enum "8" {
           description "Maximum 8 queues per interface";
         }
       }
     }
     container shdsl {
       description "SHDSL chassis configuration";
       uses apply-advanced;
       leaf pic-mode {
         description "PIC mode";
         default "2-port-atm";
         type enumeration {
           enum "1-port-atm" {
             description "Single port ATM, 8 wire mode";
           }
           enum "2-port-atm" {
             description "Two port ATM, 4 wire mode";
           }
           enum "4-port-atm" {
             description "Four port ATM, 2 wire mode";
           }
           enum "efm" {
             description "Single port EFM, 2 wire mode";
           }
         }
       }
     }
     list port-mirror-instance {
       key name;
       ordered-by user;
       max-elements 2;
       leaf name {
         description "Associate a port mirroring instance with the PIC";
         junos:must "(!(\"forwarding-options port-mirroring instance $$ input-parameters-instance\"))";
         junos:must-message "Derived instance cannot be binded";
         junos:must "(((!(\"chassis network-services lan\") && (\"forwarding-options port-mirroring instance $$\" || \"forwarding-options analyzer $$\")) || \"chassis network-services lan\"))";
         junos:must-message "Referenced port-mirroring instance does not exist";
         junos:must "((\"forwarding-options port-mirroring instance $$\" || \"forwarding-options analyzer $$\"))";
         junos:must-message "Referenced port-mirroring/analyzer instance does not exist";
         type string {
           length "1 .. 64";
         }
       }
       uses apply-advanced;
     }
     list port {
       key name;
       description "Port number";
       uses chassis_pic_port_framing;
     }
     container fibre-channel {
       description "Fibre channel configuration option";
       uses chassis_fibre_channel_type;
     }
     list qsfp-port {
       key name;
       description "Qsfp port to configure";
       leaf name {
         description "Port-group 0:'0-3' 1:'4-7'";
         type union {
           type string {
             pattern "<.*>|$.*";
           }
           type uint32 {
             range "0 .. 1";
           }
         }
       }
       uses apply-advanced;
       leaf port-mode {
         description "Select mode for port-group";
         type enumeration {
           enum "40g" {
             description "40G mode";
           }
           enum "10g" {
             description "10G mode";
           }
         }
       }
     }
     container sfpplus {
       description "Sfpplus configuration option";
       uses apply-advanced;
       leaf pic-mode {
         description "PIC mode";
         type enumeration {
           enum "1g" {
             description "1G SFP mode";
           }
           enum "10g" {
             description "10G SFP+ mode";
           }
         }
       }
     }
   }
   grouping ce1_channel_type {
     leaf name {
       description "E1 link number";
       type union {
         type string {
           pattern "<.*>|$.*";
         }
         type uint32 {
           range "0 .. 9";
         }
       }
     }
     uses apply-advanced;
     list channel-group {
       key name;
       description "Define channel group";
       leaf name {
         description "Channel group number";
         type union {
           type string {
             pattern "<.*>|$.*";
           }
           type uint32 {
             range "0 .. 23";
           }
         }
       }
       leaf timeslots {
         description "DS0 timeslots (1..31); for example, 1-3,4,9,22-24 (no spaces)";
         type string;
       }
     }
   }
   grouping chassis_fibre_channel_type {
     description "Fibre channel configuration option";
     uses apply-advanced;
     list port-range {
       key "port-range-low port-range-high";
       ordered-by user;
       description "Fibre channel port range";
       leaf port-range-low {
         description "Port range low number";
         type union {
           type string {
             pattern "<.*>|$.*";
           }
           type uint32 {
             range "0 .. 47";
           }
         }
       }
       leaf port-range-high {
         description "Port range high number";
         type union {
           type string {
             pattern "<.*>|$.*";
           }
           type uint32 {
             range "0 .. 47";
           }
         }
       }
       uses apply-advanced;
     }
   }
   grouping chassis_pic_port_framing {
     leaf name {
       description "Port number";
       type union {
         type string {
           pattern "<.*>|$.*";
         }
         type uint32;
       }
     }
     uses apply-advanced;
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
       }
     }
     leaf speed {
       description "Port speed";
       junos:must "(!((\".. .. pic-mode\" || \".. .. number-of-ports\")))";
       junos:must-message " speed config can neither co-exist with pic <> number-of-ports <> nor pic <> pic-mode config";
       type enumeration {
         enum "oc3-stm1" {
           description "OC3 or STM1";
         }
         enum "oc12-stm4" {
           description "OC12 or STM4";
         }
         enum "oc48-stm16" {
           description "OC48 or STM16";
         }
         enum "1G" {
           description "1GE-Gigabit Ethernet";
         }
         enum "10g" {
           description "Sets the interface mode to 10Gbps";
         }
         enum "25g" {
           description "Sets the interface mode to 25Gbps";
         }
         enum "40g" {
           description "Sets the interface mode to 40Gbps";
         }
         enum "100g" {
           description "Sets the interface mode to 100Gbps";
         }
       }
     }
   }
   grouping chassis_port_type {
     leaf name {
       description "Port number for tunnel services";
       type union {
         type string {
           pattern "<.*>|$.*";
         }
         type uint32 {
           range "0 .. 47";
         }
       }
     }
     uses apply-advanced;
     leaf tunnel-services {
       description "Tunnel services configuration";
       type empty;
     }
   }
   grouping chassis_redundancy_type {
     uses apply-advanced;
     list routing-engine {
       key name;
       description "Redundancy options for Routing Engines";
       uses chassis_rdd_re_type;
     }
     container failover {
       description "Failover to other Routing Engine";
       uses chassis_rdd_failover_type;
     }
     leaf keepalive-time {
       description "Time before Routing Engine failover";
       units "seconds";
       junos:must "(!(\"chassis redundancy graceful-switchover\"))";
       junos:must-message "Graceful switchover configured, cannot change the default keepalive interval";
       type union {
         type string {
           pattern "<.*>|$.*";
         }
         type uint32 {
           range "2 .. 10000";
         }
       }
     }
     container graceful-switchover {
       description "Enable graceful switchover on supported hardware";
       junos:must "(!((any \"chassis fpc <*> pic <*> monitoring-services application\" && \"chassis redundancy graceful-switchover\")))";
       junos:must-message "Graceful Switchover is not supported on monitoring-services application";
       uses chassis_non_stop_forwarding_type;
       junos:must "(!((any \"chassis fpc <*> pic <*> monitoring-services application\" && \"chassis redundancy graceful-switchover\")))";
       junos:must-message "Graceful Switchover is not supported on monitoring-services application";
     }
   }
   grouping chassis_non_stop_forwarding_type {
     junos:must "((!(\"system inet6-backup-router\") || \"system inet6-backup-router destination\"))";
     junos:must-message "Please define destination subnet with the inet6-backup-router configuration";
     junos:must "((!(\"system backup-router\") || \"system backup-router destination\"))";
     junos:must-message "Please define destination subnet with the backup-router configuration";
     uses apply-advanced;
     container traceoptions {
       description "Graceful switchover trace options";
       status deprecated;
       uses apply-advanced;
       list flag {
         key name;
         ordered-by user;
         description "Tracing parameters";
         leaf name {
           type enumeration {
             enum "update" {
               description "Trace state updates";
             }
             enum "all" {
               description "Trace everything";
             }
           }
         }
       }
     }
   }
   grouping chassis_rdd_failover_type {
     uses apply-advanced;
     leaf on-loss-of-keepalives {
       description "Failover on loss of keepalives";
       type empty;
     }
     leaf on-disk-failure {
       description "Failover on disk failure";
       junos:must "((\"chassis redundancy failover on-loss-of-keepalives\" || \"chassis redundancy graceful-switchover\"))";
       junos:must-message "Option on-loss-of-keepalives or graceful-switchover must be set";
       type empty;
     }
     leaf not-on-disk-underperform {
       description "Prevent gstatd from initiating failovers in response to slow disks";
       type empty;
     }
     leaf disk-read-threshold {
       description "Read threshold (ms) on disk underperform monitoring";
       type union {
         type string {
           pattern "<.*>|$.*";
         }
         type uint32 {
           range "1000 .. 10000";
         }
       }
     }
     leaf disk-write-threshold {
       description "Write threshold (ms) on disk underperform monitoring";
       type union {
         type string {
           pattern "<.*>|$.*";
         }
         type uint32 {
           range "1000 .. 10000";
         }
       }
     }
   }
   grouping chassis_rdd_re_type {
     leaf name {
       description "Routing Engine slot number";
       type union {
         type string {
           pattern "<.*>|$.*";
         }
         type uint32 {
           range "0 .. 1";
         }
       }
     }
     choice priority {
       case case_1 {
         leaf master {
           description "Master Routing Engine";
           type empty;
         }
       }
       case case_2 {
         leaf backup {
           description "Backup Routing Engine";
           type empty;
         }
       }
       case case_3 {
         leaf disabled {
           description "Routing Engine disabled";
           type empty;
         }
       }
     }
   }
   grouping chassis_routing_engine_type {
     uses apply-advanced;
     container on-disk-failure {
       description "Action to take when Routing Engine disk fails";
       uses chassis_re_on_disk_failure;
     }
   }
   grouping chassis_re_on_disk_failure {
     choice reboot_or_halt {
       case case_1 {
         leaf reboot {
           description "Reboot on disk failure";
           status deprecated;
           type empty;
         }
       }
       case case_2 {
         leaf disk-failure-action {
           type enumeration {
             enum "reboot" {
               description "Reboot on disk failure";
             }
             enum "halt" {
               description "Halt on disk failure";
             }
           }
         }
       }
     }
   }
   grouping chassis_sib_type {
     uses apply-advanced;
   }
   grouping chassisd_agg_container_type {
     uses apply-advanced;
     leaf device-count {
       description "Number of container devices";
       type union {
         type string {
           pattern "<.*>|$.*";
         }
         type uint32 {
           range "1 .. 128";
         }
       }
     }
   }
   grouping chassisd_agg_enet_type {
     uses apply-advanced;
     leaf device-count {
       description "Number of aggregated Ethernet devices";
       type union {
         type string {
           pattern "<.*>|$.*";
         }
         type uint32;
       }
     }
     container lacp {
       description "Global Link Aggregation Control Protocol configuration";
       uses apply-advanced;
       leaf system-priority {
         description "Priority of the system (0 ... 65535)";
         type string;
       }
       container link-protection {
         presence "enable link-protection";
         uses apply-advanced;
         leaf non-revertive {
           description "Don't revert links when better priority link comes up";
           type empty;
         }
       }
     }
   }
   grouping chassisd_agg_pos_type {
     uses apply-advanced;
     leaf device-count {
       description "Number of aggregated SONET devices";
       type union {
         type string {
           pattern "<.*>|$.*";
         }
         type uint32 {
           range "1 .. 64";
         }
       }
     }
   }
   grouping chassisd_provider_instance_type {
     uses apply-advanced;
     leaf device-count {
       description "Number of provider instance port devices";
       type union {
         type string {
           pattern "<.*>|$.*";
         }
         type uint32 {
           range "1 .. 16";
         }
       }
     }
   }
   grouping ct3_port_type {
     leaf name {
       description "CT3  L2NG_PRODUCTSport number";
       type union {
         type string {
           pattern "<.*>|$.*";
         }
         type int32 {
           range "0 .. 1";
         }
       }
     }
     uses apply-advanced;
     list t1 {
       key name;
       description "T1 link";
       uses ct3_channel_type;
     }
   }
   grouping ct3_channel_type {
     leaf name {
       description "T1 link number";
       type union {
         type string {
           pattern "<.*>|$.*";
         }
         type int32 {
           range "0 .. 27";
         }
       }
     }
     uses apply-advanced;
     list channel-group {
       key name;
       description "Define channel group";
       leaf name {
         description "Channel group number";
         type union {
           type string {
             pattern "<.*>|$.*";
           }
           type uint32 {
             range "0 .. 7";
           }
         }
       }
       leaf timeslots {
         description "DS0 timeslots (1..24); for example, 1-3,4,9,22-24 (no spaces)";
         type string;
       }
     }
   }
   grouping juniper-protected-system-domain {
     description "Protected system domain configuration";
     leaf name {
       description "Name of protected system domain (psd[1-31], ex. psd2)";
       type string {
         junos:posix-pattern "^psd([1-9]|[1-2][0-9]|[3][0-1])$";
         junos:pattern-message "Protected system domain name is a string consisting of 'psd' follows by the PSD ID (1-31), ex. psd2";
       }
     }
     uses apply-advanced;
     leaf description {
       description "Description of protected system domain";
       type string;
     }
     list lcc {
       key name;
       leaf name {
         description "Specific LCC";
         type union {
           type string {
             pattern "<.*>|$.*";
           }
           type uint32;
         }
       }
       uses apply-advanced;
       leaf-list fpcs {
         description "FPC associated with protected system domain";
         type union {
           type string {
             pattern "<.*>|$.*";
           }
           type uint32;
         }
       }
     }
     leaf control-system-id {
       description "Control system identifier";
       type union {
         type string {
           pattern "<.*>|$.*";
         }
         type uint32 {
           range "1 .. 4";
         }
       }
     }
     leaf-list control-slot-numbers {
       description "Slots associated with protected system domain";
       type union {
         type string {
           pattern "<.*>|$.*";
         }
         type uint32 {
           range "1 .. 12";
         }
       }
       max-elements 2;
     }
     leaf control-plane-bandwidth-percent {
       description "Percentage of control plane bandwidth";
       units "percent";
       type union {
         type string {
           pattern "<.*>|$.*";
         }
         type uint32 {
           range "0 .. 100";
         }
       }
     }
   }
   grouping juniper-protected-system-domain-traceoptions {
     description "Protected system domain traceoptions";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "rtsock" {
             description "Trace rtsock messages";
           }
           enum "ipc" {
             description "Trace IPC messages";
           }
           enum "init" {
             description "Trace intialization messages";
           }
           enum "psd" {
             description "Trace psd messages";
           }
           enum "all" {
             description "Trace everything";
           }
         }
       }
     }
   }
   grouping macro-data-type {
     leaf name {
       description "Keyword part of the keyword-value pair";
       type string;
     }
     leaf value {
       description "Value part of the keyword-value pair";
       type string;
     }
   }
   grouping upgrade-group-fpcs {
     description "Upgrade group fpcs";
     leaf name {
       description "Member identifier";
       type union {
         type string {
           pattern "<.*>|$.*";
         }
         type int32;
       }
     }
     uses apply-advanced;
     leaf-list fpcs {
       description "FPCs to be upgraded as a group in this member";
       type union {
         type string {
           pattern "<.*>|$.*";
         }
         type uint32;
       }
     }
   }
 }
