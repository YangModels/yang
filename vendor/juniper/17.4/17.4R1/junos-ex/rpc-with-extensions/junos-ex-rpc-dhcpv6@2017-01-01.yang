/*
 * Copyright (c) 2017 Juniper Networks, Inc.
 * All rights reserved.
 */
 module junos-ex-rpc-dhcpv6 {
   namespace "http://yang.juniper.net/junos-ex/rpc/dhcpv6";

   prefix dhcpv6;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for dhcpv6 command(s)";

   revision 2017-01-01 {
     description "Junos: 17.4R1.16";
   }

   rpc get-dhcpv6-relay-binding-information {
     description "Show DHCPv6 relay client binding information";
     input {
       leaf level {
         default "brief";
         type enumeration {
           enum "brief" {
             description "Display brief information";
           }
           enum "detail" {
             description "Display detailed information";
           }
           enum "summary" {
             description "Display summary information";
           }
         }
       }
       choice show-choice {
         case address {
           leaf address {
             description "IPv6 Prefix, session-id or CID of DHCPv6 client binding";
             type string;
           }
         }
         case interfaces-wildcard {
           leaf interfaces-wildcard {
             description "Interfaces to show bindings on (can be '*' wildcard)";
             type string {
               junos:posix-pattern "^( (((ge-)|(xe-)|(et-))( [[:digit:]]+(-([[:digit:]]+))+(-([[:digit:]]+)?)?)?) | (ae))+$";
               junos:pattern-message "Must be an interface wildcard string";
             }
           }
         }
         case interfaces-vlan {
           leaf interfaces-vlan {
             description "Interface VLAN-ID/SVLAN-ID on which to show bindings";
             type string {
               junos:posix-pattern "^(( (((ge-)|(xe-)|(et-))( [[:digit:]]+(-([[:digit:]]+))+(-([[:digit:]]+)?)?)?) | (ae))(/:)([[:digit:]]+(-[[:digit:]]+))?)+$";
               junos:pattern-message "Must be an interface:VLAN string";
             }
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml dhcpv6-relay-binding-information;
         }
         case multichassis-tag {
           anyxml multi-routing-engine-results;
         }
       }
     }
   }
   rpc get-dhcpv6-relay-binding-ltv-information {
     description "Display lease time violated client bindings";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml dhcpv6-relay-binding-information;
         }
         case multichassis-tag {
           anyxml multi-routing-engine-results;
         }
       }
     }
   }
   rpc get-dhcpv6-relay-binding-interface {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
           enum "summary" {
             description "Display summary information";
           }
         }
       }
     }
     output {
       choice output_c {
         case output-tag {
           leaf output {
             type string;
           }
         }
         case actual-tag {
           anyxml dhcpv6-relay-binding-information;
         }
         case multichassis-tag {
           anyxml multi-routing-engine-results;
         }
       }
     }
   }
   rpc get-dhcpv6-relay-statistics-information {
     description "Show DHCPv6 relay statistics";
     input {
       leaf level {
         default "summary";
         type enumeration {
           enum "summary" {
             description "Display summary information";
           }
           enum "verbose" {
             description "Display verbose information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml dhcpv6-relay-statistics-information;
         }
         case multichassis-tag {
           anyxml multi-routing-engine-results;
         }
       }
     }
   }
   rpc get-dhcpv6-relay-leasequery-statistics {
     description "Show DHCP relay leasequery statistics";
     input {
       leaf level {
         default "summary";
         type enumeration {
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml dhcp-relay-leasequery-statistics;
         }
         case multichassis-tag {
           anyxml multi-routing-engine-results;
         }
       }
     }
   }
   rpc get-dhcpv6-relay-bulk-leasequery-conn-statistics {
     description "Show DHCP relay bulk leasequery statistics";
     input {
       leaf level {
         default "summary";
         type enumeration {
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml dhcp-relay-bulk-leasequery-conn-statistics;
         }
         case multichassis-tag {
           anyxml multi-routing-engine-results;
         }
       }
     }
   }
   rpc get-dhcpv6-service-statistics-information {
     description "Show DHCPv6 service statistics";
     input {
       leaf level {
         default "summary";
         type enumeration {
           enum "summary" {
             description "Display summary information";
           }
         }
       }
       leaf interface {
         description "Name of interface";
         type union {
           type jt:interface-name;
           type string {
             pattern "<.*>|$.*";
           }
         }
       }
     }
     output {
       choice output_c {
         case output-tag {
           leaf output {
             type string;
           }
         }
         case actual-tag {
           anyxml dhcpv6-service-statistics-information;
         }
         case multichassis-tag {
           anyxml multi-routing-engine-results;
         }
       }
     }
   }
   rpc get-dhcpv6-server-binding-information {
     description "Show DHCPv6 server client binding information";
     input {
       leaf level {
         default "brief";
         type enumeration {
           enum "brief" {
             description "Display brief information";
           }
           enum "detail" {
             description "Display detailed information";
           }
           enum "summary" {
             description "Display summary information";
           }
         }
       }
       choice show-choice {
         case address {
           leaf address {
             description "IPv6 Prefix, session-id or CID of DHCPv6 client binding";
             type string;
           }
         }
         case interfaces-wildcard {
           leaf interfaces-wildcard {
             description "Interfaces to show bindings on (can be '*' wildcard)";
             type string {
               junos:posix-pattern "^( (((ge-)|(xe-)|(et-))( [[:digit:]]+(-([[:digit:]]+))+(-([[:digit:]]+)?)?)?) | (ae))+$";
               junos:pattern-message "Must be an interface wildcard string";
             }
           }
         }
         case interfaces-vlan {
           leaf interfaces-vlan {
             description "Interface VLAN-ID/SVLAN-ID on which to show bindings";
             type string {
               junos:posix-pattern "^(( (((ge-)|(xe-)|(et-))( [[:digit:]]+(-([[:digit:]]+))+(-([[:digit:]]+)?)?)?) | (ae))(/:)([[:digit:]]+(-[[:digit:]]+))?)+$";
               junos:pattern-message "Must be an interface:VLAN string";
             }
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml dhcpv6-server-binding-information;
         }
         case multichassis-tag {
           anyxml multi-routing-engine-results;
         }
       }
     }
   }
   rpc get-dhcpv6-server-binding-ltv-information {
     description "Display lease time violated client bindings";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml dhcpv6-server-binding-information;
         }
         case multichassis-tag {
           anyxml multi-routing-engine-results;
         }
       }
     }
   }
   rpc get-dhcpv6-server-binding-interface {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
           enum "summary" {
             description "Display summary information";
           }
         }
       }
     }
     output {
       choice output_c {
         case output-tag {
           leaf output {
             type string;
           }
         }
         case actual-tag {
           anyxml dhcpv6-server-binding-information;
         }
         case multichassis-tag {
           anyxml multi-routing-engine-results;
         }
       }
     }
   }
   rpc get-dhcpv6-server-statistics-information {
     description "Show DHCPv6 server statistics";
     input {
       leaf level {
         default "summary";
         type enumeration {
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml dhcpv6-server-statistics-information;
         }
         case multichassis-tag {
           anyxml multi-routing-engine-results;
         }
       }
     }
   }
   rpc get-dhcpv6-server-bulk-leasequery-conn-statistics {
     description "Show DHCP server bulk leasequeery conn statistics";
     input {
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml dhcp-server-bulk-leasequery-conn-statistics;
         }
         case multichassis-tag {
           anyxml multi-routing-engine-results;
         }
       }
     }
   }
   rpc get-dhcpv6-client-binding-information {
     description "Show DHCPV6 dhcpv6-client binding information";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml dhcpv6-client-binding-information;
         }
         case multichassis-tag {
           anyxml multi-routing-engine-results;
         }
       }
     }
   }
   rpc get-dhcpv6-client-binding-information-by-interface {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
         }
       }
     }
     output {
       choice output_c {
         case output-tag {
           leaf output {
             type string;
           }
         }
         case actual-tag {
           anyxml dhcpv6-client-binding-information-by-interface;
         }
         case multichassis-tag {
           anyxml multi-routing-engine-results;
         }
       }
     }
   }
   rpc get-dhcpv6-client-statistics-information {
     description "Show DHCPV6 dhcpv6-client statistics";
     input {
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml dhcpv6-client-statistics-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
