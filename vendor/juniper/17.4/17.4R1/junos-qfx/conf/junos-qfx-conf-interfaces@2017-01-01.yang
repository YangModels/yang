/*
 * Copyright (c) 2017 Juniper Networks, Inc.
 * All rights reserved.
 */
 module junos-qfx-conf-interfaces {
   namespace "http://yang.juniper.net/junos-qfx/conf/interfaces";

   prefix jc-interfaces;

   import junos-common-types {
     prefix jt;
   }

   import junos-qfx-conf-root {
     prefix jc;
   }

   organization "Juniper Networks, Inc.";

   contact "yang-support@juniper.net";

   description "Junos interfaces configuration module";

   revision 2017-01-01 {
     description "Junos: 17.4R1.16";
   }

   augment /jc:configuration {
     uses interfaces-group;
   }
   augment /jc:configuration/jc:groups {
     uses interfaces-group;
   }
   grouping interfaces-group {
     container interfaces {
       description "Interface configuration";
       uses apply-advanced;
       list interface-set {
         key name;
         ordered-by user;
         description "Logical interface set configuration";
         leaf name {
           type string;
         }
         uses apply-advanced;
         list interface {
           key name;
           ordered-by user;
           description "One or more interfaces that belong to interface set";
           leaf name {
             description "Interface name";
             type union {
               type jt:interface-device;
               type string {
                 pattern "<.*>|$.*";
               }
             }
           }
           uses apply-advanced;
           list unit {
             key name;
             description "One or more logical interface unit numbers";
             leaf name {
               description "Unit number";
               type union {
                 type string {
                   pattern "<.*>|$.*";
                 }
                 type uint32 {
                   range "0 .. 1073741823";
                 }
               }
             }
             uses apply-advanced;
           }
           list vlan-tags-outer {
             key name;
             description "One or more outer VLAN tags";
             leaf name {
               description "VLAN tag ID";
               type union {
                 type string {
                   pattern "<.*>|$.*";
                 }
                 type uint32 {
                   range "0 .. 4094";
                 }
               }
             }
             uses apply-advanced;
           }
         }
       }
       container traceoptions {
         description "Interface trace options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           description "Tracing parameters";
           leaf name {
             type enumeration {
               enum "all" {
                 description "Enable all configuration logging";
               }
               enum "kernel" {
                 description "Log configuration IPC messages to kernel";
               }
               enum "change-events" {
                 description "Log changes that produce configuration events";
               }
               enum "kernel-detail" {
                 description "Log details of configuration messages to kernel";
               }
               enum "config-states" {
                 description "Log the configuration state machine changes";
               }
               enum "resource-usage" {
                 description "Log the resource usage for different states";
               }
               enum "gres-events" {
                 description "Log the events related to GRES ";
               }
               enum "select-events" {
                 description "Log the events on select state machine ";
               }
               enum "bfd-events" {
                 description "Log BFD related events";
               }
               enum "lib-events" {
                 description "Log DCD library related events";
               }
               enum "reserved" {
                 description "Reserved DCD logs";
               }
               enum "emergency" {
                 description "Log DCD emergency events";
               }
               enum "alert" {
                 description "Log DCD alert events";
               }
               enum "critical" {
                 description "Log DCD critical events";
               }
               enum "error" {
                 description "Log DCD error events";
               }
               enum "warning" {
                 description "Log DCD warning events";
               }
               enum "notice" {
                 description "Log DCD notification events";
               }
               enum "informational" {
                 description "Log DCD informations";
               }
               enum "debugging" {
                 description "Log DCD debug events";
               }
               enum "verbose" {
                 description "Log DCD debug all events";
               }
               enum "japi" {
                 description "Log DCD JAPI events";
               }
             }
           }
           leaf disable {
             description "Disable this trace flag";
             type empty;
           }
         }
       }
       list interface-range {
         key name;
         ordered-by user;
         description "Interface ranges configuration";
         leaf name {
           description "Interface-range name";
           type string {
             length "1 .. 128";
           }
         }
         list member {
           key name;
           ordered-by user;
           description "Interfaces belonging to the interface range";
           leaf name {
             description "Member interface name";
             type union {
               type jt:interface-range-wild;
               type string {
                 pattern "<.*>|$.*";
               }
             }
           }
           uses apply-advanced;
         }
         list member-range {
           key name;
           ordered-by user;
           description "Interfaces range in <start-range> to <end-range> format";
           leaf name {
             type union {
               type jt:interface-device;
               type string {
                 pattern "<.*>|$.*";
               }
             }
           }
           leaf end-range {
             type union {
               type jt:interface-device;
               type string {
                 pattern "<.*>|$.*";
               }
             }
           }
         }
         uses apply-advanced;
         leaf description {
           description "Text description of interface";
           type string;
         }
         leaf metadata {
           description "Text metadata attached to interface";
           type string;
         }
         choice enable-disable {
           case case_1 {
             leaf disable {
               description "Disable this interface";
               type empty;
             }
           }
         }
         container traceoptions {
           presence "enable traceoptions";
           description "Interface trace options";
           uses apply-advanced;
           list flag {
             key name;
             ordered-by user;
             description "Tracing parameters";
             leaf name {
               type enumeration {
                 enum "ipc" {
                   description "Trace interface IPC messages";
                 }
                 enum "event" {
                   description "Trace interface events";
                 }
                 enum "media" {
                   description "Trace interface media changes";
                 }
                 enum "all" {
                   description "Enable all interface trace flags";
                 }
               }
             }
           }
         }
         leaf passive-monitor-mode {
           description "Use interface to tap packets from another router";
           type empty;
         }
         choice keepalive_choices {
           case case_1 {
             container keepalives {
               description "Send or demand keepalive messages";
               uses keepalives_type;
             }
           }
           case case_2 {
             leaf no-keepalives {
               description "Do not send keepalive messages";
               type empty;
             }
           }
         }
         choice traps-choice {
           leaf traps {
             description "Enable SNMP notifications on state changes";
             type empty;
           }
           leaf no-traps {
             description "Don't enable SNMP notifications on state changes";
             type empty;
           }
         }
         choice interface-mib-choice {
           leaf interface-mib {
             description "Enable interface-related MIBs";
             type empty;
           }
           leaf no-interface-mib {
             description "Don't enable interface-related MIBs";
             type empty;
           }
         }
         leaf accounting-profile {
           description "Accounting profile name";
           type string;
         }
         choice scheduler_type {
           case case_1 {
             choice per-unit-scheduler-choice {
               leaf per-unit-scheduler {
                 description "Enable subunit queuing on Frame Relay or VLAN IQ interface";
                 type empty;
               }
               leaf no-per-unit-scheduler {
                 description "Don't enable subunit queuing on Frame Relay or VLAN IQ interface";
                 type empty;
               }
             }
           }
           case case_2 {
             leaf shared-scheduler {
               description "Enabled shared queuing on an IQ2 interface";
               type empty;
             }
           }
           case case_3 {
             container hierarchical-scheduler {
               presence "enable hierarchical-scheduler";
               description "Enable hierarchical scheduling";
               leaf maximum-hierarchy-levels {
                 description "Maximum hierarchy levels";
                 type union {
                   type string {
                     pattern "<.*>|$.*";
                   }
                   type uint32 {
                     range "2 .. 4";
                   }
                 }
               }
               leaf implicit-hierarchy {
                 description "Implicit hierarchy (follows interface hierarchy)";
                 type empty;
               }
             }
           }
         }
         leaf l2tp-maximum-session {
           description "Maximum L2TP session";
           type union {
             type string {
               pattern "<.*>|$.*";
             }
             type uint32 {
               range "0 .. 64000";
             }
           }
         }
         leaf schedulers {
           description "Number of schedulers to allocate for interface";
           type union {
             type uint32;
             type string {
               pattern "<.*>|$.*";
             }
           }
         }
         leaf cascade-port {
           description "Cascade port";
           type empty;
         }
         leaf dce {
           description "Respond to Frame Relay status enquiry messages";
           type empty;
         }
         choice vlan_tag_mode {
           case case_1 {
             leaf vlan-tagging {
               description "802.1q VLAN tagging support";
               type empty;
             }
           }
           case case_2 {
             leaf stacked-vlan-tagging {
               description "Stacked 802.1q VLAN tagging support";
               type empty;
             }
           }
           case case_3 {
             leaf flexible-vlan-tagging {
               description "Support for no tagging, or single and double 802.1q VLAN tagging";
               type empty;
             }
           }
           case case_4 {
             leaf vlan-vci-tagging {
               description "CCC for VLAN Q-in-Q and ATM VPI/VCI interworking";
               type empty;
             }
           }
         }
         leaf native-vlan-id {
           description "Virtual LAN identifier for untagged frames";
           type union {
             type string {
               pattern "<.*>|$.*";
             }
             type uint32 {
               range "0 .. 4094";
             }
           }
         }
         leaf speed {
           description "Link speed";
           type enumeration {
             enum "auto" {
               description "Enable auto negotiation of interface speed";
             }
             enum "auto-10m-100m" {
               description "Enable auto negotiation of limiting interface speed to 10m/100m";
             }
             enum "10m" {
             }
             enum "100m" {
             }
             enum "1g" {
             }
             enum "2.5g" {
             }
             enum "5g" {
             }
             enum "10g" {
             }
             enum "40g" {
             }
             enum "oc3" {
             }
             enum "oc12" {
             }
             enum "oc48" {
             }
           }
         }
         leaf mtu {
           description "Maximum transmit packet size";
           type union {
             type string {
               pattern "<.*>|$.*";
             }
             type uint32;
           }
         }
         container hold-time {
           description "Hold time for link up and link down";
           leaf up {
             description "Link up hold time";
             units "milliseconds";
             type union {
               type uint32;
               type string {
                 pattern "<.*>|$.*";
               }
             }
           }
           leaf down {
             description "Link down hold time";
             units "milliseconds";
             type union {
               type uint32;
               type string {
                 pattern "<.*>|$.*";
               }
             }
           }
         }
         container link-degrade-monitor {
           presence "enable link-degrade-monitor";
           description "Enable link degrade monitoring";
           uses apply-advanced;
           container actions {
             description "Action upon link degrade event";
             uses apply-advanced;
             choice action_choice {
               case case_1 {
                 leaf media-based {
                   description "Media based";
                   type empty;
                 }
               }
             }
           }
           container recovery {
             description "Link degrade recovery mechanism";
             uses apply-advanced;
             leaf timer {
               description "Auto recovery timer in seconds";
               default "1800";
               type union {
                 type uint32;
                 type string {
                   pattern "<.*>|$.*";
                 }
               }
             }
             choice receovery_choice {
               case case_1 {
                 leaf auto {
                   description "Automatic recovery";
                   type empty;
                 }
               }
               case case_2 {
                 leaf manual {
                   description "Manual recovery";
                   type empty;
                 }
               }
             }
           }
           container thresholds {
             description "Link degrade threshold parameters";
             uses apply-advanced;
             leaf set {
               description "BER at which link considered degraded(1..16)";
               default "1e-7";
               type string {
               }
             }
             leaf clear {
               description "BER at which link considered improved(1..16)";
               default "1e-12";
               type string {
               }
             }
             leaf warning-set {
               description "BER at which link degrade warning raised(1..16)";
               default "1e-9";
               type string {
               }
             }
             leaf warning-clear {
               description "BER at which link degrade warning cleared(1..16)";
               default "1e-11";
               type string {
               }
             }
             leaf interval {
               description "Consecutive link degrade events";
               default "10";
               type union {
                 type string {
                   pattern "<.*>|$.*";
                 }
                 type uint32 {
                   range "1 .. 256";
                 }
               }
             }
           }
         }
         container satop-options {
           description "Structure-Agnostic TDM over Packet protocol options";
           uses apply-advanced;
           leaf idle-pattern {
             description "An 8-bit hexadecimal pattern to replace TDM data in a lost packet";
             type union {
               type string {
                 pattern "<.*>|$.*";
               }
               type uint32 {
                 range "0 .. 255";
               }
             }
           }
           leaf payload-size {
             description "Number of payload bytes per packet";
             type union {
               type string {
                 pattern "<.*>|$.*";
               }
               type uint32 {
                 range "64 .. 1024";
               }
             }
           }
           container excessive-packet-loss-rate {
             description "Packet loss options";
             uses apply-advanced;
             leaf threshold {
               description "Percentile designating the threshold of excessive packet loss rate";
               type union {
                 type string {
                   pattern "<.*>|$.*";
                 }
                 type uint8 {
                   range "1 .. 100";
                 }
               }
             }
             leaf sample-period {
               description "Number of milliseconds over which excessive packet loss rate is calculated";
               type union {
                 type string {
                   pattern "<.*>|$.*";
                 }
                 type uint32 {
                   range "1000 .. 65535";
                 }
               }
             }
           }
           choice jitter-buffer-size {
             case case_1 {
               leaf jitter-buffer-packets {
                 description "Number of packets in jitter buffer before packet data is played out in the line";
                 type union {
                   type string {
                     pattern "<.*>|$.*";
                   }
                   type uint32 {
                     range "1 .. 64";
                   }
                 }
               }
             }
             case case_2 {
               leaf jitter-buffer-latency {
                 description "Number of milliseconds delay in jitter buffer before packet data is played out in the line";
                 units "milliseconds";
                 type union {
                   type string {
                     pattern "<.*>|$.*";
                   }
                   type uint32 {
                     range "1 .. 1000";
                   }
                 }
               }
             }
             case case_3 {
               leaf jitter-buffer-auto-adjust {
                 description "Automatically adjust jitter buffer";
                 type empty;
               }
             }
           }
           leaf bit-rate {
             description "In multiples of DS0";
             type union {
               type string {
                 pattern "<.*>|$.*";
               }
               type uint32 {
                 range "1 .. 10240";
               }
             }
           }
         }
         container cesopsn-options {
           description "Structure-Aware TDM over Packet protocol options";
           uses apply-advanced;
           leaf idle-pattern {
             description "An 8-bit hexadecimal pattern to replace TDM data in a lost packet";
             type union {
               type string {
                 pattern "<.*>|$.*";
               }
               type uint32 {
                 range "0 .. 255";
               }
             }
           }
           leaf packetization-latency {
             description "Number of microseconds to create packets";
             units "microseconds";
             type union {
               type string {
                 pattern "<.*>|$.*";
               }
               type uint32 {
                 range "1000 .. 8000";
               }
             }
           }
           leaf payload-size {
             description "Number of payload bytes per packet";
             type union {
               type string {
                 pattern "<.*>|$.*";
               }
               type uint32 {
                 range "64 .. 1024";
               }
             }
           }
           container excessive-packet-loss-rate {
             description "Packet loss options";
             uses apply-advanced;
             leaf threshold {
               description "Percentile designating the threshold of excessive packet loss rate";
               type union {
                 type string {
                   pattern "<.*>|$.*";
                 }
                 type uint8 {
                   range "1 .. 100";
                 }
               }
             }
             leaf sample-period {
               description "Number of milliseconds over which excessive packet loss rate is calculated";
               type union {
                 type string {
                   pattern "<.*>|$.*";
                 }
                 type uint32 {
                   range "1000 .. 65535";
                 }
               }
             }
           }
           choice jitter-buffer-size {
             case case_1 {
               leaf jitter-buffer-packets {
                 description "Number of packets in jitter buffer before packet data is played out in the line";
                 type union {
                   type string {
                     pattern "<.*>|$.*";
                   }
                   type uint32 {
                     range "1 .. 64";
                   }
                 }
               }
             }
             case case_2 {
               leaf jitter-buffer-latency {
                 description "Number of milliseconds delay in jitter buffer before packet data is played out in the line";
                 units "milliseconds";
                 type union {
                   type string {
                     pattern "<.*>|$.*";
                   }
                   type uint32 {
                     range "1 .. 1000";
                   }
                 }
               }
             }
             case case_3 {
               leaf jitter-buffer-auto-adjust {
                 description "Automatically adjust jitter buffer";
                 type empty;
               }
             }
           }
           leaf bit-rate {
             description "In multiples of DS0";
             type union {
               type string {
                 pattern "<.*>|$.*";
               }
               type uint32 {
                 range "1 .. 10240";
               }
             }
           }
         }
         container clocking {
           description "Interface clock source";
           choice clocking_choices {
             case case_1 {
               leaf internal {
                 description "Clocking provided by local system";
                 type empty;
               }
             }
             case case_2 {
               container external {
                 presence "enable external";
                 description "Clocking provided by DCE (loop timing)";
               }
             }
           }
         }
         leaf link-mode {
           description "Link operational mode";
           type enumeration {
             enum "automatic" {
               description "Automatically negotiate duplex";
             }
             enum "half-duplex" {
               description "Half-duplex operation";
             }
             enum "full-duplex" {
               description "Full-duplex operation";
             }
           }
         }
         leaf encapsulation {
           description "Physical link-layer encapsulation";
           type enumeration {
             enum "ethernet" {
               description "Ethernet physical media";
             }
             enum "fddi" {
               description "FDDI physical media";
             }
             enum "token-ring" {
               description "Token Ring physical media";
             }
             enum "ppp" {
               description "Serial PPP device";
             }
             enum "ppp-ccc" {
               description "Serial PPP device for a cross-connect";
             }
             enum "ppp-tcc" {
               description "Serial PPP device for a translational cross-connect";
             }
             enum "ether-vpls-ppp" {
               description "Ethernet VPLS over PPP (bridging) device";
             }
             enum "frame-relay" {
               description "Frame Relay encapsulation";
             }
             enum "frame-relay-ccc" {
               description "Frame Relay for cross-connect";
             }
             enum "frame-relay-tcc" {
               description "Frame Relay for translational cross-connect";
             }
             enum "extended-frame-relay-ccc" {
               description "Any Frame Relay DLCI for cross-connect";
             }
             enum "extended-frame-relay-tcc" {
               description "Any Frame Relay DLCI for translational cross-connect";
             }
             enum "flexible-frame-relay" {
               description "Multiple Frame Relay encapsulations";
             }
             enum "frame-relay-port-ccc" {
               description "Frame Relay port encapsulation for a cross-connect";
             }
             enum "frame-relay-ether-type" {
               description "Cisco-compatible Frame Relay encapsulation";
             }
             enum "frame-relay-ether-type-tcc" {
               description "Cisco-compatible Frame Relay encapsulation for translational cross-connect";
             }
             enum "extended-frame-relay-ether-type-tcc" {
               description "Cisco-compatible Frame Relay encapsulation any DLCI for translational cross-connect";
             }
             enum "cisco-hdlc" {
               description "Cisco-compatible HDLC framing";
             }
             enum "cisco-hdlc-ccc" {
               description "Cisco-compatible HDLC framing for a cross-connect";
             }
             enum "cisco-hdlc-tcc" {
               description "Cisco-compatible HDLC framing for a translational cross-connect";
             }
             enum "vlan-ccc" {
               description "802.1q tagging for a cross-connect";
             }
             enum "extended-vlan-ccc" {
               description "Nonstandard TPID tagging for a cross-connect";
             }
             enum "ethernet-ccc" {
               description "Ethernet cross-connect";
             }
             enum "flexible-ethernet-services" {
               description "Allows per-unit Ethernet encapsulation configuration";
             }
             enum "smds-dxi" {
               description "SMDS DXI framing";
             }
             enum "atm-pvc" {
               description "ATM permanent virtual circuits";
             }
             enum "atm-ccc-cell-relay" {
               description "ATM cell relay encapsulation for cross-connect";
             }
             enum "ethernet-over-atm" {
               description "Ethernet over ATM encapsulation";
             }
             enum "ethernet-tcc" {
               description "Ethernet translational cross-connect";
             }
             enum "extended-vlan-tcc" {
               description "802.1q tagging for a translational cross-connect";
             }
             enum "multilink-frame-relay-uni-nni" {
               description "Multilink Frame Relay UNI NNI (FRF.16) encapsulation";
             }
             enum "satop" {
               description "Structure-Agnostic TDM over Packet encapsulation";
             }
             enum "cesopsn" {
               description "Structure-Agnostic TDM over Packet encapsulation";
             }
             enum "ima" {
               description "Inverse Multiplexing for ATM";
             }
             enum "ethernet-vpls" {
               description "Ethernet virtual private LAN service";
             }
             enum "ethernet-bridge" {
               description "Ethernet layer-2 bridging";
             }
             enum "vlan-vpls" {
               description "VLAN virtual private LAN service";
             }
             enum "vlan-vci-ccc" {
               description "CCC for VLAN Q-in-Q and ATM VPI/VCI interworking";
             }
             enum "extended-vlan-vpls" {
               description "Extended VLAN virtual private LAN service";
             }
             enum "extended-vlan-bridge" {
               description "VLAN layer-2 bridging";
             }
             enum "multilink-ppp" {
               description "Multilink PPP";
             }
             enum "generic-services" {
               description "Generic services";
             }
           }
         }
         container esi {
           description "ESI configuration of multi-homed interface";
           uses apply-advanced;
           leaf identifier {
             description "ESI value for the interface";
             type jt:esi;
           }
           choice mode {
             case case_1 {
               leaf single-active {
                 description "Single-active mode";
                 type empty;
               }
             }
             case case_2 {
               leaf all-active {
                 description "All-active mode";
                 type empty;
               }
             }
           }
           leaf source-bmac {
             description "Unicast Source B-MAC address per ESI for PBB-EVPN";
             type jt:mac-unicast;
           }
         }
         container framing {
           description "Frame type";
           uses apply-advanced;
           choice frame {
             case case_1 {
               leaf lan-phy {
                 description "802.3ae 10-Gbps LAN-mode interface";
                 type empty;
               }
             }
             case case_2 {
               leaf wan-phy {
                 description "802.3ae 10-Gbps WAN-mode interface";
                 type empty;
               }
             }
             case case_3 {
               leaf sonet {
                 description "SONET framing";
                 type empty;
               }
             }
             case case_4 {
               leaf sdh {
                 description "SDH framing";
                 type empty;
               }
             }
           }
         }
         container lmi {
           description "Local Management Interface settings";
           uses apply-advanced;
           leaf n391dte {
             description "DTE full status polling interval";
             type union {
               type string {
                 pattern "<.*>|$.*";
               }
               type uint16 {
                 range "1 .. 255";
               }
             }
           }
           leaf n392dce {
             description "DCE error threshold";
             type union {
               type string {
                 pattern "<.*>|$.*";
               }
               type uint16 {
                 range "1 .. 10";
               }
             }
           }
           leaf n392dte {
             description "DTE error threshold";
             type union {
               type string {
                 pattern "<.*>|$.*";
               }
               type uint16 {
                 range "1 .. 10";
               }
             }
           }
           leaf n393dce {
             description "DCE monitored event count";
             type union {
               type string {
                 pattern "<.*>|$.*";
               }
               type uint16 {
                 range "1 .. 10";
               }
             }
           }
           leaf n393dte {
             description "DTE monitored event count";
             type union {
               type string {
                 pattern "<.*>|$.*";
               }
               type uint16 {
                 range "1 .. 10";
               }
             }
           }
           leaf t391dte {
             description "DTE polling timer";
             units "seconds";
             type union {
               type string {
                 pattern "<.*>|$.*";
               }
               type uint16 {
                 range "5 .. 30";
               }
             }
           }
           leaf t392dce {
             description "DCE polling verification timer";
             units "seconds";
             type union {
               type string {
                 pattern "<.*>|$.*";
               }
               type uint16 {
                 range "5 .. 30";
               }
             }
           }
           leaf lmi-type {
             description "Specify the Frame Relay LMI type";
             type enumeration {
               enum "ansi" {
                 description "Use ANSI Annex D LMI";
               }
               enum "itu" {
                 description "Use ITU Q933a Annex A LMI";
               }
               enum "c-lmi" {
                 description "Use Consortium LMI";
               }
             }
           }
         }
         container mlfr-uni-nni-bundle-options {
           description "Multilink Frame Relay UNI NNI (FRF.16) management settings";
           uses apply-advanced;
           container cisco-interoperability {
             description "FRF.16 Cisco interoperability settings";
             uses apply-advanced;
             leaf send-lip-remove-link-for-link-reject {
               description "Send Link Integrity Protocol remove link on receiving add-link rejection";
               type empty;
             }
           }
           leaf mrru {
             description "Maximum received reconstructed unit";
             units "bytes";
             type union {
               type string {
                 pattern "<.*>|$.*";
               }
               type uint16 {
                 range "1500 .. 4500";
               }
             }
           }
           leaf yellow-differential-delay {
             description "Yellow differential delay among bundle links to give warning";
             units "milliseconds";
             type union {
               type string {
                 pattern "<.*>|$.*";
               }
               type uint16 {
                 range "3 .. 2000";
               }
             }
           }
           leaf red-differential-delay {
             description "Red differential delay among bundle links to take action";
             units "milliseconds";
             type union {
               type string {
                 pattern "<.*>|$.*";
               }
               type uint16 {
                 range "5 .. 2000";
               }
             }
           }
           leaf action-red-differential-delay {
             description "Type of actions when differential delay exceeds red limit";
             type enumeration {
               enum "remove-link" {
                 description "Remove bundle link from service when exceeding red limit";
               }
               enum "disable-tx" {
                 description "Disable transfer of bundle link when exceeding red limit";
               }
             }
           }
           leaf fragment-threshold {
             description "Fragmentation threshold";
             units "bytes";
             type union {
               type string {
                 pattern "<.*>|$.*";
               }
               type uint32 {
                 range "64 .. 16320";
               }
             }
           }
           leaf drop-timeout {
             description "Drop timeout";
             units "milliseconds";
             type union {
               type string {
                 pattern "<.*>|$.*";
               }
               type uint16 {
                 range "0 .. 2000";
               }
             }
           }
           leaf link-layer-overhead {
             description "Link layer bit stuffing overhead (0.0 .. 50.0 percent)";
             type jt:unsigned-float;
           }
           leaf lmi-type {
             description "Specify the multilink Frame Relay UNI NNI LMI type";
             type enumeration {
               enum "ansi" {
                 description "Use ANSI Annex D LMI";
               }
               enum "itu" {
                 description "Use ITU Q933a Annex A LMI";
               }
               enum "c-lmi" {
                 description "Use Consortium LMI";
               }
             }
           }
           leaf minimum-links {
             description "Minimum number of links to sustain the bundle";
             type union {
               type string {
                 pattern "<.*>|$.*";
               }
               type uint16 {
                 range "1 .. 8";
               }
             }
           }
           leaf hello-timer {
             description "LIP hello timer";
             type union {
               type string {
                 pattern "<.*>|$.*";
               }
               type uint16 {
                 range "5 .. 180";
               }
             }
           }
           leaf acknowledge-timer {
             description "LIP ack timer";
             type union {
               type string {
                 pattern "<.*>|$.*";
               }
               type uint16 {
                 range "1 .. 10";
               }
             }
           }
           leaf acknowledge-retries {
             description "LIP ack retry times";
             type union {
               type string {
                 pattern "<.*>|$.*";
               }
               type uint16 {
                 range "1 .. 5";
               }
             }
           }
           leaf n391 {
             description "Multilink Frame Relay UNI NNI full status polling counter";
             type union {
               type string {
                 pattern "<.*>|$.*";
               }
               type uint16 {
                 range "1 .. 255";
               }
             }
           }
           leaf n392 {
             description "Multilink Frame Relay UNI NNI LMI error threshold";
             type union {
               type string {
                 pattern "<.*>|$.*";
               }
               type uint16 {
                 range "1 .. 10";
               }
             }
           }
           leaf n393 {
             description "Multilink Frame Relay UNI NNI LMI monitored event count";
             type union {
               type string {
                 pattern "<.*>|$.*";
               }
               type uint16 {
                 range "1 .. 10";
               }
             }
           }
           leaf t391 {
             description "Multilink Frame Relay UNI NNI link integrity verify polling timer";
             type union {
               type string {
                 pattern "<.*>|$.*";
               }
               type uint16 {
                 range "5 .. 30";
               }
             }
           }
           leaf t392 {
             description "Multilink Frame Relay UNI NNI polling verification timer";
             type union {
               type string {
                 pattern "<.*>|$.*";
               }
               type uint16 {
                 range "5 .. 30";
               }
             }
           }
         }
         leaf mac {
           description "Hardware MAC address";
           type jt:mac-unicast;
         }
         container receive-bucket {
           description "Set receive bucket parameters";
           uses dcd_rx_bucket_config;
         }
         container transmit-bucket {
           description "Set transmit bucket parameters";
           uses dcd_tx_bucket_config;
         }
         leaf shared-interface {
           description "Enable shared interface on the interface";
           type empty;
         }
         container sonet-options {
           description "SONET interface-specific options";
           uses sonet_options_type;
         }
         container logical-tunnel-options {
           description "Logical Tunnel interface-specific options";
           uses apply-advanced;
           container link-protection {
             presence "enable link-protection";
             description "Enable link protection mode";
             uses apply-advanced;
             leaf revertive {
               description "Revert back (Default mode) from active backup link to primary, if primary is UP";
               type empty;
             }
             leaf non-revertive {
               description "Do not revert back from active backup link to primary, if primary is UP";
               type empty;
             }
           }
           leaf per-unit-mac-disable {
             description "Disable the creation of per unit mac address on LT IFLs for VPLS/CCC encaps";
             type empty;
           }
         }
         container aggregated-sonet-options {
           description "Aggregated SONET interface-specific options";
           uses apply-advanced;
           leaf minimum-links {
             description "Minimum number of aggregated links";
             type union {
               type string {
                 pattern "<.*>|$.*";
               }
               type uint16;
             }
           }
           leaf link-speed {
             description "Aggregated links speed";
             type enumeration {
               enum "oc3" {
                 description "Links are OC-3c or STM-1c";
               }
               enum "oc12" {
                 description "Links are OC-12c or STM-4c";
               }
               enum "oc48" {
                 description "Links are OC-48c or STM-16c";
               }
               enum "oc192" {
                 description "Links are OC-192c or STM-64c";
               }
               enum "oc768" {
                 description "Links are OC-768c or STM-256c";
               }
               enum "mixed" {
                 description "Links are various speeds";
               }
             }
           }
           leaf minimum-bandwidth {
             description "Minimum bandwidth necessary to sustain bundle";
             units "bps";
             type union {
               type string {
                 pattern "<.*>|$.*";
               }
               type uint64 {
                 range "0 .. 159232000000";
               }
             }
           }
         }
         container atm-options {
           description "ATM interface-specific options";
           uses apply-advanced;
           leaf pic-type {
             description "Type of ATM PIC (ATM I, ATM II or ATM CE)";
             type enumeration {
               enum "atm-ce" {
                 description "CE PIC";
               }
               enum "atm2" {
                 description "ATM II IQ PIC";
               }
               enum "atm1" {
                 description "ATM I PIC";
               }
             }
           }
           leaf cell-bundle-size {
             description "L2 circuit cell bundle size";
             units "cells";
             type union {
               type string {
                 pattern "<.*>|$.*";
               }
               type uint32 {
                 range "1 .. 176";
               }
             }
           }
           leaf cell-bundle-timeout {
             description "L2 circuit cell bundle timeout";
             units "microseconds";
             type union {
               type string {
                 pattern "<.*>|$.*";
               }
               type uint32 {
                 range "1 .. 512";
               }
             }
           }
           leaf plp-to-clp {
             description "Enable ATM2 PLP to CLP copy";
             type empty;
           }
           leaf use-null-cw {
             description "Always insert/strip null control words with cell-relay";
             type empty;
           }
           container promiscuous-mode {
             presence "enable promiscuous-mode";
             description "Set ATM interface to promiscuous mode";
             uses apply-advanced;
             list vpi {
               key name;
               ordered-by user;
               description "Open this VPI in promiscuous mode";
               leaf name {
                 description "Virtual path index";
                 type union {
                   type string {
                     pattern "<.*>|$.*";
                   }
                   type uint32 {
                     range "0 .. 255";
                   }
                 }
               }
             }
           }
           list vpi {
             key name;
             ordered-by user;
             description "Define a virtual path";
             leaf name {
               description "Virtual path index";
               type union {
                 type string {
                   pattern "<.*>|$.*";
                 }
                 type uint32 {
                   range "0 .. 255";
                 }
               }
             }
             uses apply-advanced;
             leaf maximum-vcs {
               description "Maximum number of virtual circuits on this VP";
               type union {
                 type uint32;
                 type string {
                   pattern "<.*>|$.*";
                 }
               }
             }
             container shaping {
               description "Virtual path traffic-shaping options";
               uses dcd_shaping_config;
             }
             container oam-period {
               description "F4 OAM cell period";
               choice oam_period_choices {
                 case case_1 {
                   leaf oam-period {
                     description "F4 OAM cell period";
                     units "seconds";
                     type union {
                       type string {
                         pattern "<.*>|$.*";
                       }
                       type uint32 {
                         range "1 .. 900";
                       }
                     }
                   }
                 }
                 case case_2 {
                   container disable {
                     presence "enable disable";
                     description "Disable F4 OAM loopback";
                   }
                 }
               }
             }
             container oam-liveness {
               description "F4 OAM virtual path liveness parameters";
               uses apply-advanced;
               leaf up-count {
                 description "Number of F4 OAM cells to consider VP up";
                 type union {
                   type string {
                     pattern "<.*>|$.*";
                   }
                   type uint32 {
                     range "1 .. 255";
                   }
                 }
               }
               leaf down-count {
                 description "Number of F4 OAM cells to consider VP down";
                 type union {
                   type string {
                     pattern "<.*>|$.*";
                   }
                   type uint32 {
                     range "1 .. 255";
                   }
                 }
               }
             }
           }
           container ilmi {
             presence "enable ilmi";
             description "Enable Interim Local Management Interface";
             uses apply-advanced;
           }
           list linear-red-profiles {
             key name;
             ordered-by user;
             description "ATM2 CoS virtual circuit drop profiles";
             leaf name {
               description "Linear RED profile name";
               type string {
               }
             }
             leaf queue-depth {
               description "Maximum queue depth";
               units "cells";
               type string;
             }
             leaf high-plp-threshold {
               description "Fill level percentage when linear RED is applied for high PLP";
               type union {
                 type string {
                   pattern "<.*>|$.*";
                 }
                 type uint32 {
                   range "0 .. 100";
                 }
               }
             }
             leaf low-plp-threshold {
               description "Fill level percentage when linear RED is applied for low PLP";
               type union {
                 type string {
                   pattern "<.*>|$.*";
                 }
                 type uint32 {
                   range "0 .. 100";
                 }
               }
             }
             leaf high-plp-max-threshold {
               description "Fill level percentage with 100 percent packet drop for high PLP";
               type union {
                 type string {
                   pattern "<.*>|$.*";
                 }
                 type uint32 {
                   range "0 .. 100";
                 }
               }
             }
             leaf low-plp-max-threshold {
               description "Fill level percentage with 100 percent packet drop for low PLP";
               type union {
                 type string {
                   pattern "<.*>|$.*";
                 }
                 type uint32 {
                   range "0 .. 100";
                 }
               }
             }
           }
           list scheduler-maps {
             key name;
             ordered-by user;
             description "ATM2 CoS parameters assigned to forwarding classes";
             leaf name {
               description "ATM2 CoS scheduler map name";
               type string {
               }
             }
             uses apply-advanced;
             leaf vc-cos-mode {
               description "ATM2 virtual circuit CoS mode";
               type enumeration {
                 enum "strict" {
                   description "Always schedule high priority queue first";
                 }
                 enum "alternate" {
                   description "Every other packet from high priority queue (default)";
                 }
               }
             }
             list forwarding-class {
               key name;
               ordered-by user;
               description "Scheduling parameters associated with forwarding class";
               leaf name {
                 description "Forwarding class name";
                 type string {
                 }
               }
               uses apply-advanced;
               leaf priority {
                 description "Queuing priority assigned to forwarding class";
                 type enumeration {
                   enum "low" {
                     description "Low priority queuing";
                   }
                   enum "high" {
                     description "High priority queuing";
                   }
                 }
               }
               container transmit-weight {
                 description "Transmit weight";
                 choice weight-method {
                   case case_1 {
                     leaf percent {
                       description "Transmit weight as percentage";
                       type union {
                         type string {
                           pattern "<.*>|$.*";
                         }
                         type uint32 {
                           range "5 .. 100";
                         }
                       }
                     }
                   }
                   case case_2 {
                     leaf cells {
                       description "Transmit weight by cells count";
                       type string;
                     }
                   }
                 }
               }
               choice drop-profile-method {
                 case case_1 {
                   container epd-threshold {
                     description "Early packet discard threshold for ATM2";
                     uses epd_threshold_config;
                   }
                 }
                 case case_2 {
                   leaf linear-red-profile {
                     description "Linear RED profile profile name";
                     type string;
                   }
                 }
               }
             }
           }
           container mpls {
             description "MPLS options";
             uses mpls_ifd_options;
           }
           choice payload-scrambler-choice {
             leaf payload-scrambler {
               description "Enable payload scrambling";
               type empty;
             }
             leaf no-payload-scrambler {
               description "Don't enable payload scrambling";
               type empty;
             }
           }
         }
         container multiservice-options {
           description "Multiservice interface-specific options";
           uses apply-advanced;
           choice syslog-choice {
             leaf syslog {
               description "Enable system logging on this interface";
               type empty;
             }
             leaf no-syslog {
               description "Don't enable system logging on this interface";
               type empty;
             }
           }
           choice core-dump-choice {
             leaf core-dump {
               description "Enable core dumping on this interface";
               type empty;
             }
             leaf no-core-dump {
               description "Don't enable core dumping on this interface";
               type empty;
             }
           }
           choice dump-on-flow-control-choice {
             leaf dump-on-flow-control {
               description "Enable dumping for this interface on prolonged flow-control";
               status deprecated;
               type empty;
             }
             leaf no-dump-on-flow-control {
               description "Don't enable dumping for this interface on prolonged flow-control";
               status deprecated;
               type empty;
             }
           }
           choice reset-on-flow-control-choice {
             leaf reset-on-flow-control {
               description "Enable resetting this interface on prolonged flow-control";
               status deprecated;
               type empty;
             }
             leaf no-reset-on-flow-control {
               description "Don't enable resetting this interface on prolonged flow-control";
               status deprecated;
               type empty;
             }
           }
           container flow-control-options {
             description "Flow control configuration";
             uses apply-advanced;
             leaf dump-on-flow-control {
               description "Cause core dump during prolonged flow-control";
               type empty;
             }
             leaf reset-on-flow-control {
               description "Reset interface during prolonged flow-control";
               type empty;
             }
             leaf down-on-flow-control {
               description "Bring interface down during prolonged flow-control";
               type empty;
             }
           }
         }
         container ggsn-options {
           description "GGSN interface-specific options";
           uses apply-advanced;
           choice syslog-choice {
             leaf syslog {
               description "Enable system logging on this interface";
               type empty;
             }
             leaf no-syslog {
               description "Don't enable system logging on this interface";
               type empty;
             }
           }
           choice core-dump-choice {
             leaf core-dump {
               description "Enable core dumping on this interface";
               type empty;
             }
             leaf no-core-dump {
               description "Don't enable core dumping on this interface";
               type empty;
             }
           }
         }
         container ppp-options {
           description "Point-to-Point Protocol (PPP) interface-specific options";
           uses ppp_options_type;
         }
         container redundancy-options {
           description "Redundancy options";
           uses apply-advanced;
           leaf primary {
             description "Specify the primary interface";
             type union {
               type jt:interface-device;
               type string {
                 pattern "<.*>|$.*";
               }
             }
           }
           leaf secondary {
             description "Specify the secondary interface";
             type union {
               type jt:interface-device;
               type string {
                 pattern "<.*>|$.*";
               }
             }
           }
           container redundancy-peer {
             description "Specify information for peer";
             uses apply-advanced;
             leaf ipaddress {
               description "Specify the IP address";
               type jt:ipv4addr;
             }
           }
           container redundancy-local {
             description "Specify information for the local peer";
             uses apply-advanced;
             leaf data-address {
               description "Specify the HA local data IP address";
               type jt:ipv4addr;
             }
           }
           leaf routing-instance {
             description "Specify routing-instance for the HA traffic";
             type string;
           }
           leaf replication-threshold {
             description "Duration for which flow should remain active for replication";
             default "180";
             units "seconds";
             type union {
               type string {
                 pattern "<.*>|$.*";
               }
               type uint32 {
                 range "60 .. 3600";
               }
             }
           }
           container replication-options {
             description "Specify state replication attributes";
             uses apply-advanced;
             leaf mtu {
               description "Specify the maximal packet size for replicated data";
               default "1500";
               type union {
                 type string {
                   pattern "<.*>|$.*";
                 }
                 type uint32 {
                   range "1500 .. 8000";
                 }
               }
             }
           }
           container replicate-services {
             description "Replicate services state from active to backup";
             uses apply-advanced;
             leaf pgcp {
               description "Replicate the PGCP service state";
               type empty;
             }
           }
         }
         container lsq-failure-options {
           description "Link services queuing failure options";
           uses apply-advanced;
           list trigger-link-failure {
             key name;
             ordered-by user;
             description "Link on which to trigger failure";
             leaf name {
               description "Interface name";
               type union {
                 type jt:interface-device;
                 type string {
                   pattern "<.*>|$.*";
                 }
               }
             }
             uses apply-advanced;
           }
           choice no-termination-request-choice {
             leaf no-termination-request {
               description "Do not send PPP termination requests";
               type empty;
             }
             leaf no-no-termination-request {
               description "Don't do not send PPP termination requests";
               type empty;
             }
           }
         }
         container services-options {
           description "Services interface-specific options";
           uses apply-advanced;
           container syslog {
             description "Define system log parameters";
             uses service_set_syslog_object;
           }
           container jflow-log {
             description "Define Jflow-log parameters.";
             uses apply-advanced;
             leaf message-rate-limit {
               description "Maximum jflow-log NAT error events allowed per second from this interface";
               units "messages per second";
               type union {
                 type string {
                   pattern "<.*>|$.*";
                 }
                 type uint32 {
                   range "1 .. 2147483647";
                 }
               }
             }
           }
           container deterministic-nat-configuration-log-interval {
             presence "enable deterministic-nat-configuration-log-interval";
             description "Define Deterministic NAT parameters";
             uses apply-advanced;
             leaf interval {
               description "Interval in which deterministic NAT logs are generated";
               units "seconds";
               type union {
                 type string {
                   pattern "<.*>|$.*";
                 }
                 type uint32 {
                   range "1800 .. 86400";
                 }
               }
             }
           }
           leaf open-timeout {
             description "Timeout period for TCP session establishment";
             units "seconds";
             type union {
               type string {
                 pattern "<.*>|$.*";
               }
               type uint32 {
                 range "4 .. 300";
               }
             }
           }
           leaf close-timeout {
             description "Timeout period for TCP session tear-down";
             units "seconds";
             type union {
               type string {
                 pattern "<.*>|$.*";
               }
               type uint32 {
                 range "2 .. 300";
               }
             }
           }
           leaf inactivity-timeout {
             description "Inactivity timeout period for established sessions (4..86400)";
             units "seconds";
             type union {
               type uint32;
               type string {
                 pattern "<.*>|$.*";
               }
             }
           }
           leaf inactivity-tcp-timeout {
             description "Inactivity timeout period for TCP established sessions";
             units "seconds";
             type union {
               type string {
                 pattern "<.*>|$.*";
               }
               type uint32 {
                 range "4 .. 86400";
               }
             }
           }
           leaf inactivity-asymm-tcp-timeout {
             description "Inactivity timeout period for asymmetric TCP established sessions";
             units "seconds";
             type union {
               type string {
                 pattern "<.*>|$.*";
               }
               type uint32 {
                 range "4 .. 86400";
               }
             }
           }
           leaf inactivity-non-tcp-timeout {
             description "Inactivity timeout period for non-TCP established sessions";
             units "seconds";
             type union {
               type string {
                 pattern "<.*>|$.*";
               }
               type uint32 {
                 range "4 .. 86400";
               }
             }
           }
           leaf session-timeout {
             description "Session timeout period for established sessions";
             units "seconds";
             type union {
               type string {
                 pattern "<.*>|$.*";
               }
               type uint32 {
                 range "4 .. 86400";
               }
             }
           }
           leaf disable-global-timeout-override {
             description "Disallow overriding  global inactivity or session timeout";
             type empty;
           }
           leaf tcp-tickles {
             description "Number of TCP keep-alive packets to be sent for bi-directional TCP flows";
             default "4";
             type union {
               type string {
                 pattern "<.*>|$.*";
               }
               type uint8 {
                 range "0 .. 30";
               }
             }
           }
           leaf fragment-limit {
             description "Maximum number of fragments allowed for a packet";
             default "250";
             type union {
               type string {
                 pattern "<.*>|$.*";
               }
               type uint8 {
                 range "1 .. 250";
               }
             }
           }
           leaf reassembly-timeout {
             description "Re-assembly timeout (seconds) for fragments of a packet";
             default "4";
             units "seconds";
             type union {
               type string {
                 pattern "<.*>|$.*";
               }
               type uint8 {
                 range "1 .. 60";
               }
             }
           }
           leaf cgn-pic {
             description "PIC will be used for Carrier Grade NAT configuration only";
             type empty;
           }
           leaf pba-interim-logging-interval {
             description "Interim logging interval in seconds";
             default "0";
             units "seconds";
             type union {
               type string {
                 pattern "<.*>|$.*";
               }
               type uint32 {
                 range "0 .. 86400";
               }
             }
           }
           container session-limit {
             presence "enable session-limit";
             description "Session limit";
             uses apply-advanced;
             leaf maximum {
               description "Maximum number of sessions allowed simultaneously";
               type string;
             }
             leaf rate {
               description "Maximum number of new sessions allowed per second";
               type string;
             }
             leaf cpu-load-threshold {
               description "CPU limit in percentage for auto-tuning of session rate";
               units "percent";
               type union {
                 type string {
                   pattern "<.*>|$.*";
                 }
                 type uint8 {
                   range "1 .. 100";
                 }
               }
             }
           }
           container ignore-errors {
             presence "enable ignore-errors";
             description "Ignore anomalies or errors";
             leaf tcp {
               description "TCP protocol errors";
               type empty;
             }
             leaf alg {
               description "ALG anomalies or errors";
               type empty;
             }
           }
           container capture {
             description "Packet capture for SFW and NAT on the Services PIC";
             uses apply-advanced;
             leaf capture-size {
               description "The number of packets to store";
               type union {
                 type string {
                   pattern "<.*>|$.*";
                 }
                 type uint32 {
                   range "1 .. 344000";
                 }
               }
             }
             leaf pkt-size {
               description "Number of bytes to be saved from each packet";
               type union {
                 type string {
                   pattern "<.*>|$.*";
                 }
                 type uint16 {
                   range "64 .. 15000";
                 }
               }
             }
             leaf logs-per-packet {
               description "The number of trace messages stored for each packet";
               type union {
                 type string {
                   pattern "<.*>|$.*";
                 }
                 type uint16 {
                   range "0 .. 500";
                 }
               }
             }
             leaf max-log-line-size {
               description "The maximum length of a stored trace message";
               type union {
                 type uint8;
                 type string {
                   pattern "<.*>|$.*";
                 }
               }
             }
             container filter {
               presence "enable filter";
               description "Filtering options for the packet capture";
               uses apply-advanced;
               container source-ip {
                 description "Filter based on source-ip (and wildcard)";
                 leaf ip {
                   description "Source IP";
                   type jt:ipaddr;
                 }
                 leaf wildcard {
                   description "Source IP wildcard";
                   type jt:ipaddr;
                 }
               }
               container dest-ip {
                 description "Filter based on dest-ip (and wildcard)";
                 leaf ip {
                   description "Dest IP";
                   type jt:ipaddr;
                 }
                 leaf wildcard {
                   description "Dest IP wildcard";
                   type jt:ipaddr;
                 }
               }
               container sw-sip {
                 description "Filter based on source softwire ip (and wildcard)";
                 leaf ip {
                   description "Source softwire IP";
                   type jt:ipv6addr;
                 }
                 leaf wildcard {
                   description "Source IP wildcard";
                   type jt:ipv6addr;
                 }
               }
               container sw-dip {
                 description "Filter based on destination softwire ip (and wildcard)";
                 leaf ip {
                   description "Destination softwire IP";
                   type jt:ipaddr;
                 }
                 leaf wildcard {
                   description "Destination IP wildcard";
                   type jt:ipaddr;
                 }
               }
               container sport-range {
                 description "Filter based on source port";
                 leaf low {
                   description "Source port range start";
                   type union {
                     type uint16;
                     type string {
                       pattern "<.*>|$.*";
                     }
                   }
                 }
                 leaf high {
                   description "Source port range end";
                   type union {
                     type uint16;
                     type string {
                       pattern "<.*>|$.*";
                     }
                   }
                 }
               }
               container dport-range {
                 description "Filter based on destination port";
                 leaf low {
                   description "Destination port range start";
                   type union {
                     type uint16;
                     type string {
                       pattern "<.*>|$.*";
                     }
                   }
                 }
                 leaf high {
                   description "Destination port range end";
                   type union {
                     type uint16;
                     type string {
                       pattern "<.*>|$.*";
                     }
                   }
                 }
               }
               leaf proto {
                 description "Filter based on L4 protocol";
                 type enumeration {
                   enum "icmp" {
                   }
                   enum "tcp" {
                   }
                   enum "udp" {
                   }
                 }
               }
             }
           }
         }
         container t3-options {
           description "T3 interface-specific options";
           uses apply-advanced;
           leaf loopback {
             description "Loopback mode";
             type enumeration {
               enum "local" {
                 description "Local loopback";
               }
               enum "remote" {
                 description "Remote loopback";
               }
               enum "payload" {
                 description "Payload loopback";
               }
             }
           }
           choice long-buildout-choice {
             leaf long-buildout {
               description "Set hardware to drive line longer than 255 feet";
               type empty;
             }
             leaf no-long-buildout {
               description "Don't set hardware to drive line longer than 255 feet";
               type empty;
             }
           }
           choice loop-timing-choice {
             leaf loop-timing {
               description "Set loop timing for T3";
               type empty;
             }
             leaf no-loop-timing {
               description "Don't set loop timing for T3";
               type empty;
             }
           }
           container compatibility-mode {
             description "Set CSU compatibility mode";
             choice vendor {
               case case_1 {
                 container larscom {
                   presence "enable larscom";
                   description "Compatible with Larscom CSU";
                   leaf subrate {
                     description "Set subrate value";
                     type union {
                       type string {
                         pattern "<.*>|$.*";
                       }
                       type uint32 {
                         range "1 .. 14";
                       }
                     }
                   }
                 }
               }
               case case_2 {
                 container verilink {
                   presence "enable verilink";
                   description "Compatible with Verilink CSU (not on 2/4-port T3 PIC)";
                   leaf subrate {
                     description "Set subrate value";
                     type union {
                       type string {
                         pattern "<.*>|$.*";
                       }
                       type uint32 {
                         range "1 .. 28";
                       }
                     }
                   }
                 }
               }
               case case_3 {
                 container adtran {
                   presence "enable adtran";
                   description "Compatible with Adtran CSU (not on 2/4-port T3 PIC)";
                   leaf subrate {
                     description "Set subrate value";
                     type union {
                       type string {
                         pattern "<.*>|$.*";
                       }
                       type uint32 {
                         range "1 .. 588";
                       }
                     }
                   }
                 }
               }
               case case_4 {
                 container kentrox {
                   presence "enable kentrox";
                   description "Compatible with Kentrox CSU";
                   leaf subrate {
                     description "Set subrate value (not on 2/4-port T3 PIC)";
                     type union {
                       type string {
                         pattern "<.*>|$.*";
                       }
                       type uint32 {
                         range "1 .. 69";
                       }
                     }
                   }
                 }
               }
               case case_5 {
                 container digital-link {
                   presence "enable digital-link";
                   description "Compatible with Digital Link CSU";
                   leaf subrate {
                     description "Set subrate value";
                     type enumeration {
                       enum "301Kb" {
                         description "301 Kbps";
                       }
                       enum "601Kb" {
                         description "601 Kbps";
                       }
                       enum "902Kb" {
                         description "902 Kbps";
                       }
                       enum "1.2Mb" {
                         description "1.2 Mbps";
                       }
                       enum "1.5Mb" {
                         description "1.5 Mbps";
                       }
                       enum "1.8Mb" {
                         description "1.8 Mbps";
                       }
                       enum "2.1Mb" {
                         description "2.1 Mbps";
                       }
                       enum "2.4Mb" {
                         description "2.4 Mbps";
                       }
                       enum "2.7Mb" {
                         description "2.7 Mbps";
                       }
                       enum "3.0Mb" {
                         description "3.0 Mbps";
                       }
                       enum "3.3Mb" {
                         description "3.3 Mbps";
                       }
                       enum "3.6Mb" {
                         description "3.6 Mbps";
                       }
                       enum "3.9Mb" {
                         description "3.9 Mbps";
                       }
                       enum "4.2Mb" {
                         description "4.2 Mbps";
                       }
                       enum "4.5Mb" {
                         description "4.5 Mbps";
                       }
                       enum "4.8Mb" {
                         description "4.8 Mbps";
                       }
                       enum "5.1Mb" {
                         description "5.1 Mbps";
                       }
                       enum "5.4Mb" {
                         description "5.4 Mbps";
                       }
                       enum "5.7Mb" {
                         description "5.7 Mbps";
                       }
                       enum "6.0Mb" {
                         description "6.0 Mbps";
                       }
                       enum "6.3Mb" {
                         description "6.3 Mbps";
                       }
                       enum "6.6Mb" {
                         description "6.6 Mbps";
                       }
                       enum "6.9Mb" {
                         description "6.9 Mbps";
                       }
                       enum "7.2Mb" {
                         description "7.2 Mbps";
                       }
                       enum "7.5Mb" {
                         description "7.5 Mbps";
                       }
                       enum "7.8Mb" {
                         description "7.8 Mbps";
                       }
                       enum "8.1Mb" {
                         description "8.1 Mbps";
                       }
                       enum "8.4Mb" {
                         description "8.4 Mbps";
                       }
                       enum "8.7Mb" {
                         description "8.7 Mbps";
                       }
                       enum "9.0Mb" {
                         description "9.0 Mbps";
                       }
                       enum "9.3Mb" {
                         description "9.3 Mbps";
                       }
                       enum "9.6Mb" {
                         description "9.6 Mbps";
                       }
                       enum "9.9Mb" {
                         description "9.9 Mbps";
                       }
                       enum "10.2Mb" {
                         description "10.2 Mbps";
                       }
                       enum "10.5Mb" {
                         description "10.5 Mbps";
                       }
                       enum "10.8Mb" {
                         description "10.8 Mbps";
                       }
                       enum "11.1Mb" {
                         description "11.1 Mbps";
                       }
                       enum "11.4Mb" {
                         description "11.4 Mbps";
                       }
                       enum "11.7Mb" {
                         description "11.7 Mbps";
                       }
                       enum "12.0Mb" {
                         description "12.0 Mbps";
                       }
                       enum "12.3Mb" {
                         description "12.3 Mbps";
                       }
                       enum "12.6Mb" {
                         description "12.6 Mbps";
                       }
                       enum "12.9Mb" {
                         description "12.9 Mbps";
                       }
                       enum "13.2Mb" {
                         description "13.2 Mbps";
                       }
                       enum "13.5Mb" {
                         description "13.5 Mbps";
                       }
                       enum "13.8Mb" {
                         description "13.8 Mbps";
                       }
                       enum "14.1Mb" {
                         description "14.1 Mbps";
                       }
                       enum "14.4Mb" {
                         description "14.4 Mbps";
                       }
                       enum "14.7Mb" {
                         description "14.7 Mbps";
                       }
                       enum "15.0Mb" {
                         description "15.0 Mbps";
                       }
                       enum "15.3Mb" {
                         description "15.3 Mbps";
                       }
                       enum "15.6Mb" {
                         description "15.6 Mbps";
                       }
                       enum "15.9Mb" {
                         description "15.9 Mbps";
                       }
                       enum "16.2Mb" {
                         description "16.2 Mbps";
                       }
                       enum "16.5Mb" {
                         description "16.5 Mbps";
                       }
                       enum "16.8Mb" {
                         description "16.8 Mbps";
                       }
                       enum "17.1Mb" {
                         description "17.1 Mbps";
                       }
                       enum "17.4Mb" {
                         description "17.4 Mbps";
                       }
                       enum "17.7Mb" {
                         description "17.7 Mbps";
                       }
                       enum "18.0Mb" {
                         description "18.0 Mbps";
                       }
                       enum "18.3Mb" {
                         description "18.3 Mbps";
                       }
                       enum "18.6Mb" {
                         description "18.6 Mbps";
                       }
                       enum "18.9Mb" {
                         description "18.9 Mbps";
                       }
                       enum "19.2Mb" {
                         description "19.2 Mbps";
                       }
                       enum "19.5Mb" {
                         description "19.5 Mbps";
                       }
                       enum "19.8Mb" {
                         description "19.8 Mbps";
                       }
                       enum "20.1Mb" {
                         description "20.1 Mbps";
                       }
                       enum "20.5Mb" {
                         description "20.5 Mbps";
                       }
                       enum "20.8Mb" {
                         description "20.8 Mbps";
                       }
                       enum "21.1Mb" {
                         description "21.1 Mbps";
                       }
                       enum "21.4Mb" {
                         description "21.4 Mbps";
                       }
                       enum "21.7Mb" {
                         description "21.7 Mbps";
                       }
                       enum "22.0Mb" {
                         description "22.0 Mbps";
                       }
                       enum "22.3Mb" {
                         description "22.3 Mbps";
                       }
                       enum "22.6Mb" {
                         description "22.6 Mbps";
                       }
                       enum "22.9Mb" {
                         description "22.9 Mbps";
                       }
                       enum "23.2Mb" {
                         description "23.2 Mbps";
                       }
                       enum "23.5Mb" {
                         description "23.5 Mbps";
                       }
                       enum "23.8Mb" {
                         description "23.8 Mbps";
                       }
                       enum "24.1Mb" {
                         description "24.1 Mbps";
                       }
                       enum "24.4Mb" {
                         description "24.4 Mbps";
                       }
                       enum "24.7Mb" {
                         description "24.7 Mbps";
                       }
                       enum "25.0Mb" {
                         description "25.0 Mbps";
                       }
                       enum "25.3Mb" {
                         description "25.3 Mbps";
                       }
                       enum "25.6Mb" {
                         description "25.6 Mbps";
                       }
                       enum "25.9Mb" {
                         description "25.9 Mbps";
                       }
                       enum "26.2Mb" {
                         description "26.2 Mbps";
                       }
                       enum "26.5Mb" {
                         description "26.5 Mbps";
                       }
                       enum "26.8Mb" {
                         description "26.8 Mbps";
                       }
                       enum "27.1Mb" {
                         description "27.1 Mbps";
                       }
                       enum "27.4Mb" {
                         description "27.4 Mbps";
                       }
                       enum "27.7Mb" {
                         description "27.7 Mbps";
                       }
                       enum "28.0Mb" {
                         description "28.0 Mbps";
                       }
                       enum "28.3Mb" {
                         description "28.3 Mbps";
                       }
                       enum "28.6Mb" {
                         description "28.6 Mbps";
                       }
                       enum "28.9Mb" {
                         description "28.9 Mbps";
                       }
                       enum "29.2Mb" {
                         description "29.2 Mbps";
                       }
                       enum "29.5Mb" {
                         description "29.5 Mbps";
                       }
                       enum "29.8Mb" {
                         description "29.8 Mbps";
                       }
                       enum "30.1Mb" {
                         description "30.1 Mbps";
                       }
                       enum "30.4Mb" {
                         description "30.4 Mbps";
                       }
                       enum "30.7Mb" {
                         description "30.7 Mbps";
                       }
                       enum "31.0Mb" {
                         description "31.0 Mbps";
                       }
                       enum "31.3Mb" {
                         description "31.3 Mbps";
                       }
                       enum "31.6Mb" {
                         description "31.6 Mbps";
                       }
                       enum "31.9Mb" {
                         description "31.9 Mbps";
                       }
                       enum "32.2Mb" {
                         description "32.2 Mbps";
                       }
                       enum "32.5Mb" {
                         description "32.5 Mbps";
                       }
                       enum "32.8Mb" {
                         description "32.8 Mbps";
                       }
                       enum "33.1Mb" {
                         description "33.1 Mbps";
                       }
                       enum "33.4Mb" {
                         description "33.4 Mbps";
                       }
                       enum "33.7Mb" {
                         description "33.7 Mbps";
                       }
                       enum "34.0Mb" {
                         description "34.0 Mbps";
                       }
                       enum "34.3Mb" {
                         description "34.3 Mbps";
                       }
                       enum "34.6Mb" {
                         description "34.6 Mbps";
                       }
                       enum "34.9Mb" {
                         description "34.9 Mbps";
                       }
                       enum "35.2Mb" {
                         description "35.2 Mbps";
                       }
                       enum "35.5Mb" {
                         description "35.5 Mbps";
                       }
                       enum "35.8Mb" {
                         description "35.8 Mbps";
                       }
                       enum "36.1Mb" {
                         description "36.1 Mbps";
                       }
                       enum "36.4Mb" {
                         description "36.4 Mbps";
                       }
                       enum "36.7Mb" {
                         description "36.7 Mbps";
                       }
                       enum "37.0Mb" {
                         description "37.0 Mbps";
                       }
                       enum "37.3Mb" {
                         description "37.3 Mbps";
                       }
                       enum "37.6Mb" {
                         description "37.6 Mbps";
                       }
                       enum "37.9Mb" {
                         description "37.9 Mbps";
                       }
                       enum "38.2Mb" {
                         description "38.2 Mbps";
                       }
                       enum "38.5Mb" {
                         description "38.5 Mbps";
                       }
                       enum "38.8Mb" {
                         description "38.8 Mbps";
                       }
                       enum "39.1Mb" {
                         description "39.1 Mbps";
                       }
                       enum "39.4Mb" {
                         description "39.4 Mbps";
                       }
                       enum "39.7Mb" {
                         description "39.7 Mbps";
                       }
                       enum "40.0Mb" {
                         description "40.0 Mbps";
                       }
                       enum "40.3Mb" {
                         description "40.3 Mbps";
                       }
                       enum "40.6Mb" {
                         description "40.6 Mbps";
                       }
                       enum "40.9Mb" {
                         description "40.9 Mbps";
                       }
                       enum "41.2Mb" {
                         description "41.2 Mbps";
                       }
                       enum "41.5Mb" {
                         description "41.5 Mbps";
                       }
                       enum "41.8Mb" {
                         description "41.8 Mbps";
                       }
                       enum "42.1Mb" {
                         description "42.1 Mbps";
                       }
                       enum "42.4Mb" {
                         description "42.4 Mbps";
                       }
                       enum "42.7Mb" {
                         description "42.7 Mbps";
                       }
                       enum "43.0Mb" {
                         description "43.0 Mbps";
                       }
                       enum "43.3Mb" {
                         description "43.3 Mbps";
                       }
                       enum "43.6Mb" {
                         description "43.6 Mbps";
                       }
                       enum "43.9Mb" {
                         description "43.9 Mbps";
                       }
                       enum "44.2Mb" {
                         description "44.2 Mbps";
                       }
                     }
                   }
                 }
               }
             }
           }
           choice payload-scrambler-choice {
             leaf payload-scrambler {
               description "Enable payload scrambling";
               type empty;
             }
             leaf no-payload-scrambler {
               description "Don't enable payload scrambling";
               type empty;
             }
           }
           choice cbit-parity-choice {
             leaf cbit-parity {
               description "Enable C-bit parity mode";
               type empty;
             }
             leaf no-cbit-parity {
               description "Don't enable C-bit parity mode";
               type empty;
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           choice feac-loop-respond-choice {
             leaf feac-loop-respond {
               description "Respond to FEAC loop requests";
               type empty;
             }
             leaf no-feac-loop-respond {
               description "Don't respond to FEAC loop requests";
               type empty;
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
           leaf buildout {
             description "Line buildout";
             units "feet";
             type union {
               type string {
                 pattern "<.*>|$.*";
               }
               type uint32 {
                 range "0 .. 450";
               }
             }
           }
           leaf atm-encapsulation {
             description "DS-3 interface encapsulation";
             type enumeration {
               enum "plcp" {
                 description "PLCP encapsulation";
               }
               enum "direct" {
                 description "ATM direct mapping";
               }
             }
           }
         }
         container e3-options {
           description "E3 interface-specific options";
           uses apply-advanced;
           leaf loopback {
             description "Loopback mode";
             type enumeration {
               enum "local" {
                 description "Local loopback";
               }
               enum "remote" {
                 description "Remote loopback";
               }
             }
           }
           choice unframed-choice {
             leaf unframed {
               description "Enable unframed mode";
               type empty;
             }
             leaf no-unframed {
               description "Don't enable unframed mode";
               type empty;
             }
           }
           container compatibility-mode {
             description "Set CSU compatibility mode";
             choice vendor {
               case case_1 {
                 leaf larscom {
                   description "Compatible with Larscom CSU (only non IQ E3 interfaces)";
                   type empty;
                 }
               }
               case case_2 {
                 container digital-link {
                   presence "enable digital-link";
                   description "Compatible with Digital Link CSU";
                   leaf subrate {
                     description "Set subrate value";
                     type enumeration {
                       enum "358Kb" {
                         description "358 Kbps";
                       }
                       enum "716Kb" {
                         description "716 Kbps";
                       }
                       enum "1.1Mb" {
                         description "1.1 Mbps";
                       }
                       enum "1.4Mb" {
                         description "1.4 Mbps";
                       }
                       enum "1.8Mb" {
                         description "1.8 Mbps";
                       }
                       enum "2.1Mb" {
                         description "2.1 Mbps";
                       }
                       enum "2.5Mb" {
                         description "2.5 Mbps";
                       }
                       enum "2.9Mb" {
                         description "2.9 Mbps";
                       }
                       enum "3.2Mb" {
                         description "3.2 Mbps";
                       }
                       enum "3.6Mb" {
                         description "3.6 Mbps";
                       }
                       enum "3.9Mb" {
                         description "3.9 Mbps";
                       }
                       enum "4.3Mb" {
                         description "4.3 Mbps";
                       }
                       enum "4.7Mb" {
                         description "4.7 Mbps";
                       }
                       enum "5.0Mb" {
                         description "5.0 Mbps";
                       }
                       enum "5.4Mb" {
                         description "5.4 Mbps";
                       }
                       enum "5.7Mb" {
                         description "5.7 Mbps";
                       }
                       enum "6.1Mb" {
                         description "6.1 Mbps";
                       }
                       enum "6.4Mb" {
                         description "6.4 Mbps";
                       }
                       enum "6.8Mb" {
                         description "6.8 Mbps";
                       }
                       enum "7.2Mb" {
                         description "7.2 Mbps";
                       }
                       enum "7.5Mb" {
                         description "7.5 Mbps";
                       }
                       enum "7.9Mb" {
                         description "7.9 Mbps";
                       }
                       enum "8.2Mb" {
                         description "8.2 Mbps";
                       }
                       enum "8.6Mb" {
                         description "8.6 Mbps";
                       }
                       enum "9.0Mb" {
                         description "9.0 Mbps";
                       }
                       enum "9.3Mb" {
                         description "9.3 Mbps";
                       }
                       enum "9.7Mb" {
                         description "9.7 Mbps";
                       }
                       enum "10.0Mb" {
                         description "10.0 Mbps";
                       }
                       enum "10.4Mb" {
                         description "10.4 Mbps";
                       }
                       enum "10.7Mb" {
                         description "10.7 Mbps";
                       }
                       enum "11.1Mb" {
                         description "11.1 Mbps";
                       }
                       enum "11.5Mb" {
                         description "11.5 Mbps";
                       }
                       enum "11.8Mb" {
                         description "11.8 Mbps";
                       }
                       enum "12.2Mb" {
                         description "12.2 Mbps";
                       }
                       enum "12.5Mb" {
                         description "12.5 Mbps";
                       }
                       enum "12.9Mb" {
                         description "12.9 Mbps";
                       }
                       enum "13.2Mb" {
                         description "13.2 Mbps";
                       }
                       enum "13.6Mb" {
                         description "13.6 Mbps";
                       }
                       enum "14.0Mb" {
                         description "14.0 Mbps";
                       }
                       enum "14.3Mb" {
                         description "14.3 Mbps";
                       }
                       enum "14.7Mb" {
                         description "14.7 Mbps";
                       }
                       enum "15.0Mb" {
                         description "15.0 Mbps";
                       }
                       enum "15.4Mb" {
                         description "15.4 Mbps";
                       }
                       enum "15.8Mb" {
                         description "15.8 Mbps";
                       }
                       enum "16.1Mb" {
                         description "16.1 Mbps";
                       }
                       enum "16.5Mb" {
                         description "16.5 Mbps";
                       }
                       enum "16.8Mb" {
                         description "16.8 Mbps";
                       }
                       enum "17.2Mb" {
                         description "17.2 Mbps";
                       }
                       enum "17.5Mb" {
                         description "17.5 Mbps";
                       }
                       enum "17.9Mb" {
                         description "17.9 Mbps";
                       }
                       enum "18.3Mb" {
                         description "18.3 Mbps";
                       }
                       enum "18.6Mb" {
                         description "18.6 Mbps";
                       }
                       enum "19.0Mb" {
                         description "19.0 Mbps";
                       }
                       enum "19.3Mb" {
                         description "19.3 Mbps";
                       }
                       enum "19.7Mb" {
                         description "19.7 Mbps";
                       }
                       enum "20.0Mb" {
                         description "20.0 Mbps";
                       }
                       enum "20.4Mb" {
                         description "20.4 Mbps";
                       }
                       enum "20.8Mb" {
                         description "20.8 Mbps";
                       }
                       enum "21.1Mb" {
                         description "21.1 Mbps";
                       }
                       enum "21.5Mb" {
                         description "21.5 Mbps";
                       }
                       enum "21.8Mb" {
                         description "21.8 Mbps";
                       }
                       enum "22.2Mb" {
                         description "22.2 Mbps";
                       }
                       enum "22.6Mb" {
                         description "22.6 Mbps";
                       }
                       enum "22.9Mb" {
                         description "22.9 Mbps";
                       }
                       enum "23.3Mb" {
                         description "23.3 Mbps";
                       }
                       enum "23.6Mb" {
                         description "23.6 Mbps";
                       }
                       enum "24.0Mb" {
                         description "24.0 Mbps";
                       }
                       enum "24.3Mb" {
                         description "24.3 Mbps";
                       }
                       enum "24.7Mb" {
                         description "24.7 Mbps";
                       }
                       enum "25.1Mb" {
                         description "25.1 Mbps";
                       }
                       enum "25.4Mb" {
                         description "25.4 Mbps";
                       }
                       enum "25.8Mb" {
                         description "25.8 Mbps";
                       }
                       enum "26.1Mb" {
                         description "26.1 Mbps";
                       }
                       enum "26.5Mb" {
                         description "26.5 Mbps";
                       }
                       enum "26.9Mb" {
                         description "26.9 Mbps";
                       }
                       enum "27.2Mb" {
                         description "27.2 Mbps";
                       }
                       enum "27.6Mb" {
                         description "27.6 Mbps";
                       }
                       enum "27.9Mb" {
                         description "27.9 Mbps";
                       }
                       enum "28.3Mb" {
                         description "28.3 Mbps";
                       }
                       enum "28.6Mb" {
                         description "28.6 Mbps";
                       }
                       enum "29.0Mb" {
                         description "29.0 Mbps";
                       }
                       enum "29.4Mb" {
                         description "29.4 Mbps";
                       }
                       enum "29.7Mb" {
                         description "29.7 Mbps";
                       }
                       enum "30.1Mb" {
                         description "30.1 Mbps";
                       }
                       enum "30.4Mb" {
                         description "30.4 Mbps";
                       }
                       enum "30.8Mb" {
                         description "30.8 Mbps";
                       }
                       enum "31.1Mb" {
                         description "31.1 Mbps";
                       }
                       enum "31.5Mb" {
                         description "31.5 Mbps";
                       }
                       enum "31.9Mb" {
                         description "31.9 Mbps";
                       }
                       enum "32.2Mb" {
                         description "32.2 Mbps";
                       }
                       enum "32.6Mb" {
                         description "32.6 Mbps";
                       }
                       enum "32.9Mb" {
                         description "32.9 Mbps";
                       }
                       enum "33.3Mb" {
                         description "33.3 Mbps";
                       }
                       enum "33.7Mb" {
                         description "33.7 Mbps";
                       }
                       enum "34.0Mb" {
                         description "34.0 Mbps";
                       }
                     }
                   }
                 }
               }
               case case_3 {
                 container kentrox {
                   presence "enable kentrox";
                   description "Compatible with Kentrox CSU";
                   leaf subrate {
                     description "Set subrate value (only for E3 IQ interfaces)";
                     type union {
                       type string {
                         pattern "<.*>|$.*";
                       }
                       type uint32 {
                         range "1 .. 48";
                       }
                     }
                   }
                 }
               }
             }
           }
           choice payload-scrambler-choice {
             leaf payload-scrambler {
               description "Enable payload scrambling";
               type empty;
             }
             leaf no-payload-scrambler {
               description "Don't enable payload scrambling";
               type empty;
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf invert-data {
             description "Invert data";
             type empty;
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
           leaf buildout {
             description "Line buildout";
             units "feet";
             type union {
               type string {
                 pattern "<.*>|$.*";
               }
               type uint32 {
                 range "0 .. 450";
               }
             }
           }
           leaf atm-encapsulation {
             description "E3 interface encapsulation";
             type enumeration {
               enum "plcp" {
                 description "PLCP encapsulation";
               }
               enum "direct" {
                 description "ATM direct mapping";
               }
             }
           }
           leaf framing {
             description "E3 line format";
             type enumeration {
               enum "g.751" {
                 description "G.751 format";
               }
               enum "g.832" {
                 description "G.832 format";
               }
             }
           }
         }
         container e1-options {
           description "E1 interface-specific options";
           uses apply-advanced;
           leaf timeslots {
             description "Timeslots (1..32); for example, 1-4,6,9-11,32 (no space)";
             type string;
           }
           leaf loopback {
             description "Loopback mode";
             type enumeration {
               enum "local" {
                 description "Local loopback";
               }
               enum "remote" {
                 description "Remote loopback";
               }
             }
           }
           leaf framing {
             description "Framing mode";
             type enumeration {
               enum "g704" {
                 description "G704 mode with CRC4";
               }
               enum "unframed" {
                 description "Unframed mode";
               }
               enum "g704-no-crc4" {
                 description "G704 mode without CRC4";
               }
             }
           }
           leaf fcs {
             description "Frame checksum";
             type enumeration {
               enum "32" {
                 description "32-bit mode";
               }
               enum "16" {
                 description "16-bit mode";
               }
             }
           }
           leaf invert-data {
             description "Invert data";
             type empty;
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 86400";
               }
             }
           }
         }
         container t1-options {
           description "T1 interface-specific options";
           uses apply-advanced;
           leaf timeslots {
             description "Timeslots (1..24; for example, 1-3,4,9,22-24 (no space)";
             type string;
           }
           leaf loopback {
             description "Loopback mode";
             type enumeration {
               enum "local" {
                 description "Local loopback";
               }
               enum "remote" {
                 description "Remote loopback";
               }
               enum "payload" {
                 description "Payload loopback";
               }
             }
           }
           leaf buildout {
             description "Line buildout";
             type enumeration {
               enum "0-132" {
                 description "Line buildout is between 0-132 feet";
               }
               enum "133-265" {
                 description "Line buildout is between 133-265 feet";
               }
               enum "266-398" {
                 description "Line buildout is between 266-398 feet";
               }
               enum "399-531" {
                 description "Line buildout is between 399-531 feet";
               }
               enum "532-655" {
                 description "Line buildout is between 532-655 feet";
               }
               enum "long-0db" {
                 description "Long buildout with 0 dB transmit attenuation";
               }
               enum "long-7.5db" {
                 description "Long buildout with 7.5 dB transmit attenuation";
               }
               enum "long-15db" {
                 description "Long buildout with 15 dB transmit attenuation";
               }
               enum "long-22.5db" {
                 description "Long buildout with 22.5 dB transmit attenuation";
               }
             }
           }
           leaf byte-encoding {
             description "Byte encoding";
             type enumeration {
               enum "nx64" {
                 description "8 bits per byte";
               }
               enum "nx56" {
                 description "7 bits per byte";
               }
             }
           }
           leaf line-encoding {
             description "Line encoding";
             type enumeration {
               enum "ami" {
                 description "Automatic mark inversion";
               }
               enum "b8zs" {
                 description "8-bit zero suppression";
               }
             }
           }
           leaf invert-data {
             description "Invert data";
             type empty;
           }
           leaf framing {
             description "Framing mode";
             type enumeration {
               enum "sf" {
                 description "Super frame";
               }
               enum "esf" {
                 description "Extended super frame";
               }
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 86400";
               }
             }
           }
           leaf remote-loopback-respond {
             description "Respond to loop requests from remote end";
             type empty;
           }
           leaf crc-major-alarm-threshold {
             description "CRC Major alarm threshold value";
             default "5e-5";
             type enumeration {
               enum "1e-3" {
                 description "1 crc error in 10^3 bits";
               }
               enum "5e-4" {
                 description "5 crc errors in 10^4 bits";
               }
               enum "1e-4" {
                 description "1 crc error in 10^4 bits";
               }
               enum "5e-5" {
                 description "5 crc errors in 10^5 bits";
               }
               enum "1e-5" {
                 description "1 crc error in 10^5 bits";
               }
             }
           }
           leaf crc-minor-alarm-threshold {
             description "CRC Minor alarm threshold value";
             default "5e-6";
             type enumeration {
               enum "1e-3" {
                 description "1 crc error in 10^3 bits";
               }
               enum "5e-4" {
                 description "5 crc errors in 10^4 bits";
               }
               enum "1e-4" {
                 description "1 crc error in 10^4 bits";
               }
               enum "5e-5" {
                 description "5 crc errors in 10^5 bits";
               }
               enum "1e-5" {
                 description "1 crc error in 10^5 bits";
               }
               enum "5e-6" {
                 description "5 crc errors in 10^6 bits";
               }
               enum "1e-6" {
                 description "1 crc error in 10^6 bits";
               }
             }
           }
         }
         container ds0-options {
           description "DS-0 interface-specific options";
           uses apply-advanced;
           leaf loopback {
             description "Loopback mode";
             type enumeration {
               enum "payload" {
                 description "Payload loopback";
               }
             }
           }
           leaf byte-encoding {
             description "Byte encoding";
             type enumeration {
               enum "nx64" {
                 description "8 bits per byte";
               }
               enum "nx56" {
                 description "7 bits per byte";
               }
             }
           }
           leaf invert-data {
             description "Invert data";
             type empty;
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e11-o152" {
                 description "Pattern is 2^11 -1 (per O.152 standard)";
               }
               enum "pseudo-2e15-o151" {
                 description "Pattern is 2^15 - 1 (per O.151 standard)";
               }
               enum "pseudo-2e20-o153" {
                 description "Pattern is 2^20 - 1 (per O.153 standard)";
               }
               enum "pseudo-2e20-o151" {
                 description "Pattern is 2^20 - 1 (per O.151 standard)";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
               enum "repeating-1-in-16" {
                 description "1 bit in 16 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
         }
         container serial-options {
           description "Serial interface-specific options";
           uses apply-advanced;
           leaf line-protocol {
             description "Line protocol to be used";
             default "eia530";
             type enumeration {
               enum "eia530" {
                 description "Line protocol EIA530";
               }
               enum "v.35" {
                 description "Line protocol V.35";
               }
               enum "x.21" {
                 description "Line protocol X.21";
               }
             }
           }
           choice control_leads_choice {
             case case_1 {
               container dte-options {
                 description "DTE options/control leads";
                 uses apply-advanced;
                 leaf ignore-all {
                   description "Ignore all control leads";
                   type empty;
                 }
                 container dtr {
                   description "Data Transmit Ready signal handling";
                   choice dtr_choices {
                     case case_1 {
                       leaf assert {
                         description "Assert DTR signal";
                         type empty;
                       }
                     }
                     case case_2 {
                       leaf de-assert {
                         description "Deassert DTR signal";
                         type empty;
                       }
                     }
                     case case_3 {
                       leaf normal {
                         description "Normal DTR signal";
                         type empty;
                       }
                     }
                     case case_4 {
                       container auto-synchronize {
                         presence "enable auto-synchronize";
                         description "Normal DTR signal, with autoresynchronization";
                         uses apply-advanced;
                         leaf duration {
                           description "Duration of autoresynchronization";
                           units "milliseconds";
                           type union {
                             type string {
                               pattern "<.*>|$.*";
                             }
                             type uint16 {
                               range "1 .. 1000";
                             }
                           }
                         }
                         leaf interval {
                           description "Interval for autoresynchronization";
                           units "seconds";
                           type union {
                             type string {
                               pattern "<.*>|$.*";
                             }
                             type uint16 {
                               range "1 .. 31";
                             }
                           }
                         }
                       }
                     }
                   }
                 }
                 leaf control-signal {
                   description "X.21 control signal handling";
                   type enumeration {
                     enum "assert" {
                       description "Assert control signal";
                     }
                     enum "de-assert" {
                       description "Deassert control signal";
                     }
                     enum "normal" {
                       description "Normal control signal";
                     }
                   }
                 }
                 leaf rts {
                   description "Request To Send signal handling";
                   type enumeration {
                     enum "assert" {
                       description "Assert RTS signal";
                     }
                     enum "de-assert" {
                       description "Deassert RTS signal";
                     }
                     enum "normal" {
                       description "Normal RTS signal";
                     }
                   }
                 }
                 leaf dcd {
                   description "Data Carrier Detect signal handling";
                   type enumeration {
                     enum "require" {
                       description "Require DCD signal";
                     }
                     enum "ignore" {
                       description "Ignore DCD signal";
                     }
                     enum "normal" {
                       description "Normal DCD signal";
                     }
                   }
                 }
                 leaf dsr {
                   description "Data Set Ready signal handling";
                   type enumeration {
                     enum "require" {
                       description "Require DSR signal";
                     }
                     enum "ignore" {
                       description "Ignore DSR signal";
                     }
                     enum "normal" {
                       description "Normal DSR signal";
                     }
                   }
                 }
                 leaf cts {
                   description "Clear To Send signal handling";
                   type enumeration {
                     enum "require" {
                       description "Require CTS signal";
                     }
                     enum "ignore" {
                       description "Ignore CTS signal";
                     }
                     enum "normal" {
                       description "Normal CTS signal";
                     }
                   }
                 }
                 leaf indication {
                   description "X.21 Indication signal handling";
                   type enumeration {
                     enum "require" {
                       description "Require Indication signal";
                     }
                     enum "ignore" {
                       description "Ignore Indication signal";
                     }
                     enum "normal" {
                       description "Normal Indication signal";
                     }
                   }
                 }
                 leaf tm {
                   description "Test Mode signal handling";
                   type enumeration {
                     enum "require" {
                       description "Require TM signal";
                     }
                     enum "ignore" {
                       description "Ignore TM signal";
                     }
                     enum "normal" {
                       description "Normal TM signal";
                     }
                   }
                 }
               }
             }
             case case_2 {
             }
           }
           leaf dtr-circuit {
             description "Data Transmit Ready circuit mode";
             type enumeration {
               enum "balanced" {
                 description "Balanced signal";
               }
               enum "unbalanced" {
                 description "Unbalanced signal";
               }
             }
           }
           leaf dtr-polarity {
             description "Data Transmit Ready signal polarity";
             type enumeration {
               enum "positive" {
                 description "Positive polarity";
               }
               enum "negative" {
                 description "Negative polarity";
               }
             }
           }
           leaf rts-polarity {
             description "Request To Send signal polarity";
             type enumeration {
               enum "positive" {
                 description "Positive polarity";
               }
               enum "negative" {
                 description "Negative polarity";
               }
             }
           }
           leaf control-polarity {
             description "X.21 Control signal polarity";
             type enumeration {
               enum "positive" {
                 description "Positive polarity";
               }
               enum "negative" {
                 description "Negative polarity";
               }
             }
           }
           leaf dcd-polarity {
             description "Data Carrier Detect signal polarity";
             type enumeration {
               enum "positive" {
                 description "Positive polarity";
               }
               enum "negative" {
                 description "Negative polarity";
               }
             }
           }
           leaf dsr-polarity {
             description "Data Set Ready signal polarity";
             type enumeration {
               enum "positive" {
                 description "Positive polarity";
               }
               enum "negative" {
                 description "Negative polarity";
               }
             }
           }
           leaf cts-polarity {
             description "Clear To Send signal polarity";
             type enumeration {
               enum "positive" {
                 description "Positive polarity";
               }
               enum "negative" {
                 description "Negative polarity";
               }
             }
           }
           leaf indication-polarity {
             description "X.21 Indication signal polarity";
             type enumeration {
               enum "positive" {
                 description "Positive polarity";
               }
               enum "negative" {
                 description "Negative polarity";
               }
             }
           }
           leaf tm-polarity {
             description "Test Mode signal polarity";
             type enumeration {
               enum "positive" {
                 description "Positive polarity";
               }
               enum "negative" {
                 description "Negative polarity";
               }
             }
           }
           leaf clocking-mode {
             description "Clock mode";
             type enumeration {
               enum "dce" {
                 description "DCE timing (DTE mode only, not valid for X.21)";
               }
               enum "internal" {
                 description "Internal baud timing";
               }
               enum "loop" {
                 description "Loop timing";
               }
             }
           }
           leaf transmit-clock {
             description "Transmit clock phase";
             type enumeration {
               enum "invert" {
                 description "Shift clock phase 180 degrees";
               }
             }
           }
           leaf clock-rate {
             description "Interface clock rate";
             type enumeration {
               enum "2.048mhz" {
                 description "2.048 MHz";
               }
               enum "2.341mhz" {
                 description "2.341 MHz";
               }
               enum "2.731mhz" {
                 description "2.731 MHz";
               }
               enum "3.277mhz" {
                 description "3.277 MHz";
               }
               enum "4.096mhz" {
                 description "4.096 MHz";
               }
               enum "5.461mhz" {
                 description "5.461 MHz";
               }
               enum "8.192mhz" {
                 description "8.192 MHz";
               }
               enum "16.384mhz" {
                 description "16.384 MHz";
               }
               enum "1.2khz" {
                 description "1.2 KHz";
               }
               enum "2.4khz" {
                 description "2.4 KHz";
               }
               enum "9.6khz" {
                 description "9.6 KHz";
               }
               enum "19.2khz" {
                 description "19.2 KHz";
               }
               enum "38.4khz" {
                 description "38.4 KHz";
               }
               enum "56.0khz" {
                 description "56.0 KHz";
               }
               enum "64.0khz" {
                 description "64.0 KHz";
               }
               enum "72.0khz" {
                 description "72.0 KHz";
               }
               enum "125.0khz" {
                 description "125.0 KHz";
               }
               enum "148.0khz" {
                 description "148.0 KHz";
               }
               enum "250.0khz" {
                 description "250.0 KHz";
               }
               enum "500.0khz" {
                 description "500.0 KHz";
               }
               enum "800.0khz" {
                 description "800.0 KHz";
               }
               enum "1.0mhz" {
                 description "1.0 MHz";
               }
               enum "1.3mhz" {
                 description "1.3 MHz";
               }
               enum "2.0mhz" {
                 description "2.0 MHz";
               }
               enum "4.0mhz" {
                 description "4.0 MHz";
               }
               enum "8.0mhz" {
                 description "8.0 MHz";
               }
             }
           }
           leaf loopback {
             description "Loopback mode";
             type enumeration {
               enum "local" {
                 description "Local loopback";
               }
               enum "remote" {
                 description "Remote/LIU loopback";
               }
               enum "dce-local" {
                 description "DCE local loopback (DTE mode only)";
               }
               enum "dce-remote" {
                 description "DCE remote loopback";
               }
             }
           }
           leaf encoding {
             description "Line encoding";
             type enumeration {
               enum "nrz" {
                 description "Non-Return-To-Zero";
               }
               enum "nrzi" {
                 description "Non-Return-To-Zero-Invertible";
               }
             }
           }
         }
         choice gratuitous-arp-reply-choice {
           leaf gratuitous-arp-reply {
             description "Enable gratuitous ARP reply";
             type empty;
           }
           leaf no-gratuitous-arp-reply {
             description "Don't enable gratuitous ARP reply";
             type empty;
           }
         }
         choice no-gratuitous-arp-request-choice {
           leaf no-gratuitous-arp-request {
             description "Ignore gratuitous ARP request";
             type empty;
           }
           leaf no-no-gratuitous-arp-request {
             description "Don't ignore gratuitous ARP request";
             type empty;
           }
         }
         leaf arp-l2-validate {
           description "Validate ARP against L2";
           type empty;
         }
         container ether-options {
           description "Ethernet interface-specific options";
           uses apply-advanced;
           choice loopback-choice {
             leaf loopback {
               description "Enable loopback";
               type empty;
             }
             leaf no-loopback {
               description "Don't enable loopback";
               type empty;
             }
           }
           choice source-filtering-choice {
             leaf source-filtering {
               description "Enable source address filtering";
               type empty;
             }
             leaf no-source-filtering {
               description "Don't enable source address filtering";
               type empty;
             }
           }
           container ethernet-switch-profile {
             description "Ethernet virtual LAN/media access control-level options";
             uses apply-advanced;
             leaf-list tag-protocol-id {
               description "IEEE 802.1q Tag Protocol Identifier values for VLAN-tagged frames";
               type string;
             }
             container ethernet-policer-profile {
               description "Ethernet level CoS-based policer configuration";
               uses apply-advanced;
               container input-priority-map {
                 description "Input policer priority map";
                 uses cos_policer_input_priority_map;
               }
               container output-priority-map {
                 description "Output policer priority map";
                 uses cos_policer_output_priority_map;
               }
               list policer {
                 key name;
                 ordered-by user;
                 description "Policer template definition";
                 uses cos_policer;
               }
             }
             container storm-control {
               description "Storm control profile name to bind";
               uses apply-advanced;
               leaf profile-name {
                 description "Profile name";
                 type string;
               }
             }
             container recovery-timeout {
               description "Recovery timeout for this interface";
               leaf time-in-seconds {
                 units "seconds";
                 type union {
                   type string {
                     pattern "<.*>|$.*";
                   }
                   type uint32 {
                     range "10 .. 3600";
                   }
                 }
               }
             }
             choice mac-learn-enable-choice {
               leaf mac-learn-enable {
                 description "Learn MAC addresses dynamically";
                 type empty;
               }
               leaf no-mac-learn-enable {
                 description "Don't learn MAC addresses dynamically";
                 type empty;
               }
             }
           }
           leaf asynchronous-notification {
             description "Enable sending asynchronous notification to peer on CCC-down";
             type empty;
           }
           list source-address-filter {
             key name;
             description "Source address filters";
             leaf name {
               description "Remote MAC address";
               type jt:mac-addr;
             }
           }
           choice auto-negotiation-choice {
             leaf auto-negotiation {
               description "Enable auto-negotiation";
               type empty;
             }
             leaf no-auto-negotiation {
               description "Don't enable auto-negotiation";
               type empty;
             }
           }
           choice flow-control-choice {
             leaf flow-control {
               description "Enable flow control";
               type empty;
             }
             leaf no-flow-control {
               description "Don't enable flow control";
               type empty;
             }
           }
           container configured-flow-control {
             presence "enable configured-flow-control";
             description "Enable flow control";
             uses apply-advanced;
             leaf rx-buffers {
               description "Enable/Disable Rx buffers";
               type enumeration {
                 enum "on" {
                   description "Enable Rx buffers";
                 }
                 enum "off" {
                   description "Disable Rx buffers";
                 }
               }
             }
             leaf tx-buffers {
               description "Enable/Disable Tx buffers";
               type enumeration {
                 enum "on" {
                   description "Enable Tx buffers";
                 }
                 enum "off" {
                   description "Disable Tx buffers";
                 }
               }
             }
           }
           leaf link-mode {
             description "Link duplex";
             type enumeration {
               enum "automatic" {
                 description "Automatic negotiate duplex ";
               }
               enum "half-duplex" {
                 description "Half-duplex operation";
               }
               enum "full-duplex" {
                 description "Full-duplex operation";
               }
             }
           }
           container mpls {
             description "MPLS options";
             uses mpls_ifd_options;
           }
           leaf ignore-l3-incompletes {
             description "Ignore L3 incomplete errors";
             type empty;
           }
           leaf no-auto-mdix {
             description "Disable auto MDI/MDIX";
             type empty;
           }
           container speed {
             description "Specify speed";
             choice automatic {
               case case_1 {
                 container auto-negotiation {
                   presence "enable auto-negotiation";
                   description "Enable auto-negotiation";
                   leaf auto-negotiate-10-100 {
                     description "Limits the auto-negotiation to 10m/100m only";
                     type empty;
                   }
                 }
               }
               case case_2 {
                 leaf ethernet-10m {
                   description "10Mbps";
                   type empty;
                 }
               }
               case case_3 {
                 leaf ethernet-100m {
                   description "100Mbps";
                   type empty;
                 }
               }
               case case_4 {
                 leaf ethernet-1g {
                   description "1Gbps";
                   type empty;
                 }
               }
               case case_5 {
                 leaf ethernet-10g {
                   description "10Gbps";
                   type empty;
                 }
               }
             }
           }
           container ieee-802.3ad {
             description "IEEE 802.3ad";
             uses apply-advanced;
             container lacp {
               description "Link Aggregation Control Protocol configuration";
               uses apply-advanced;
               leaf force-up {
                 description "Keep the port up in absence of received LACPDU";
                 type empty;
               }
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
             container link-protection-sub-group {
               description "Link Protection subgroup configuration";
               uses apply-advanced;
               leaf subgroup-name {
                 description "Name of the subgroup";
                 type string {
                   length "2 .. 64";
                 }
               }
             }
             leaf port-priority {
               description "Link protection Priority of the port (0 ... 65535)";
               type union {
                 type uint16;
                 type string {
                   pattern "<.*>|$.*";
                 }
               }
             }
           }
           leaf ieee-802-3az-eee {
             description "IEEE 802.3az Energy Efficient Ethernet(EEE)";
             type empty;
           }
           leaf autostate-exclude {
             description "Interface will not contribute to IRB state";
             type empty;
           }
         }
         container fibrechannel-options {
           description "Fibre Channel interface-specific options";
           uses apply-advanced;
           choice loopback-choice {
             leaf loopback {
               description "Enable loopback";
               type empty;
             }
             leaf no-loopback {
               description "Don't enable loopback";
               type empty;
             }
           }
           leaf bb-sc-n {
             description "B2B state change number";
             type union {
               type string {
                 pattern "<.*>|$.*";
               }
               type uint16 {
                 range "0 .. 15";
               }
             }
           }
           leaf speed {
             description "Specify speed";
             type enumeration {
               enum "auto-negotiation" {
                 description "Enable auto-negotiation";
               }
               enum "1g" {
                 description "1Gbps";
               }
               enum "2g" {
                 description "2Gbps";
               }
               enum "4g" {
                 description "4Gbps";
               }
               enum "8g" {
                 description "8Gbps";
               }
             }
           }
         }
         container gigether-options {
           description "Gigabit Ethernet interface-specific options";
           uses apply-advanced;
           choice loopback-choice {
             leaf loopback {
               description "Enable loopback";
               type empty;
             }
             leaf no-loopback {
               description "Don't enable loopback";
               type empty;
             }
           }
           leaf loopback-remote {
             description "Enable remote loopback";
             type empty;
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           choice auto_negotiation_option {
             case case_1 {
               leaf no-auto-negotiation {
                 description "Disable auto-negotiation";
                 type empty;
               }
             }
             case case_2 {
               container auto-negotiation {
                 presence "enable auto-negotiation";
                 description "Enable auto-negotiation";
                 leaf remote-fault {
                   type enumeration {
                     enum "local-interface-offline" {
                       description "Disable local interface";
                     }
                     enum "local-interface-online" {
                       description "Enable local interface";
                     }
                   }
                 }
               }
             }
           }
           leaf asynchronous-notification {
             description "Enable sending asynchronous notification to peer on CCC-down";
             type empty;
           }
           list source-address-filter {
             key name;
             description "Source address filters";
             leaf name {
               description "Remote MAC address";
               type jt:mac-addr;
             }
           }
           container ieee-802.3ad {
             description "IEEE 802.3ad";
             uses apply-advanced;
             container lacp {
               description "Link Aggregation Control Protocol configuration";
               uses apply-advanced;
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
           }
           container ethernet-switch-profile {
             description "Ethernet virtual LAN/media access control-level options";
             uses apply-advanced;
             leaf-list tag-protocol-id {
               description "IEEE 802.1q Tag Protocol Identifier values for VLAN-tagged frames";
               type string;
             }
             container ethernet-policer-profile {
               description "Ethernet level CoS-based policer configuration";
               uses apply-advanced;
               container ieee802.1-priority-map {
                 presence "enable ieee802.1-priority-map";
                 description "Premium priority values for IEEE 802.1p bits";
                 status deprecated;
                 uses apply-advanced;
                 leaf-list premium {
                   description "Premium policer priority map";
                   type union {
                     type string {
                       pattern "<.*>|$.*";
                     }
                     type uint32 {
                       range "0 .. 7";
                     }
                   }
                 }
               }
               container input-priority-map {
                 description "Input policer priority map";
                 uses cos_policer_input_priority_map;
               }
               container output-priority-map {
                 description "Output policer priority map";
                 uses cos_policer_output_priority_map;
               }
               list policer {
                 key name;
                 ordered-by user;
                 description "Policer template definition";
                 uses cos_policer;
               }
             }
             container accept-from {
               description "Accept traffic from or to specified remote MAC";
               status deprecated;
               uses apply-advanced;
               list mac-address {
                 key name;
                 description "Remote MAC";
                 uses mac_list;
               }
             }
             choice reject-the-rest-choice {
               leaf reject-the-rest {
                 description "Accept traffic from only the specified MAC addresses";
                 status deprecated;
                 type empty;
               }
               leaf no-reject-the-rest {
                 description "Don't accept traffic from only the specified MAC addresses";
                 status deprecated;
                 type empty;
               }
             }
             leaf mac-learn-enable {
               description "Learn MAC addresses dynamically";
               type empty;
             }
           }
           container mpls {
             description "MPLS options";
             uses mpls_ifd_options;
           }
           leaf ignore-l3-incompletes {
             description "Ignore L3 incomplete errors";
             type empty;
           }
           leaf ieee-802-3az-eee {
             description "IEEE 802.3az Energy Efficient Ethernet(EEE)";
             type empty;
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
             }
           }
         }
         container optics-options {
           description "Optics options";
           uses apply-advanced;
           leaf wavelength {
             description "Wavelength of the optics (nanometers) for 50Ghz/100Ghz spacing";
             type enumeration {
               enum "1568.77" {
                 description "1568.77 nm/191.1003 THz 50/100Ghz spacing";
               }
               enum "1568.36" {
                 description "1568.36 nm/191.1500 THz 12.5/50GHz spacing";
               }
               enum "1568.26" {
                 description "1568.26 nm/191.1625 THz 12.5GHz spacing";
               }
               enum "1568.16" {
                 description "1568.16 nm/191.1750 THz 12.5GHz spacing";
               }
               enum "1568.05" {
                 description "1568.05 nm/191.1875 THz 12.5GHz spacing";
               }
               enum "1567.95" {
                 description "1567.95 nm/191.2000 THz 12.5/50/100GHz spacing";
               }
               enum "1567.85" {
                 description "1567.85 nm/191.2125 THz 12.5GHz spacing";
               }
               enum "1567.75" {
                 description "1567.75 nm/191.2250 THz 12.5GHz spacing";
               }
               enum "1567.64" {
                 description "1567.64 nm/191.2375 THz 12.5GHz spacing";
               }
               enum "1567.54" {
                 description "1567.54 nm/191.2500 THz 12.5/50GHz spacing";
               }
               enum "1567.44" {
                 description "1567.44 nm/191.2625 THz 12.5GHz spacing";
               }
               enum "1567.34" {
                 description "1567.34 nm/191.2750 THz 12.5GHz spacing";
               }
               enum "1567.23" {
                 description "1567.23 nm/191.2875 THz 12.5GHz spacing";
               }
               enum "1567.13" {
                 description "1567.13 nm/191.3000 THz 12.5/50/100GHz spacing";
               }
               enum "1567.03" {
                 description "1567.03 nm/191.3125 THz 12.5GHz spacing";
               }
               enum "1566.93" {
                 description "1566.93 nm/191.3250 THz 12.5GHz spacing";
               }
               enum "1566.83" {
                 description "1566.83 nm/191.3375 THz 12.5GHz spacing";
               }
               enum "1566.72" {
                 description "1566.72 nm/191.3500 THz 12.5/50GHz spacing";
               }
               enum "1566.62" {
                 description "1566.62 nm/191.3625 THz 12.5GHz spacing";
               }
               enum "1566.52" {
                 description "1566.52 nm/191.3750 THz 12.5GHz spacing";
               }
               enum "1566.42" {
                 description "1566.42 nm/191.3875 THz 12.5GHz spacing";
               }
               enum "1566.31" {
                 description "1566.31 nm/191.4000 THz 12.5/50/100GHz spacing";
               }
               enum "1566.21" {
                 description "1566.21 nm/191.4125 THz 12.5GHz spacing";
               }
               enum "1566.11" {
                 description "1566.11 nm/191.4250 THz 12.5GHz spacing";
               }
               enum "1566.01" {
                 description "1566.01 nm/191.4375 THz 12.5GHz spacing";
               }
               enum "1565.90" {
                 description "1565.90 nm/191.4500 THz 12.5/50GHz spacing";
               }
               enum "1565.80" {
                 description "1565.80 nm/191.4625 THz 12.5GHz spacing";
               }
               enum "1565.70" {
                 description "1565.70 nm/191.4750 THz 12.5GHz spacing";
               }
               enum "1565.60" {
                 description "1565.60 nm/191.4875 THz 12.5GHz spacing";
               }
               enum "1565.50" {
                 description "1565.50 nm/191.5000 THz 12.5/50/100GHz spacing";
               }
               enum "1565.39" {
                 description "1565.39 nm/191.5125 THz 12.5GHz spacing";
               }
               enum "1565.29" {
                 description "1565.29 nm/191.5250 THz 12.5GHz spacing";
               }
               enum "1565.19" {
                 description "1565.19 nm/191.5375 THz 12.5GHz spacing";
               }
               enum "1565.09" {
                 description "1565.09 nm/191.5500 THz 12.5/50GHz spacing";
               }
               enum "1564.99" {
                 description "1564.99 nm/191.5625 THz 12.5GHz spacing";
               }
               enum "1564.88" {
                 description "1564.88 nm/191.5750 THz 12.5GHz spacing";
               }
               enum "1564.78" {
                 description "1564.78 nm/191.5875 THz 12.5GHz spacing";
               }
               enum "1564.68" {
                 description "1564.68 nm/191.6000 THz 12.5/50/100GHz spacing";
               }
               enum "1564.58" {
                 description "1564.58 nm/191.6125 THz 12.5GHz spacing";
               }
               enum "1564.47" {
                 description "1564.47 nm/191.6250 THz 12.5GHz spacing";
               }
               enum "1564.37" {
                 description "1564.37 nm/191.6375 THz 12.5GHz spacing";
               }
               enum "1564.27" {
                 description "1564.27 nm/191.6500 THz 12.5/50GHz spacing";
               }
               enum "1564.17" {
                 description "1564.17 nm/191.6625 THz 12.5GHz spacing";
               }
               enum "1564.07" {
                 description "1564.07 nm/191.6750 THz 12.5GHz spacing";
               }
               enum "1563.96" {
                 description "1563.96 nm/191.6875 THz 12.5GHz spacing";
               }
               enum "1563.86" {
                 description "1563.86 nm/191.7000 THz 12.5/50/100GHz spacing";
               }
               enum "1563.76" {
                 description "1563.76 nm/191.7125 THz 12.5GHz spacing";
               }
               enum "1563.66" {
                 description "1563.66 nm/191.7250 THz 12.5GHz spacing";
               }
               enum "1563.56" {
                 description "1563.56 nm/191.7375 THz 12.5GHz spacing";
               }
               enum "1563.45" {
                 description "1563.45 nm/191.7500 THz 12.5/50GHz spacing";
               }
               enum "1563.35" {
                 description "1563.35 nm/191.7625 THz 12.5GHz spacing";
               }
               enum "1563.25" {
                 description "1563.25 nm/191.7750 THz 12.5GHz spacing";
               }
               enum "1563.15" {
                 description "1563.15 nm/191.7875 THz 12.5GHz spacing";
               }
               enum "1563.05" {
                 description "1563.05 nm/191.8000 THz 12.5/50/100GHz spacing";
               }
               enum "1562.95" {
                 description "1562.95 nm/191.8125 THz 12.5GHz spacing";
               }
               enum "1562.84" {
                 description "1562.84 nm/191.8250 THz 12.5GHz spacing";
               }
               enum "1562.74" {
                 description "1562.74 nm/191.8375 THz 12.5GHz spacing";
               }
               enum "1562.64" {
                 description "1562.64 nm/191.8500 THz 12.5/50GHz spacing";
               }
               enum "1562.54" {
                 description "1562.54 nm/191.8625 THz 12.5GHz spacing";
               }
               enum "1562.44" {
                 description "1562.44 nm/191.8750 THz 12.5GHz spacing";
               }
               enum "1562.33" {
                 description "1562.33 nm/191.8875 THz 12.5GHz spacing";
               }
               enum "1562.23" {
                 description "1562.23 nm/191.9000 THz 12.5/50/100GHz spacing";
               }
               enum "1562.13" {
                 description "1562.13 nm/191.9125 THz 12.5GHz spacing";
               }
               enum "1562.03" {
                 description "1562.03 nm/191.9250 THz 12.5GHz spacing";
               }
               enum "1561.93" {
                 description "1561.93 nm/191.9375 THz 12.5GHz spacing";
               }
               enum "1561.83" {
                 description "1561.83 nm/191.9500 THz 12.5/50GHz spacing";
               }
               enum "1561.72" {
                 description "1561.72 nm/191.9625 THz 12.5GHz spacing";
               }
               enum "1561.62" {
                 description "1561.62 nm/191.9750 THz 12.5GHz spacing";
               }
               enum "1561.52" {
                 description "1561.52 nm/191.9875 THz 12.5GHz spacing";
               }
               enum "1561.42" {
                 description "1561.42 nm/192.0000 THz 12.5/50/100GHz spacing";
               }
               enum "1561.32" {
                 description "1561.32 nm/192.0125 THz 12.5GHz spacing";
               }
               enum "1561.22" {
                 description "1561.22 nm/192.0250 THz 12.5GHz spacing";
               }
               enum "1561.11" {
                 description "1561.11 nm/192.0375 THz 12.5GHz spacing";
               }
               enum "1561.01" {
                 description "1561.01 nm/192.0500 THz 12.5/50GHz spacing";
               }
               enum "1560.91" {
                 description "1560.91 nm/192.0625 THz 12.5GHz spacing";
               }
               enum "1560.81" {
                 description "1560.81 nm/192.0750 THz 12.5GHz spacing";
               }
               enum "1560.71" {
                 description "1560.71 nm/192.0875 THz 12.5GHz spacing";
               }
               enum "1560.61" {
                 description "1560.61 nm/192.1000 THz 12.5/50/100GHz spacing";
               }
               enum "1560.50" {
                 description "1560.50 nm/192.1125 THz 12.5GHz spacing";
               }
               enum "1560.40" {
                 description "1560.40 nm/192.1250 THz 12.5GHz spacing";
               }
               enum "1560.30" {
                 description "1560.30 nm/192.1375 THz 12.5GHz spacing";
               }
               enum "1560.20" {
                 description "1560.20 nm/192.1500 THz 12.5/50GHz spacing";
               }
               enum "1560.10" {
                 description "1560.10 nm/192.1625 THz 12.5GHz spacing";
               }
               enum "1560.00" {
                 description "1560.00 nm/192.1750 THz 12.5GHz spacing";
               }
               enum "1559.90" {
                 description "1559.90 nm/192.1875 THz 12.5GHz spacing";
               }
               enum "1559.79" {
                 description "1559.79 nm/192.2000 THz 12.5/50/100GHz spacing";
               }
               enum "1559.69" {
                 description "1559.69 nm/192.2125 THz 12.5GHz spacing";
               }
               enum "1559.59" {
                 description "1559.59 nm/192.2250 THz 12.5GHz spacing";
               }
               enum "1559.49" {
                 description "1559.49 nm/192.2375 THz 12.5GHz spacing";
               }
               enum "1559.39" {
                 description "1559.39 nm/192.2500 THz 12.5/50GHz spacing";
               }
               enum "1559.29" {
                 description "1559.29 nm/192.2625 THz 12.5GHz spacing";
               }
               enum "1559.19" {
                 description "1559.19 nm/192.2750 THz 12.5GHz spacing";
               }
               enum "1559.08" {
                 description "1559.08 nm/192.2875 THz 12.5GHz spacing";
               }
               enum "1558.98" {
                 description "1558.98 nm/192.3000 THz 12.5/50/100GHz spacing";
               }
               enum "1558.88" {
                 description "1558.88 nm/192.3125 THz 12.5GHz spacing";
               }
               enum "1558.78" {
                 description "1558.78 nm/192.3250 THz 12.5GHz spacing";
               }
               enum "1558.68" {
                 description "1558.68 nm/192.3375 THz 12.5GHz spacing";
               }
               enum "1558.58" {
                 description "1558.58 nm/192.3500 THz 12.5/50GHz spacing";
               }
               enum "1558.48" {
                 description "1558.48 nm/192.3625 THz 12.5GHz spacing";
               }
               enum "1558.38" {
                 description "1558.38 nm/192.3750 THz 12.5GHz spacing";
               }
               enum "1558.27" {
                 description "1558.27 nm/192.3875 THz 12.5GHz spacing";
               }
               enum "1558.17" {
                 description "1558.17 nm/192.4000 THz 12.5/50/100GHz spacing";
               }
               enum "1558.07" {
                 description "1558.07 nm/192.4125 THz 12.5GHz spacing";
               }
               enum "1557.97" {
                 description "1557.97 nm/192.4250 THz 12.5GHz spacing";
               }
               enum "1557.87" {
                 description "1557.87 nm/192.4375 THz 12.5GHz spacing";
               }
               enum "1557.77" {
                 description "1557.77 nm/192.4500 THz 12.5/50GHz spacing";
               }
               enum "1557.67" {
                 description "1557.67 nm/192.4625 THz 12.5GHz spacing";
               }
               enum "1557.57" {
                 description "1557.57 nm/192.4750 THz 12.5GHz spacing";
               }
               enum "1557.46" {
                 description "1557.46 nm/192.4875 THz 12.5GHz spacing";
               }
               enum "1557.36" {
                 description "1557.36 nm/192.5000 THz 12.5/50/100GHz spacing";
               }
               enum "1557.26" {
                 description "1557.26 nm/192.5125 THz 12.5GHz spacing";
               }
               enum "1557.16" {
                 description "1557.16 nm/192.5250 THz 12.5GHz spacing";
               }
               enum "1557.06" {
                 description "1557.06 nm/192.5375 THz 12.5GHz spacing";
               }
               enum "1556.96" {
                 description "1556.96 nm/192.5500 THz 12.5/50GHz spacing";
               }
               enum "1556.86" {
                 description "1556.86 nm/192.5625 THz 12.5GHz spacing";
               }
               enum "1556.76" {
                 description "1556.76 nm/192.5750 THz 12.5GHz spacing";
               }
               enum "1556.66" {
                 description "1556.66 nm/192.5875 THz 12.5GHz spacing";
               }
               enum "1556.55" {
                 description "1556.55 nm/192.6000 THz 12.5/50/100GHz spacing";
               }
               enum "1556.45" {
                 description "1556.45 nm/192.6125 THz 12.5GHz spacing";
               }
               enum "1556.35" {
                 description "1556.35 nm/192.6250 THz 12.5GHz spacing";
               }
               enum "1556.25" {
                 description "1556.25 nm/192.6375 THz 12.5GHz spacing";
               }
               enum "1556.15" {
                 description "1556.15 nm/192.6500 THz 12.5/50GHz spacing";
               }
               enum "1556.05" {
                 description "1556.05 nm/192.6625 THz 12.5GHz spacing";
               }
               enum "1555.95" {
                 description "1555.95 nm/192.6750 THz 12.5GHz spacing";
               }
               enum "1555.85" {
                 description "1555.85 nm/192.6875 THz 12.5GHz spacing";
               }
               enum "1555.75" {
                 description "1555.75 nm/192.7000 THz 12.5/50/100GHz spacing";
               }
               enum "1555.65" {
                 description "1555.65 nm/192.7125 THz 12.5GHz spacing";
               }
               enum "1555.55" {
                 description "1555.55 nm/192.7250 THz 12.5GHz spacing";
               }
               enum "1555.44" {
                 description "1555.44 nm/192.7375 THz 12.5GHz spacing";
               }
               enum "1555.34" {
                 description "1555.34 nm/192.7500 THz 12.5/50GHz spacing";
               }
               enum "1555.24" {
                 description "1555.24 nm/192.7625 THz 12.5GHz spacing";
               }
               enum "1555.14" {
                 description "1555.14 nm/192.7750 THz 12.5GHz spacing";
               }
               enum "1555.04" {
                 description "1555.04 nm/192.7875 THz 12.5GHz spacing";
               }
               enum "1554.94" {
                 description "1554.94 nm/192.8000 THz 12.5/50/100GHz spacing";
               }
               enum "1554.84" {
                 description "1554.84 nm/192.8125 THz 12.5GHz spacing";
               }
               enum "1554.74" {
                 description "1554.74 nm/192.8250 THz 12.5GHz spacing";
               }
               enum "1554.64" {
                 description "1554.64 nm/192.8375 THz 12.5GHz spacing";
               }
               enum "1554.54" {
                 description "1554.54 nm/192.8500 THz 12.5/50GHz spacing";
               }
               enum "1554.44" {
                 description "1554.44 nm/192.8625 THz 12.5GHz spacing";
               }
               enum "1554.34" {
                 description "1554.34 nm/192.8750 THz 12.5GHz spacing";
               }
               enum "1554.23" {
                 description "1554.23 nm/192.8875 THz 12.5GHz spacing";
               }
               enum "1554.13" {
                 description "1554.13 nm/192.9000 THz 12.5/50/100GHz spacing";
               }
               enum "1554.03" {
                 description "1554.03 nm/192.9125 THz 12.5GHz spacing";
               }
               enum "1553.93" {
                 description "1553.93 nm/192.9250 THz 12.5GHz spacing";
               }
               enum "1553.83" {
                 description "1553.83 nm/192.9375 THz 12.5GHz spacing";
               }
               enum "1553.73" {
                 description "1553.73 nm/192.9500 THz 12.5/50GHz spacing";
               }
               enum "1553.63" {
                 description "1553.63 nm/192.9625 THz 12.5GHz spacing";
               }
               enum "1553.53" {
                 description "1553.53 nm/192.9750 THz 12.5GHz spacing";
               }
               enum "1553.43" {
                 description "1553.43 nm/192.9875 THz 12.5GHz spacing";
               }
               enum "1553.33" {
                 description "1553.33 nm/193.0000 THz 12.5/50/100GHz spacing";
               }
               enum "1553.23" {
                 description "1553.23 nm/193.0125 THz 12.5GHz spacing";
               }
               enum "1553.13" {
                 description "1553.13 nm/193.0250 THz 12.5GHz spacing";
               }
               enum "1553.03" {
                 description "1553.03 nm/193.0375 THz 12.5GHz spacing";
               }
               enum "1552.93" {
                 description "1552.93 nm/193.0500 THz 12.5/50GHz spacing";
               }
               enum "1552.83" {
                 description "1552.83 nm/193.0625 THz 12.5GHz spacing";
               }
               enum "1552.73" {
                 description "1552.73 nm/193.0750 THz 12.5GHz spacing";
               }
               enum "1552.62" {
                 description "1552.62 nm/193.0875 THz 12.5GHz spacing";
               }
               enum "1552.52" {
                 description "1552.52 nm/193.1000 THz 12.5/50/100GHz spacing";
               }
               enum "1552.42" {
                 description "1552.42 nm/193.1125 THz 12.5GHz spacing";
               }
               enum "1552.32" {
                 description "1552.32 nm/193.1250 THz 12.5GHz spacing";
               }
               enum "1552.22" {
                 description "1552.22 nm/193.1375 THz 12.5GHz spacing";
               }
               enum "1552.12" {
                 description "1552.12 nm/193.1500 THz 12.5/50GHz spacing";
               }
               enum "1552.02" {
                 description "1552.02 nm/193.1625 THz 12.5GHz spacing";
               }
               enum "1551.92" {
                 description "1551.92 nm/193.1750 THz 12.5GHz spacing";
               }
               enum "1551.82" {
                 description "1551.82 nm/193.1875 THz 12.5GHz spacing";
               }
               enum "1551.72" {
                 description "1551.72 nm/193.2000 THz 12.5/50/100GHz spacing";
               }
               enum "1551.62" {
                 description "1551.62 nm/193.2125 THz 12.5GHz spacing";
               }
               enum "1551.52" {
                 description "1551.52 nm/193.2250 THz 12.5GHz spacing";
               }
               enum "1551.42" {
                 description "1551.42 nm/193.2375 THz 12.5GHz spacing";
               }
               enum "1551.32" {
                 description "1551.32 nm/193.2500 THz 12.5/50GHz spacing";
               }
               enum "1551.22" {
                 description "1551.22 nm/193.2625 THz 12.5GHz spacing";
               }
               enum "1551.12" {
                 description "1551.12 nm/193.2750 THz 12.5GHz spacing";
               }
               enum "1551.02" {
                 description "1551.02 nm/193.2875 THz 12.5GHz spacing";
               }
               enum "1550.92" {
                 description "1550.92 nm/193.3000 THz 12.5/50/100GHz spacing";
               }
               enum "1550.82" {
                 description "1550.82 nm/193.3125 THz 12.5GHz spacing";
               }
               enum "1550.72" {
                 description "1550.72 nm/193.3250 THz 12.5GHz spacing";
               }
               enum "1550.62" {
                 description "1550.62 nm/193.3375 THz 12.5GHz spacing";
               }
               enum "1550.52" {
                 description "1550.52 nm/193.3500 THz 12.5/50GHz spacing";
               }
               enum "1550.42" {
                 description "1550.42 nm/193.3625 THz 12.5GHz spacing";
               }
               enum "1550.32" {
                 description "1550.32 nm/193.3750 THz 12.5GHz spacing";
               }
               enum "1550.22" {
                 description "1550.22 nm/193.3875 THz 12.5GHz spacing";
               }
               enum "1550.12" {
                 description "1550.12 nm/193.4000 THz 12.5/50/100GHz spacing";
               }
               enum "1550.02" {
                 description "1550.02 nm/193.4125 THz 12.5GHz spacing";
               }
               enum "1549.92" {
                 description "1549.92 nm/193.4250 THz 12.5GHz spacing";
               }
               enum "1549.82" {
                 description "1549.82 nm/193.4375 THz 12.5GHz spacing";
               }
               enum "1549.72" {
                 description "1549.72 nm/193.4500 THz 12.5/50GHz spacing";
               }
               enum "1549.62" {
                 description "1549.62 nm/193.4625 THz 12.5GHz spacing";
               }
               enum "1549.52" {
                 description "1549.52 nm/193.4750 THz 12.5GHz spacing";
               }
               enum "1549.42" {
                 description "1549.42 nm/193.4875 THz 12.5GHz spacing";
               }
               enum "1549.32" {
                 description "1549.32 nm/193.5000 THz 12.5/50/100GHz spacing";
               }
               enum "1549.21" {
                 description "1549.21 nm/193.5125 THz 12.5GHz spacing";
               }
               enum "1549.11" {
                 description "1549.11 nm/193.5250 THz 12.5GHz spacing";
               }
               enum "1549.01" {
                 description "1549.01 nm/193.5375 THz 12.5GHz spacing";
               }
               enum "1548.91" {
                 description "1548.91 nm/193.5500 THz 12.5/50GHz spacing";
               }
               enum "1548.81" {
                 description "1548.81 nm/193.5625 THz 12.5GHz spacing";
               }
               enum "1548.71" {
                 description "1548.71 nm/193.5750 THz 12.5GHz spacing";
               }
               enum "1548.61" {
                 description "1548.61 nm/193.5875 THz 12.5GHz spacing";
               }
               enum "1548.51" {
                 description "1548.51 nm/193.6000 THz 12.5/50/100GHz spacing";
               }
               enum "1548.41" {
                 description "1548.41 nm/193.6125 THz 12.5GHz spacing";
               }
               enum "1548.31" {
                 description "1548.31 nm/193.6250 THz 12.5GHz spacing";
               }
               enum "1548.21" {
                 description "1548.21 nm/193.6375 THz 12.5GHz spacing";
               }
               enum "1548.11" {
                 description "1548.11 nm/193.6500 THz 12.5/50GHz spacing";
               }
               enum "1548.02" {
                 description "1548.02 nm/193.6625 THz 12.5GHz spacing";
               }
               enum "1547.92" {
                 description "1547.92 nm/193.6750 THz 12.5GHz spacing";
               }
               enum "1547.82" {
                 description "1547.82 nm/193.6875 THz 12.5GHz spacing";
               }
               enum "1547.72" {
                 description "1547.72 nm/193.7000 THz 12.5/50/100GHz spacing";
               }
               enum "1547.62" {
                 description "1547.62 nm/193.7125 THz 12.5GHz spacing";
               }
               enum "1547.52" {
                 description "1547.52 nm/193.7250 THz 12.5GHz spacing";
               }
               enum "1547.42" {
                 description "1547.42 nm/193.7375 THz 12.5GHz spacing";
               }
               enum "1547.32" {
                 description "1547.32 nm/193.7500 THz 12.5/50GHz spacing";
               }
               enum "1547.22" {
                 description "1547.22 nm/193.7625 THz 12.5GHz spacing";
               }
               enum "1547.12" {
                 description "1547.12 nm/193.7750 THz 12.5GHz spacing";
               }
               enum "1547.02" {
                 description "1547.02 nm/193.7875 THz 12.5GHz spacing";
               }
               enum "1546.92" {
                 description "1546.92 nm/193.8000 THz 12.5/50/100GHz spacing";
               }
               enum "1546.82" {
                 description "1546.82 nm/193.8125 THz 12.5GHz spacing";
               }
               enum "1546.72" {
                 description "1546.72 nm/193.8250 THz 12.5GHz spacing";
               }
               enum "1546.62" {
                 description "1546.62 nm/193.8375 THz 12.5GHz spacing";
               }
               enum "1546.52" {
                 description "1546.52 nm/193.8500 THz 12.5/50GHz spacing";
               }
               enum "1546.42" {
                 description "1546.42 nm/193.8625 THz 12.5GHz spacing";
               }
               enum "1546.32" {
                 description "1546.32 nm/193.8750 THz 12.5GHz spacing";
               }
               enum "1546.22" {
                 description "1546.22 nm/193.8875 THz 12.5GHz spacing";
               }
               enum "1546.12" {
                 description "1546.12 nm/193.9000 THz 12.5/50/100GHz spacing";
               }
               enum "1546.02" {
                 description "1546.02 nm/193.9125 THz 12.5GHz spacing";
               }
               enum "1545.92" {
                 description "1545.92 nm/193.9250 THz 12.5GHz spacing";
               }
               enum "1545.82" {
                 description "1545.82 nm/193.9375 THz 12.5GHz spacing";
               }
               enum "1545.72" {
                 description "1545.72 nm/193.9500 THz 12.5/50GHz spacing";
               }
               enum "1545.62" {
                 description "1545.62 nm/193.9625 THz 12.5GHz spacing";
               }
               enum "1545.52" {
                 description "1545.52 nm/193.9750 THz 12.5GHz spacing";
               }
               enum "1545.42" {
                 description "1545.42 nm/193.9875 THz 12.5GHz spacing";
               }
               enum "1545.32" {
                 description "1545.32 nm/194.0000 THz 12.5/50/100GHz spacing";
               }
               enum "1545.22" {
                 description "1545.22 nm/194.0125 THz 12.5GHz spacing";
               }
               enum "1545.12" {
                 description "1545.12 nm/194.0250 THz 12.5GHz spacing";
               }
               enum "1545.02" {
                 description "1545.02 nm/194.0375 THz 12.5GHz spacing";
               }
               enum "1544.92" {
                 description "1544.92 nm/194.0500 THz 12.5/50GHz spacing";
               }
               enum "1544.82" {
                 description "1544.82 nm/194.0625 THz 12.5GHz spacing";
               }
               enum "1544.72" {
                 description "1544.72 nm/194.0750 THz 12.5GHz spacing";
               }
               enum "1544.63" {
                 description "1544.63 nm/194.0875 THz 12.5GHz spacing";
               }
               enum "1544.53" {
                 description "1544.53 nm/194.1000 THz 12.5/50/100GHz spacing";
               }
               enum "1544.43" {
                 description "1544.43 nm/194.1125 THz 12.5GHz spacing";
               }
               enum "1544.33" {
                 description "1544.33 nm/194.1250 THz 12.5GHz spacing";
               }
               enum "1544.23" {
                 description "1544.23 nm/194.1375 THz 12.5GHz spacing";
               }
               enum "1544.13" {
                 description "1544.13 nm/194.1500 THz 12.5/50GHz spacing";
               }
               enum "1544.03" {
                 description "1544.03 nm/194.1625 THz 12.5GHz spacing";
               }
               enum "1543.93" {
                 description "1543.93 nm/194.1750 THz 12.5GHz spacing";
               }
               enum "1543.83" {
                 description "1543.83 nm/194.1875 THz 12.5GHz spacing";
               }
               enum "1543.73" {
                 description "1543.73 nm/194.2000 THz 12.5/50/100GHz spacing";
               }
               enum "1543.63" {
                 description "1543.63 nm/194.2125 THz 12.5GHz spacing";
               }
               enum "1543.53" {
                 description "1543.53 nm/194.2250 THz 12.5GHz spacing";
               }
               enum "1543.43" {
                 description "1543.43 nm/194.2375 THz 12.5GHz spacing";
               }
               enum "1543.33" {
                 description "1543.33 nm/194.2500 THz 12.5/50GHz spacing";
               }
               enum "1543.23" {
                 description "1543.23 nm/194.2625 THz 12.5GHz spacing";
               }
               enum "1543.13" {
                 description "1543.13 nm/194.2750 THz 12.5GHz spacing";
               }
               enum "1543.04" {
                 description "1543.04 nm/194.2875 THz 12.5GHz spacing";
               }
               enum "1542.94" {
                 description "1542.94 nm/194.3000 THz 12.5/50/100GHz spacing";
               }
               enum "1542.84" {
                 description "1542.84 nm/194.3125 THz 12.5GHz spacing";
               }
               enum "1542.74" {
                 description "1542.74 nm/194.3250 THz 12.5GHz spacing";
               }
               enum "1542.64" {
                 description "1542.64 nm/194.3375 THz 12.5GHz spacing";
               }
               enum "1542.54" {
                 description "1542.54 nm/194.3500 THz 12.5/50GHz spacing";
               }
               enum "1542.44" {
                 description "1542.44 nm/194.3625 THz 12.5GHz spacing";
               }
               enum "1542.34" {
                 description "1542.34 nm/194.3750 THz 12.5GHz spacing";
               }
               enum "1542.24" {
                 description "1542.24 nm/194.3875 THz 12.5GHz spacing";
               }
               enum "1542.14" {
                 description "1542.14 nm/194.4000 THz 12.5/50/100GHz spacing";
               }
               enum "1542.04" {
                 description "1542.04 nm/194.4125 THz 12.5GHz spacing";
               }
               enum "1541.94" {
                 description "1541.94 nm/194.4250 THz 12.5GHz spacing";
               }
               enum "1541.84" {
                 description "1541.84 nm/194.4375 THz 12.5GHz spacing";
               }
               enum "1541.75" {
                 description "1541.75 nm/194.4500 THz 12.5/50GHz spacing";
               }
               enum "1541.65" {
                 description "1541.65 nm/194.4625 THz 12.5GHz spacing";
               }
               enum "1541.55" {
                 description "1541.55 nm/194.4750 THz 12.5GHz spacing";
               }
               enum "1541.45" {
                 description "1541.45 nm/194.4875 THz 12.5GHz spacing";
               }
               enum "1541.35" {
                 description "1541.35 nm/194.5000 THz 12.5/50/100GHz spacing";
               }
               enum "1541.25" {
                 description "1541.25 nm/194.5125 THz 12.5GHz spacing";
               }
               enum "1541.15" {
                 description "1541.15 nm/194.5250 THz 12.5GHz spacing";
               }
               enum "1541.05" {
                 description "1541.05 nm/194.5375 THz 12.5GHz spacing";
               }
               enum "1540.95" {
                 description "1540.95 nm/194.5500 THz 12.5/50GHz spacing";
               }
               enum "1540.85" {
                 description "1540.85 nm/194.5625 THz 12.5GHz spacing";
               }
               enum "1540.76" {
                 description "1540.76 nm/194.5750 THz 12.5GHz spacing";
               }
               enum "1540.66" {
                 description "1540.66 nm/194.5875 THz 12.5GHz spacing";
               }
               enum "1540.56" {
                 description "1540.56 nm/194.6000 THz 12.5/50/100GHz spacing";
               }
               enum "1540.46" {
                 description "1540.46 nm/194.6125 THz 12.5GHz spacing";
               }
               enum "1540.36" {
                 description "1540.36 nm/194.6250 THz 12.5GHz spacing";
               }
               enum "1540.26" {
                 description "1540.26 nm/194.6375 THz 12.5GHz spacing";
               }
               enum "1540.16" {
                 description "1540.16 nm/194.6500 THz 12.5/50GHz spacing";
               }
               enum "1540.06" {
                 description "1540.06 nm/194.6625 THz 12.5GHz spacing";
               }
               enum "1539.96" {
                 description "1539.96 nm/194.6750 THz 12.5GHz spacing";
               }
               enum "1539.86" {
                 description "1539.86 nm/194.6875 THz 12.5GHz spacing";
               }
               enum "1539.77" {
                 description "1539.77 nm/194.7000 THz 12.5/50/100GHz spacing";
               }
               enum "1539.67" {
                 description "1539.67 nm/194.7125 THz 12.5GHz spacing";
               }
               enum "1539.57" {
                 description "1539.57 nm/194.7250 THz 12.5GHz spacing";
               }
               enum "1539.47" {
                 description "1539.47 nm/194.7375 THz 12.5GHz spacing";
               }
               enum "1539.37" {
                 description "1539.37 nm/194.7500 THz 12.5/50GHz spacing";
               }
               enum "1539.27" {
                 description "1539.27 nm/194.7625 THz 12.5GHz spacing";
               }
               enum "1539.17" {
                 description "1539.17 nm/194.7750 THz 12.5GHz spacing";
               }
               enum "1539.07" {
                 description "1539.07 nm/194.7875 THz 12.5GHz spacing";
               }
               enum "1538.98" {
                 description "1538.98 nm/194.8000 THz 12.5/50/100GHz spacing";
               }
               enum "1538.88" {
                 description "1538.88 nm/194.8125 THz 12.5GHz spacing";
               }
               enum "1538.78" {
                 description "1538.78 nm/194.8250 THz 12.5GHz spacing";
               }
               enum "1538.68" {
                 description "1538.68 nm/194.8375 THz 12.5GHz spacing";
               }
               enum "1538.58" {
                 description "1538.58 nm/194.8500 THz 12.5/50GHz spacing";
               }
               enum "1538.48" {
                 description "1538.48 nm/194.8625 THz 12.5GHz spacing";
               }
               enum "1538.38" {
                 description "1538.38 nm/194.8750 THz 12.5GHz spacing";
               }
               enum "1538.28" {
                 description "1538.28 nm/194.8875 THz 12.5GHz spacing";
               }
               enum "1538.19" {
                 description "1538.19 nm/194.9000 THz 12.5/50/100GHz spacing";
               }
               enum "1538.09" {
                 description "1538.09 nm/194.9125 THz 12.5GHz spacing";
               }
               enum "1537.99" {
                 description "1537.99 nm/194.9250 THz 12.5GHz spacing";
               }
               enum "1537.89" {
                 description "1537.89 nm/194.9375 THz 12.5GHz spacing";
               }
               enum "1537.79" {
                 description "1537.79 nm/194.9500 THz 12.5/50GHz spacing";
               }
               enum "1537.69" {
                 description "1537.69 nm/194.9625 THz 12.5GHz spacing";
               }
               enum "1537.59" {
                 description "1537.59 nm/194.9750 THz 12.5GHz spacing";
               }
               enum "1537.50" {
                 description "1537.50 nm/194.9875 THz 12.5GHz spacing";
               }
               enum "1537.40" {
                 description "1537.40 nm/195.0000 THz 12.5/50/100GHz spacing";
               }
               enum "1537.30" {
                 description "1537.30 nm/195.0125 THz 12.5GHz spacing";
               }
               enum "1537.20" {
                 description "1537.20 nm/195.0250 THz 12.5GHz spacing";
               }
               enum "1537.10" {
                 description "1537.10 nm/195.0375 THz 12.5GHz spacing";
               }
               enum "1537.00" {
                 description "1537.00 nm/195.0500 THz 12.5/50GHz spacing";
               }
               enum "1536.90" {
                 description "1536.90 nm/195.0625 THz 12.5GHz spacing";
               }
               enum "1536.81" {
                 description "1536.81 nm/195.0750 THz 12.5GHz spacing";
               }
               enum "1536.71" {
                 description "1536.71 nm/195.0875 THz 12.5GHz spacing";
               }
               enum "1536.61" {
                 description "1536.61 nm/195.1000 THz 12.5/50/100GHz spacing";
               }
               enum "1536.51" {
                 description "1536.51 nm/195.1125 THz 12.5GHz spacing";
               }
               enum "1536.41" {
                 description "1536.41 nm/195.1250 THz 12.5GHz spacing";
               }
               enum "1536.31" {
                 description "1536.31 nm/195.1375 THz 12.5GHz spacing";
               }
               enum "1536.22" {
                 description "1536.22 nm/195.1500 THz 12.5/50GHz spacing";
               }
               enum "1536.12" {
                 description "1536.12 nm/195.1625 THz 12.5GHz spacing";
               }
               enum "1536.02" {
                 description "1536.02 nm/195.1750 THz 12.5GHz spacing";
               }
               enum "1535.92" {
                 description "1535.92 nm/195.1875 THz 12.5GHz spacing";
               }
               enum "1535.82" {
                 description "1535.82 nm/195.2000 THz 12.5/50/100GHz spacing";
               }
               enum "1535.72" {
                 description "1535.72 nm/195.2125 THz 12.5GHz spacing";
               }
               enum "1535.63" {
                 description "1535.63 nm/195.2250 THz 12.5GHz spacing";
               }
               enum "1535.53" {
                 description "1535.53 nm/195.2375 THz 12.5GHz spacing";
               }
               enum "1535.43" {
                 description "1535.43 nm/195.2500 THz 12.5/50GHz spacing";
               }
               enum "1535.33" {
                 description "1535.33 nm/195.2625 THz 12.5GHz spacing";
               }
               enum "1535.23" {
                 description "1535.23 nm/195.2750 THz 12.5GHz spacing";
               }
               enum "1535.13" {
                 description "1535.13 nm/195.2875 THz 12.5GHz spacing";
               }
               enum "1535.04" {
                 description "1535.04 nm/195.3000 THz 12.5/50/100GHz spacing";
               }
               enum "1534.94" {
                 description "1534.94 nm/195.3125 THz 12.5GHz spacing";
               }
               enum "1534.84" {
                 description "1534.84 nm/195.3250 THz 12.5GHz spacing";
               }
               enum "1534.74" {
                 description "1534.74 nm/195.3375 THz 12.5GHz spacing";
               }
               enum "1534.64" {
                 description "1534.64 nm/195.3500 THz 12.5/50GHz spacing";
               }
               enum "1534.54" {
                 description "1534.54 nm/195.3625 THz 12.5GHz spacing";
               }
               enum "1534.45" {
                 description "1534.45 nm/195.3750 THz 12.5GHz spacing";
               }
               enum "1534.35" {
                 description "1534.35 nm/195.3875 THz 12.5GHz spacing";
               }
               enum "1534.25" {
                 description "1534.25 nm/195.4000 THz 12.5/50/100GHz spacing";
               }
               enum "1534.15" {
                 description "1534.15 nm/195.4125 THz 12.5GHz spacing";
               }
               enum "1534.05" {
                 description "1534.05 nm/195.4250 THz 12.5GHz spacing";
               }
               enum "1533.96" {
                 description "1533.96 nm/195.4375 THz 12.5GHz spacing";
               }
               enum "1533.86" {
                 description "1533.86 nm/195.4500 THz 12.5/50GHz spacing";
               }
               enum "1533.76" {
                 description "1533.76 nm/195.4625 THz 12.5GHz spacing";
               }
               enum "1533.66" {
                 description "1533.66 nm/195.4750 THz 12.5GHz spacing";
               }
               enum "1533.56" {
                 description "1533.56 nm/195.4875 THz 12.5GHz spacing";
               }
               enum "1533.47" {
                 description "1533.47 nm/195.5000 THz 12.5/50/100GHz spacing";
               }
               enum "1533.37" {
                 description "1533.37 nm/195.5125 THz 12.5GHz spacing";
               }
               enum "1533.27" {
                 description "1533.27 nm/195.5250 THz 12.5GHz spacing";
               }
               enum "1533.17" {
                 description "1533.17 nm/195.5375 THz 12.5GHz spacing";
               }
               enum "1533.07" {
                 description "1533.07 nm/195.5500 THz 12.5/50GHz spacing";
               }
               enum "1532.98" {
                 description "1532.98 nm/195.5625 THz 12.5GHz spacing";
               }
               enum "1532.88" {
                 description "1532.88 nm/195.5750 THz 12.5GHz spacing";
               }
               enum "1532.78" {
                 description "1532.78 nm/195.5875 THz 12.5GHz spacing";
               }
               enum "1532.68" {
                 description "1532.68 nm/195.6000 THz 12.5/50/100GHz spacing";
               }
               enum "1532.58" {
                 description "1532.58 nm/195.6125 THz 12.5GHz spacing";
               }
               enum "1532.49" {
                 description "1532.49 nm/195.6250 THz 12.5GHz spacing";
               }
               enum "1532.39" {
                 description "1532.39 nm/195.6375 THz 12.5GHz spacing";
               }
               enum "1532.29" {
                 description "1532.29 nm/195.6500 THz 12.5/50GHz spacing";
               }
               enum "1532.19" {
                 description "1532.19 nm/195.6625 THz 12.5GHz spacing";
               }
               enum "1532.09" {
                 description "1532.09 nm/195.6750 THz 12.5GHz spacing";
               }
               enum "1532.00" {
                 description "1532.00 nm/195.6875 THz 12.5GHz spacing";
               }
               enum "1531.90" {
                 description "1531.90 nm/195.7000 THz 12.5/50/100GHz spacing";
               }
               enum "1531.80" {
                 description "1531.80 nm/195.7125 THz 12.5GHz spacing";
               }
               enum "1531.70" {
                 description "1531.70 nm/195.7250 THz 12.5GHz spacing";
               }
               enum "1531.60" {
                 description "1531.60 nm/195.7375 THz 12.5GHz spacing";
               }
               enum "1531.51" {
                 description "1531.51 nm/195.7500 THz 12.5/50GHz spacing";
               }
               enum "1531.41" {
                 description "1531.41 nm/195.7625 THz 12.5GHz spacing";
               }
               enum "1531.31" {
                 description "1531.31 nm/195.7750 THz 12.5GHz spacing";
               }
               enum "1531.21" {
                 description "1531.21 nm/195.7875 THz 12.5GHz spacing";
               }
               enum "1531.12" {
                 description "1531.12 nm/195.8000 THz 12.5/50/100GHz spacing";
               }
               enum "1531.02" {
                 description "1531.02 nm/195.8125 THz 12.5GHz spacing";
               }
               enum "1530.92" {
                 description "1530.92 nm/195.8250 THz 12.5GHz spacing";
               }
               enum "1530.82" {
                 description "1530.82 nm/195.8375 THz 12.5GHz spacing";
               }
               enum "1530.72" {
                 description "1530.72 nm/195.8500 THz 12.5/50GHz spacing";
               }
               enum "1530.63" {
                 description "1530.63 nm/195.8625 THz 12.5GHz spacing";
               }
               enum "1530.53" {
                 description "1530.53 nm/195.8750 THz 12.5GHz spacing";
               }
               enum "1530.43" {
                 description "1530.43 nm/195.8875 THz 12.5GHz spacing";
               }
               enum "1530.33" {
                 description "1530.33 nm/195.9000 THz 12.5/50/100GHz spacing";
               }
               enum "1530.24" {
                 description "1530.24 nm/195.9125 THz 12.5GHz spacing";
               }
               enum "1530.14" {
                 description "1530.14 nm/195.9250 THz 12.5GHz spacing";
               }
               enum "1530.04" {
                 description "1530.04 nm/195.9375 THz 12.5GHz spacing";
               }
               enum "1529.94" {
                 description "1529.94 nm/195.9500 THz 12.5/50GHz spacing";
               }
               enum "1529.85" {
                 description "1529.85 nm/195.9625 THz 12.5GHz spacing";
               }
               enum "1529.75" {
                 description "1529.75 nm/195.9750 THz 12.5GHz spacing";
               }
               enum "1529.65" {
                 description "1529.65 nm/195.9875 THz 12.5GHz spacing";
               }
               enum "1529.55" {
                 description "1529.55 nm/196.0000 THz 12.5/50/100GHz spacing";
               }
               enum "1529.46" {
                 description "1529.46 nm/196.0125 THz 12.5GHz spacing";
               }
               enum "1529.36" {
                 description "1529.36 nm/196.0250 THz 12.5GHz spacing";
               }
               enum "1529.26" {
                 description "1529.26 nm/196.0375 THz 12.5GHz spacing";
               }
               enum "1529.16" {
                 description "1529.16 nm/196.0500 THz 12.5/50GHz spacing";
               }
               enum "1529.07" {
                 description "1529.07 nm/196.0625 THz 12.5GHz spacing";
               }
               enum "1528.97" {
                 description "1528.97 nm/196.0750 THz 12.5GHz spacing";
               }
               enum "1528.87" {
                 description "1528.87 nm/196.0875 THz 12.5GHz spacing";
               }
               enum "1528.77" {
                 description "1528.77 nm/196.1000 THz 12.5/50/100GHz spacing";
               }
               enum "1528.38" {
                 description "1528.38 nm/196.1504 THz 50Ghz spacing";
               }
             }
           }
           leaf tx-power {
             description "Transmit laser output power";
             units "dBm";
             type string;
           }
           leaf loopback {
             description "Put the optics in loopback mode";
             type empty;
           }
           leaf los-warning-threshold {
             description "LOS warning threshold";
             units "dBm";
             type string;
           }
           leaf los-alarm-threshold {
             description "LOS alarm threshold";
             units "dBm";
             type string;
           }
           leaf modulation-format {
             description "Type of Modulation Format";
             type enumeration {
               enum "16qam" {
                 description "16-QAM Modulation Format";
               }
               enum "8qam" {
                 description "8-QAM MOdulation Format";
               }
               enum "qpsk" {
                 description "QPSK Modulation Format";
               }
             }
           }
           choice laser-enable-choice {
             leaf laser-enable {
               description "Enable Laser";
               type empty;
             }
             leaf no-laser-enable {
               description "Don't enable Laser";
               type empty;
             }
           }
           choice is-ma-choice {
             leaf is-ma {
               description "Link is enabled with alarms masked";
               type empty;
             }
             leaf no-is-ma {
               description "Don't link is enabled with alarms masked";
               type empty;
             }
           }
           leaf encoding {
             description "Line encoding";
             type enumeration {
               enum "differential" {
                 description "Differential phase line encoding";
               }
               enum "non-differential" {
                 description "Non-differential phase line encoding";
               }
             }
           }
           leaf fec {
             description "Forward Error Correction mode";
             type enumeration {
               enum "sdfec" {
                 description "SDFEC-Sky-Compatible Soft Decision Forward Error Correction";
               }
               enum "sdfec25" {
                 description "SDFEC-Denali Soft Decision Forward Error Correction with 25 percent overhead";
               }
             }
           }
           list alarm {
             key name;
             ordered-by user;
             description "Set optic alarms";
             leaf name {
               type enumeration {
                 enum "low-light-alarm" {
                   description "Enable low light alarm";
                 }
               }
             }
             uses apply-advanced;
             choice actiontype {
               case case_1 {
                 leaf syslog {
                   type empty;
                 }
               }
               case case_2 {
                 leaf link-down {
                   type empty;
                 }
               }
             }
           }
           container tca {
             description "Set tca for optic alarms";
             uses apply-advanced;
             container tx-power-high-tca {
               description "Tx power high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute tx power high TCA in dBm";
                 type string;
               }
               leaf threshold-24hrs {
                 description "Threshold for 24 hour tx power high TCA in dBm";
                 type string;
               }
             }
             container tx-power-low-tca {
               description "Tx power low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute tx power low TCA in dBm";
                 type string;
               }
               leaf threshold-24hrs {
                 description "Threshold for 24 hour tx power low TCA in dBm";
                 type string;
               }
             }
             container rx-power-high-tca {
               description "Rx power high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute rx power high TCA in dBm";
                 type string;
               }
               leaf threshold-24hrs {
                 description "Threshold for 24 hour rx power high TCA in dBm";
                 type string;
               }
             }
             container rx-power-low-tca {
               description "Rx power low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute rx power low TCA in dBm";
                 type string;
               }
               leaf threshold-24hrs {
                 description "Threshold for 24 hour rx power low TCA in dBm";
                 type string;
               }
             }
             container temperature-high-tca {
               description "Temperature high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute high temperature TCA in celsius";
                 type string;
               }
               leaf threshold-24hrs {
                 description "Threshold for 24 hour high temperature TCA in celsius";
                 type string;
               }
             }
             container temperature-low-tca {
               description "Temperature low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute low temperature TCA in celsius";
                 type string;
               }
               leaf threshold-24hrs {
                 description "Threshold for 24 hour low temperature TCA in celsius";
                 type string;
               }
             }
             container carrier-frequency-offset-high-tca {
               description "Carrier frequency offset high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute frequency offset high TCA in MHz";
                 type string;
               }
               leaf threshold-24hrs {
                 description "Threshold for 24 hour frequency offset high TCA in MHz";
                 type string;
               }
             }
             container carrier-frequency-offset-low-tca {
               description "Carrier frequency offset low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute frequency offset low TCA in MHz";
                 type string;
               }
               leaf threshold-24hrs {
                 description "Threshold for 24 hour frequency offset low TCA in MHz";
                 type string;
               }
             }
             container fec-ber {
               description "Optics Errored Seconds Threshold crossing defect trigger";
               choice enable-tca-choice {
                 leaf enable-tca {
                   description "Enable the Optics errored seconds threshold crossing alert";
                   type empty;
                 }
                 leaf no-enable-tca {
                   description "Don't enable the Optics errored seconds threshold crossing alert";
                   type empty;
                 }
               }
               leaf threshold {
                 description "TCA threshold for BER value in format: xe-n, x is an integer or decimal number, n = 0..9";
                 default "10e-3";
                 type string {
                 }
               }
               leaf threshold-24hrs {
                 description "TCA threshold for BER value in format: xe-n, x is an integer or decimal number, n = 0..9";
                 default "10e-3";
                 type string {
                 }
               }
             }
             container tec-current-high-tca {
               description "TEC Current high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute TEC Current high TCA in mA";
                 type string;
               }
               leaf threshold-24hrs {
                 description "Threshold for 24 hour TEC Current high TCA in mA";
                 type string;
               }
             }
             container tec-current-low-tca {
               description "TEC Current low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute TEC Current low TCA in mA";
                 type string;
               }
               leaf threshold-24hrs {
                 description "Threshold for 24 hour TEC Current low TCA in mA";
                 type string;
               }
             }
             container residual-isi-high-tca {
               description "Residual ISI high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute Residual ISI high TCA in ps/nm";
                 type string;
               }
               leaf threshold-24hrs {
                 description "Threshold for 24 hour Residual ISI high TCA in ps/nm";
                 type string;
               }
             }
             container residual-isi-low-tca {
               description "Residual ISI low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute Residual ISI low TCA in ps/nm";
                 type string;
               }
               leaf threshold-24hrs {
                 description "Threshold for 24 hour Residual ISI low TCA in ps/nm";
                 type string;
               }
             }
             container pam-histogram-high-tca {
               description "PAM Histogram high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute PAM Histogram high TCA";
                 type string;
               }
               leaf threshold-24hrs {
                 description "Threshold for 24 hour PAM Histogram high TCA";
                 type string;
               }
             }
             container snr-low-tca {
               description "SNR low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute SNR low TCA in dBm ";
                 type string;
               }
               leaf threshold-24hrs {
                 description "Threshold for 24 hour SNR low TCA in dBm";
                 type string;
               }
             }
             container fec-corrected-errors-high-tca {
               description "FEC Corrected Error High Threshold crossing defect trigger";
               uses apply-advanced;
               choice enable-tca-choice {
                 leaf enable-tca {
                   description "Enable the FEC Corrected Errors threshold crossing alert";
                   type empty;
                 }
                 leaf no-enable-tca {
                   description "Don't enable the FEC Corrected Errors threshold crossing alert";
                   type empty;
                 }
               }
               leaf threshold {
                 description "FEC Corrected-Errs value in format: xe-n, x is an integer or decimal number, n = 0..9";
                 default "10e-3";
                 type string {
                 }
               }
               leaf threshold-24hrs {
                 description "FEC Corrected-Errs value in format: xe-n, x is an integer or decimal number, n = 0..9";
                 default "10e-3";
                 type string {
                 }
               }
             }
             container fec-ucorrected-words-high-tca {
               description "FEC UCorrected Words High Threshold crossing defect trigger";
               uses apply-advanced;
               choice enable-tca-choice {
                 leaf enable-tca {
                   description "Enable the FEC UCorrected Words threshold crossing alert";
                   type empty;
                 }
                 leaf no-enable-tca {
                   description "Don't enable the FEC UCorrected Words threshold crossing alert";
                   type empty;
                 }
               }
               leaf threshold {
                 description "FEC UCorrected-Words value in format: xe-n, x is an integer or decimal number, n = 0..9";
                 default "10e-3";
                 type string {
                 }
               }
               leaf threshold-24hrs {
                 description "FEC UCorrected-Words value in format: xe-n, x is an integer or decimal number, n = 0..9";
                 default "10e-3";
                 type string {
                 }
               }
             }
             container laser-frequency-error-high-tca {
               description "Laser frequency error high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute frequency error high TCA in MHz";
                 type string;
               }
               leaf threshold-24hrs {
                 description "Threshold for 24 hour frequency error high TCA in MHz";
                 type string;
               }
             }
             container laser-frequency-error-low-tca {
               description "Laser frequency error low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute frequency error low TCA in MHz";
                 type string;
               }
               leaf threshold-24hrs {
                 description "Threshold for 24 hour frequency error low TCA in MHz";
                 type string;
               }
             }
           }
           list warning {
             key name;
             ordered-by user;
             description "Set optic warnings";
             leaf name {
               type enumeration {
                 enum "low-light-warning" {
                   description "Enable low light warning";
                 }
               }
             }
             uses apply-advanced;
             choice actiontype {
               case case_1 {
                 leaf syslog {
                   description "Set action as syslog";
                   type empty;
                 }
               }
               case case_2 {
                 leaf link-down {
                   description "Set action as link-down";
                   type empty;
                 }
               }
             }
           }
         }
         container otn-options {
           description "Optical Transmission Network interface-specific options";
           uses otn_options_type;
         }
         container fastether-options {
           description "Fast Ethernet interface-specific options";
           uses apply-advanced;
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           leaf ingress-rate-limit {
             description "Ingress rate at port";
             units "megabits per second";
             type union {
               type string {
                 pattern "<.*>|$.*";
               }
               type uint32 {
                 range "1 .. 100";
               }
             }
           }
           list source-address-filter {
             key name;
             ordered-by user;
             description "Source address filters";
             leaf name {
               description "Remote MAC address";
               type jt:mac-addr;
             }
           }
           container ieee-802.3ad {
             description "IEEE 802.3ad";
             uses apply-advanced;
             container lacp {
               description "Link Aggregation Control Protocol configuration";
               uses apply-advanced;
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
           }
           container mpls {
             description "MPLS options";
             uses mpls_ifd_options;
           }
           leaf ignore-l3-incompletes {
             description "Ignore L3 incomplete errors";
             type empty;
           }
         }
         container aggregated-ether-options {
           description "Aggregated Ethernet interface-specific options";
           uses apply-advanced;
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           leaf autostate-exclude {
             description "Interface will not contribute to IRB state";
             type empty;
           }
           container link-protection {
             presence "enable link-protection";
             description "Enable link protection mode";
             uses apply-advanced;
             leaf revertive {
               description "Revert back from active backup link to primary, if primary is UP";
               type empty;
             }
             leaf non-revertive {
               description "Do not revert back (default mode) from active backup link to primary, if primary is UP";
               type empty;
             }
             leaf backup-state {
               description "Link protection backup link state";
               default "accept-data";
               type enumeration {
                 enum "accept-data" {
                   description "Accept data on receive channel of backup link";
                 }
                 enum "discard-data" {
                   description "Discard data on receive channel of backup link";
                 }
                 enum "down" {
                   description "Backup link is marked down";
                 }
               }
             }
             container rtg-config {
               presence "enable rtg-config";
               description "RTG enable on AE";
               uses apply-advanced;
               leaf preempt-cutover-timer {
                 description "RTG preempt-cutover-timer in seconds";
                 default "1";
                 type union {
                   type string {
                     pattern "<.*>|$.*";
                   }
                   type uint32 {
                     range "0 .. 255";
                   }
                 }
               }
             }
           }
           choice fcoe-lag-choice {
             leaf fcoe-lag {
               description "Enable FIP/FCoE LAG";
               type empty;
             }
             leaf no-fcoe-lag {
               description "Don't enable FIP/FCoE LAG";
               type empty;
             }
           }
           list source-address-filter {
             key name;
             ordered-by user;
             description "Source address filters";
             leaf name {
               description "Remote MAC address";
               type jt:mac-addr;
             }
           }
           container configured-flow-control {
             presence "enable configured-flow-control";
             description "Enable flow control";
             uses apply-advanced;
             leaf rx-buffers {
               description "Enable/Disable Rx buffers";
               type enumeration {
                 enum "on" {
                   description "Enable Rx buffers";
                 }
                 enum "off" {
                   description "Disable Rx buffers";
                 }
               }
             }
             leaf tx-buffers {
               description "Enable/Disable Tx buffers";
               type enumeration {
                 enum "on" {
                   description "Enable Tx buffers";
                 }
                 enum "off" {
                   description "Disable Tx buffers";
                 }
               }
             }
           }
           container load-balance {
             uses aggregate-load-balance;
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             leaf neighbor {
               description "BFD neighbor address";
               type jt:ipaddr;
             }
             leaf local-address {
               description "BFD local address";
               type jt:ipaddr;
             }
             leaf holddown-interval {
               description "Time to hold the session-UP notification to the client";
               units "milliseconds";
               type union {
                 type string {
                   pattern "<.*>|$.*";
                 }
                 type uint32 {
                   range "0 .. 255000";
                 }
               }
             }
           }
           leaf minimum-links {
             description "Minimum number of aggregated links";
             type union {
               type string {
                 pattern "<.*>|$.*";
               }
               type uint16;
             }
           }
           container minimum-bandwidth {
             presence "enable minimum-bandwidth";
             description "Minimum bandwidth configured for aggregated bundle";
             uses apply-advanced;
             leaf bw-value {
               description "Bandwidth value";
               default "1";
               type union {
                 type uint64;
                 type string {
                   pattern "<.*>|$.*";
                 }
               }
             }
             leaf bw-unit {
               description "Bandwidth unit";
               type enumeration {
                 enum "bps" {
                   description "Links are in bytes per sec";
                 }
                 enum "kbps" {
                   description "Links are in kilo bytes per sec";
                 }
                 enum "mbps" {
                   description "Links are in mega bytes per sec";
                 }
                 enum "gbps" {
                   description "Links are in giga bytes per sec ";
                 }
               }
             }
           }
           choice redundancy_choice {
             case case_1 {
             }
             case case_2 {
             }
           }
           container rebalance-periodic {
             uses apply-advanced;
           }
           leaf link-speed {
             description "Link speed of individual interface that joins the AE";
             type enumeration {
               enum "10m" {
                 description "Links are 10M";
               }
               enum "100m" {
                 description "Links are 100M";
               }
               enum "1g" {
                 description "Links are 1G";
               }
               enum "2.5g" {
                 description "Links are 2.5G";
               }
               enum "5g" {
                 description "Links are 5G";
               }
               enum "8g" {
                 description "Links are 8G";
               }
               enum "10g" {
                 description "Links are 10G";
               }
               enum "25g" {
                 description "Links are 25G";
               }
               enum "40g" {
                 description "Links are 40G";
               }
               enum "50g" {
                 description "Links are 50G";
               }
               enum "80g" {
                 description "Links are 80G";
               }
               enum "100g" {
                 description "Links are 100G";
               }
               enum "oc192" {
                 description "Links are OC-192";
               }
               enum "mixed" {
                 description "Links are various speeds";
               }
             }
           }
           container local-bias {
             presence "enable local-bias";
             description "Turn on local bias functionality";
             uses apply-advanced;
             leaf disable {
               description "Disable local-bias";
               type empty;
             }
           }
           leaf local-minimum-links-threshold {
             description "Specify threshold for minimum links per VC/VCF member";
             type union {
               type string {
                 pattern "<.*>|$.*";
               }
               type uint16 {
                 range "1 .. 100";
               }
             }
           }
           leaf resilient-hash {
             description "Turn on resilient-hash";
             type empty;
           }
           container lacp {
             description "Link Aggregation Control Protocol configuration";
             uses apply-advanced;
             choice mode {
               case case_1 {
                 leaf active {
                   description "Initiate transmission of LACP packets";
                   type empty;
                 }
               }
               case case_2 {
                 leaf passive {
                   description "Respond to LACP packets";
                   type empty;
                 }
               }
             }
             leaf periodic {
               description "Timer interval for periodic transmission of LACP packets";
               type enumeration {
                 enum "fast" {
                   description "Receive packets every second";
                 }
                 enum "slow" {
                   description "Receive packets every 30 seconds";
                 }
               }
             }
             container link-protection {
               presence "enable link-protection";
               uses apply-advanced;
               leaf disable {
                 description "To turn off LACP link-protection";
                 type empty;
               }
               choice mode {
                 case case_1 {
                   leaf revertive {
                     description "Switch links when better priority link comes up";
                     type empty;
                   }
                 }
                 case case_2 {
                   leaf non-revertive {
                     description "Do not switch links when better priority link comes up";
                     type empty;
                   }
                 }
               }
               container rtg-config {
                 presence "enable rtg-config";
                 description "RTG Feature enable on AE";
                 uses apply-advanced;
                 leaf preempt-cutover-timer {
                   description "RTG preempt-cutover-timer in seconds";
                   default "1";
                   type union {
                     type string {
                       pattern "<.*>|$.*";
                     }
                     type uint32 {
                       range "0 .. 255";
                     }
                   }
                 }
               }
             }
             leaf system-priority {
               description "Priority of the system (0 ... 65535)";
               type string;
             }
             leaf system-id {
               description "Node's System ID, encoded as a MAC address";
               type jt:mac-addr;
             }
             leaf admin-key {
               description "Node's administrative key";
               type union {
                 type uint16;
                 type string {
                   pattern "<.*>|$.*";
                 }
               }
             }
             container hold-time {
               description "Hold time for link up and link down for AE link members";
               leaf up {
                 description "Link up hold time for the AE link members";
                 units "seconds";
                 type union {
                   type string {
                     pattern "<.*>|$.*";
                   }
                   type uint16 {
                     range "1 .. 6000";
                   }
                 }
               }
             }
             leaf force-up {
               description "Forceup AE interface with LACP";
               type empty;
             }
           }
           list link-protection-sub-group {
             key name;
             ordered-by user;
             description "Link Protection subgroup configuration";
             leaf name {
               description "Name of the subgroup";
               type string {
                 length "2 .. 64";
               }
             }
             uses apply-advanced;
             choice type {
               case case_1 {
                 leaf primary {
                   description "Primary subgroup for N:N link-protection mode";
                   type empty;
                 }
               }
               case case_2 {
                 leaf backup {
                   description "Backup subgroup for N:N link-protection mode";
                   type empty;
                 }
               }
             }
           }
           container ethernet-switch-profile {
             description "Ethernet virtual LAN/media access control-level options";
             uses apply-advanced;
             leaf-list tag-protocol-id {
               description "IEEE 802.1q Tag Protocol Identifier values for VLAN-tagged frames";
               type string;
             }
             leaf mac-learn-enable {
               description "Learn MAC addresses dynamically";
               type empty;
             }
           }
           container mc-ae {
             description "Multi-chassis aggregation (MC-AE) network device configuration";
             uses apply-advanced;
             leaf mc-ae-id {
               description "MC-AE group id";
               type union {
                 type string {
                   pattern "<.*>|$.*";
                 }
                 type uint16 {
                   range "1 .. 65535";
                 }
               }
             }
             leaf redundancy-group {
               description "Redundancy group id";
               default "1";
               type union {
                 type string {
                   pattern "<.*>|$.*";
                 }
                 type uint32 {
                   range "1 .. 4294967294";
                 }
               }
             }
             leaf chassis-id {
               description "Chassis id of MC-AE network device";
               type union {
                 type string {
                   pattern "<.*>|$.*";
                 }
                 type uint16 {
                   range "0 .. 1";
                 }
               }
             }
             leaf mode {
               description "Mode of the MC-AE";
               type enumeration {
                 enum "active-active" {
                   description "MC-AE in active-active mode";
                 }
               }
             }
             leaf status-control {
               description "Status of the MC-AE chassis";
               type enumeration {
                 enum "active" {
                   description "Chassis is Active";
                 }
                 enum "standby" {
                   description "Chassis is Standby";
                 }
               }
             }
             leaf switchover-mode {
               description "Switchover mode";
               type enumeration {
                 enum "revertive" {
                   description "Switch mcae node when preferred link comes up";
                 }
                 enum "non-revertive" {
                   description "Do not switch mcae node when preferred link comes up";
                 }
               }
             }
             leaf revert-time {
               description "Wait interval before performing switchover";
               default "3";
               units "minute";
               type union {
                 type string {
                   pattern "<.*>|$.*";
                 }
                 type uint32 {
                   range "1 .. 10";
                 }
               }
             }
             leaf init-delay-time {
               description "Init delay timer for mcae sm for min traffic loss";
               units "seconds";
               type union {
                 type string {
                   pattern "<.*>|$.*";
                 }
                 type uint16 {
                   range "1 .. 6000";
                 }
               }
             }
             leaf recovery-delay-time {
               description "Delay timer for bringing up ICL, ICCP";
               units "seconds";
               type union {
                 type string {
                   pattern "<.*>|$.*";
                 }
                 type uint16 {
                   range "1 .. 6000";
                 }
               }
             }
             leaf enhanced-convergence {
               description "Optimized convergence time for mcae";
               type empty;
             }
             container events {
               presence "enable events";
               description "MCAE related events";
               uses apply-advanced;
               container iccp-peer-down {
                 presence "enable iccp-peer-down";
                 description "Define behavior in the event of ICCP peer down";
                 uses apply-advanced;
                 leaf force-icl-down {
                   description "Bring down ICL logical interface";
                   type empty;
                 }
                 leaf prefer-status-control-active {
                   description "Keep this node up (recommended only on status-control active)";
                   type empty;
                 }
               }
             }
           }
         }
         container es-options {
           description "ES PIC interface-specific options";
           uses apply-advanced;
           leaf backup-interface {
             description "Name of backup interface";
             type union {
               type jt:interface-device;
               type string {
                 pattern "<.*>|$.*";
               }
             }
           }
         }
         container vdsl-options {
           description "VDSL interface-specific options";
           uses apply-advanced;
           leaf vdsl-profile {
             description "VDSL profile";
             type enumeration {
               enum "auto" {
                 description "Auto";
               }
               enum "8a" {
                 description "Profile 8a";
               }
               enum "8b" {
                 description "Profile 8b";
               }
               enum "8c" {
                 description "Profile 8c";
               }
               enum "8d" {
                 description "Profile 8d";
               }
               enum "12a" {
                 description "Profile 12a";
               }
               enum "12b" {
                 description "Profile 12b";
               }
               enum "17a" {
                 description "Profile 17a";
               }
             }
           }
           leaf sra {
             description "DSL SRA";
             default "disable";
             type enumeration {
               enum "enable" {
                 description "Enable SRA";
               }
               enum "disable" {
                 description "Disable SRA";
               }
             }
           }
           leaf v43 {
             description "DSL V43 tones";
             default "enable";
             type enumeration {
               enum "enable" {
                 description "Enable V43";
               }
               enum "disable" {
                 description "Disable V43";
               }
             }
           }
         }
         container shdsl-options {
           description "SHDSL interface-specific options";
           uses apply-advanced;
           leaf annex {
             description "Type of SHDSL annex";
             default "annex-b";
             type enumeration {
               enum "annex-a" {
                 description "Annex-a PIC";
               }
               enum "annex-b" {
                 description "Annex-b PIC";
               }
               enum "annex-f" {
                 description "Annex-f PIC";
               }
               enum "annex-g" {
                 description "Annex-g PIC";
               }
               enum "annex-auto" {
                 description "Annex-auto PIC";
               }
             }
           }
           leaf line-rate {
             description "SHDSL line rate";
             type string;
           }
           leaf loopback {
             description "Loopback mode";
             type enumeration {
               enum "local" {
                 description "Local loopback";
               }
               enum "remote" {
                 description "Remote loopback";
               }
             }
           }
           container snr-margin {
             presence "enable snr-margin";
             description "Signal to noise ratio margin";
             uses apply-advanced;
             leaf current {
               description "Current signal to noise ratio margin";
               units "dB";
               type string;
             }
             leaf snext {
               description "SNEXT signal to noise ratio margin";
               units "dB";
               type string;
             }
           }
         }
         container container-options {
           description "Container interface specific options";
           uses apply-advanced;
           container container-type {
             presence "enable container-type";
             description "Protocol type of the container interface";
             uses apply-advanced;
             choice container-type-choice {
               case case_1 {
                 container aps {
                   description "APS options on the container";
                   uses aps_type;
                 }
               }
             }
           }
           container member-interface-type {
             description "Link type of members of container";
             uses apply-advanced;
             choice member_interface_type_choice {
               case case_1 {
                 container sonet {
                   uses apply-advanced;
                   leaf member-interface-speed {
                     description "Link speed of members of container";
                     type enumeration {
                       enum "oc3" {
                         description "Links are OC-3";
                       }
                       enum "oc12" {
                         description "Links are OC-12";
                       }
                       enum "oc48" {
                         description "Links are OC-48";
                       }
                       enum "oc192" {
                         description "Links are OC-192";
                       }
                       enum "oc768" {
                         description "Links are OC-768";
                       }
                       enum "mixed" {
                         description "Links are of different speeds";
                       }
                     }
                   }
                 }
               }
               case case_2 {
                 container atm {
                   uses apply-advanced;
                   leaf member-interface-speed {
                     description "Link speed of members of container";
                     type enumeration {
                       enum "oc3" {
                         description "Links are OC-3";
                       }
                       enum "oc12" {
                         description "Links are OC-12";
                       }
                       enum "oc48" {
                         description "Links are OC-48";
                       }
                     }
                   }
                 }
               }
               case case_3 {
                 container channelized-sonet {
                   uses apply-advanced;
                   leaf member-interface-speed {
                     description "Link speed of members of container";
                     type enumeration {
                       enum "coc3" {
                         description "Links are COC-3";
                       }
                       enum "coc12" {
                         description "Links are COC-12";
                       }
                       enum "coc48" {
                         description "Links are COC-48";
                       }
                       enum "coc192" {
                         description "Links are COC-192";
                       }
                       enum "coc768" {
                         description "Links are COC-768";
                       }
                     }
                   }
                 }
               }
               case case_4 {
                 container channelized-sdh {
                   uses apply-advanced;
                   leaf member-interface-speed {
                     description "Link speed of members of container";
                     type enumeration {
                       enum "cstm1" {
                         description "Links are cstm-1";
                       }
                       enum "cstm4" {
                         description "Links are cstm-4";
                       }
                       enum "cstm16" {
                         description "Links are cstm-16";
                       }
                       enum "coc64" {
                         description "Links are cstm-64";
                       }
                       enum "cstm256" {
                         description "Links are cstm256";
                       }
                     }
                   }
                 }
               }
             }
           }
           container redundancy {
             description "Container interface redundancy options";
             uses apply-advanced;
             container hold-time {
               description "Hold time for link up and link down";
               leaf up {
                 description "Link up hold time";
                 units "milliseconds";
                 type union {
                   type string {
                     pattern "<.*>|$.*";
                   }
                   type uint32 {
                     range "0 .. 65534";
                   }
                 }
               }
               leaf down {
                 description "Link down hold time";
                 units "milliseconds";
                 type union {
                   type string {
                     pattern "<.*>|$.*";
                   }
                   type uint32 {
                     range "0 .. 65534";
                   }
                 }
               }
             }
           }
           leaf-list container-list {
             description "List of container interfaces this member link is associated to";
             type union {
               type jt:interface-device;
               type string {
                 pattern "<.*>|$.*";
               }
             }
           }
           choice redundancy-type {
             case case_1 {
               choice aps-redundancy {
                 case case_1 {
                   leaf primary {
                     description "This member link is primary interface of the container";
                     type empty;
                   }
                 }
                 case case_2 {
                   leaf standby {
                     description "This member link is standby interface of the container";
                     type empty;
                   }
                 }
               }
             }
           }
           leaf fast-aps {
             description "Fast APS switch";
             type empty;
           }
           leaf allow-configuration-override {
             description "Allow physical configuration of member link to override container configuration";
             type empty;
           }
         }
         list unit {
           key name;
           description "Logical interface";
           leaf name {
             type string;
           }
           uses apply-advanced;
           leaf alias {
             description "Interface alias";
             type string;
           }
           leaf enhanced-convergence {
             description "Optimize convergence time for L3";
             type empty;
           }
           leaf proxy-macip-advertisement {
             description "Proxy advertisement of type 2 MAC+IP route for EVPN";
             type empty;
           }
           leaf virtual-gateway-accept-data {
             description "Accept packets destined for virtual gateway address";
             type empty;
           }
           container peer-psd {
             presence "enable peer-psd";
             description "Peer psd";
             leaf psd-name {
               description "Peer psd name";
               type string;
             }
           }
           container peer-interface {
             presence "enable peer-interface";
             description "Peer interface";
             uses apply-advanced;
             leaf interface-name {
               description "Peer interface name";
               type union {
                 type jt:interface-unit;
                 type string {
                   pattern "<.*>|$.*";
                 }
               }
             }
           }
           container interface-shared-with {
             presence "enable interface-shared-with";
             description "Specify which PSD owns this logical interface";
             uses apply-advanced;
             leaf psd-name {
               description "Name of protected system domain (psd[1-31], ex. psd2)";
               type string {
               }
             }
           }
           choice enable-disable {
             case case_1 {
               leaf disable {
                 description "Disable this logical interface";
                 type empty;
               }
             }
           }
           leaf passive-monitor-mode {
             description "Use interface to tap packets from another router";
             type empty;
           }
           leaf clear-dont-fragment-bit {
             description "Clear DF bit in packet (AS PIC and J-series only as well as MIF)";
             type empty;
           }
           leaf description {
             description "Text description of interface";
             type string;
           }
           leaf metadata {
             description "Text metadata attached to interface";
             type string;
           }
           leaf encapsulation {
             description "Logical link-layer encapsulation";
             type enumeration {
               enum "atm-nlpid" {
                 description "ATM NLPID encapsulation";
               }
               enum "atm-cisco-nlpid" {
                 description "Cisco-compatible ATM NLPID encapsulation";
               }
               enum "atm-snap" {
                 description "ATM LLC/SNAP encapsulation";
               }
               enum "atm-vc-mux" {
                 description "ATM VC multiplexing";
               }
               enum "atm-ccc-vc-mux" {
                 description "ATM VC for CCC";
               }
               enum "atm-tcc-vc-mux" {
                 description "ATM VC for translational cross-connect";
               }
               enum "atm-tcc-snap" {
                 description "ATM LLC/SNAP for translational cross-connect";
               }
               enum "atm-ccc-cell-relay" {
                 description "ATM cell relay for CCC";
               }
               enum "vlan-vci-ccc" {
                 description "CCC for VLAN Q-in-Q and ATM VPI/VCI interworking";
               }
               enum "ether-over-atm-llc" {
                 description "Ethernet over ATM (LLC/SNAP) encapsulation";
               }
               enum "ether-vpls-over-atm-llc" {
                 description "Ethernet VPLS over ATM (bridging) encapsulation";
               }
               enum "ppp-over-ether-over-atm-llc" {
                 description "PPPoE over ATM (LLC/SNAP) encapsulation";
               }
               enum "ppp-over-ether" {
                 description "PPPoE encapsulation";
               }
               enum "atm-ppp-vc-mux" {
                 description "ATM PPP over raw AAL5";
               }
               enum "atm-ppp-llc" {
                 description "ATM PPP over AAL5/LLC";
               }
               enum "atm-mlppp-llc" {
                 description "ATM MLPPP over AAL5/LLC";
               }
               enum "frame-relay-ppp" {
                 description "PPP over Frame Relay";
               }
               enum "frame-relay-ccc" {
                 description "Frame Relay DLCI for CCC";
               }
               enum "frame-relay" {
                 description "Frame Relay DLCI";
               }
               enum "frame-relay-tcc" {
                 description "Frame Relay DLCI for translational cross-connect";
               }
               enum "frame-relay-ether-type" {
                 description "Cisco-compatible Frame Relay Encapsulation DLCI";
               }
               enum "frame-relay-ether-type-tcc" {
                 description "Cisco-compatible Frame Relay Encapsulation DLCI for TCC";
               }
               enum "ether-vpls-fr" {
                 description "Ethernet VPLS over Frame Relay (bridging) encapsulation";
               }
               enum "vlan-ccc" {
                 description "802.1q tagging for a cross-connect";
               }
               enum "ethernet-ccc" {
                 description "Ethernet for a cross-connect";
               }
               enum "vlan-vpls" {
                 description "VLAN virtual private LAN service";
               }
               enum "vlan-bridge" {
                 description "VLAN layer-2 bridging";
               }
               enum "dix" {
                 description "Ethernet DIXv2 (RFC 894)";
               }
               enum "ethernet" {
                 description "Ethernet II (RFC 894)";
               }
               enum "ethernet-vpls" {
                 description "Ethernet II virtual private LAN service";
               }
               enum "ethernet-bridge" {
                 description "Ethernet II bridging";
               }
               enum "vlan" {
                 description "802.1q-tagged Ethernet";
               }
               enum "vlan-tcc" {
                 description "802.1q tagging for a translational cross-connect";
               }
               enum "multilink-ppp" {
                 description "Multilink PPP";
               }
               enum "multilink-frame-relay-end-to-end" {
                 description "Multilink Frame Relay end-to-end (FRF.15)";
               }
               enum "ppp-ccc" {
                 description "Serial PPP device for a cross-connect";
               }
             }
           }
           leaf mtu {
             description "Maximum transmission unit packet size";
             type union {
               type string {
                 pattern "<.*>|$.*";
               }
               type uint32;
             }
           }
           choice pointedness {
             case case_1 {
               leaf point-to-point {
                 description "Point-to-point connection";
                 type empty;
               }
             }
             case case_2 {
               leaf multipoint {
                 description "Multipoint connection";
                 type empty;
               }
             }
           }
           leaf bandwidth {
             description "Logical unit bandwidth (informational only)";
             type string;
           }
           leaf global-layer2-domainid {
             description "Global Layer-2 Identifier for this interface";
             type union {
               type string {
                 pattern "<.*>|$.*";
               }
               type uint32 {
                 range "5 .. 4094";
               }
             }
           }
           choice traps-choice {
             leaf traps {
               description "Enable SNMP notifications on state changes";
               type empty;
             }
             leaf no-traps {
               description "Don't enable SNMP notifications on state changes";
               type empty;
             }
           }
           choice routing-services-choice {
             leaf routing-services {
               description "Enable routing services";
               type empty;
             }
             leaf no-routing-services {
               description "Don't enable routing services";
               type empty;
             }
           }
           container arp-resp {
             presence "enable arp-resp";
             description "Knob to control ARP response on the interface, default is restricted";
             choice arp-response-options {
               case case_1 {
                 leaf unrestricted {
                   description "Enable unrestricted ARP respone on the interface";
                   type empty;
                 }
               }
               case case_2 {
                 leaf restricted {
                   description "Enable restricted proxy ARP response on the interface";
                   type empty;
                 }
               }
             }
           }
           container proxy-arp {
             presence "enable proxy-arp";
             description "Enable proxy ARP on the interface, default is unrestricted";
             choice proxyarp-options {
               case case_1 {
                 leaf unrestricted {
                   description "Enable unrestricted proxy ARP on the interface";
                   type empty;
                 }
               }
               case case_2 {
                 leaf restricted {
                   description "Enable restricted proxy ARP on the interface";
                   type empty;
                 }
               }
             }
           }
           choice vlan_choice {
             case case_1 {
               leaf vlan-id {
                 description "Virtual LAN identifier value for 802.1q VLAN tags";
                 type string;
               }
             }
             case case_2 {
               leaf vlan-id-range {
                 description "Virtual LAN identifier range of form vid1-vid2";
                 type string {
                 }
               }
             }
             case case_3 {
               leaf-list inner-vlan-id-swap-ranges {
                 description "Inner vlan-id swap range(s) of form vid1-vid2 for dynamic L2 VLANs";
                 type jt:vlan-range;
               }
             }
             case case_4 {
               leaf-list vlan-id-list {
                 description "List of VLAN identifiers";
                 type jt:vlan-range;
               }
             }
             case case_5 {
               leaf-list vlan-tag {
                 description "IEEE 802.1q tag list for VLAN tagged frames";
                 status deprecated;
                 type string;
               }
             }
             case case_6 {
               container vlan-tags {
                 presence "enable vlan-tags";
                 description "IEEE 802.1q tags";
                 leaf outer {
                   description "[tpid.]vlan-id, tpid format is 0xNNNN and is optional";
                   type string;
                 }
                 choice inner_choice {
                   case case_1 {
                     leaf inner {
                       description "[tpid.]vlan-id, tpid format is 0xNNNN and is optional";
                       type string;
                     }
                   }
                   case case_2 {
                     leaf inner-range {
                       description "[tpid.]vid1-vid2, tpid format is 0xNNNN and is optional";
                       type string {
                       }
                     }
                   }
                   case case_3 {
                     leaf-list inner-list {
                       description "List of VLAN identifiers";
                       type jt:vlan-range;
                     }
                   }
                 }
               }
             }
           }
           leaf native-inner-vlan-id {
             description "Native virtual LAN identifier for singly tagged frames";
             type union {
               type string {
                 pattern "<.*>|$.*";
               }
               type uint32 {
                 range "0 .. 4094";
               }
             }
           }
           container accept-source-mac {
             description "Remote media access control address to/from which to accept traffic";
             uses apply-advanced;
             list mac-address {
               key name;
               description "Remote MAC address";
               uses mac_list;
             }
           }
           container input-vlan-map {
             description "VLAN map operation on input";
             uses vlan_map;
           }
           container output-vlan-map {
             description "VLAN map operation on output";
             uses vlan_map;
           }
           leaf swap-by-poppush {
             description "Pop original vlan tag and then push a new vlan tag";
             type empty;
           }
           leaf receive-lsp {
             description "Name of incoming label-switched path";
             type string;
           }
           leaf transmit-lsp {
             description "Name of outgoing label-switched path";
             type string;
           }
           leaf dlci {
             description "Frame Relay data-link control identifier";
             type union {
               type string {
                 pattern "<.*>|$.*";
               }
               type uint32 {
                 range "1 .. 1022";
               }
             }
           }
           leaf multicast-dlci {
             description "Frame Relay data-link control identifier for multicast packets";
             type union {
               type string {
                 pattern "<.*>|$.*";
               }
               type uint32 {
                 range "1 .. 1022";
               }
             }
           }
           choice vci_type {
             case case_1 {
               leaf vci {
                 description "ATM point-to-point virtual circuit identifier ([vpi.]vci)";
                 type jt:atm-vci;
               }
             }
             case case_2 {
               leaf allow-any-vci {
                 description "Allow all VCIs to open in atm-ccc-cell-relay mode";
                 type empty;
               }
             }
             case case_3 {
               leaf vpi {
                 description "ATM point-to-point virtual path identifier (vpi)";
                 type union {
                   type string {
                     pattern "<.*>|$.*";
                   }
                   type uint32 {
                     range "0 .. 255";
                   }
                 }
               }
             }
             case case_4 {
               leaf trunk-id {
                 description "ATM trunk identifier";
                 type union {
                   type string {
                     pattern "<.*>|$.*";
                   }
                   type uint32 {
                     range "0 .. 31";
                   }
                 }
               }
             }
           }
           choice psn_vci_type {
             case case_1 {
             }
             case case_2 {
             }
           }
           container atm-l2circuit-mode {
             description "Select ATM Layer 2 circuit transport mode";
             choice mode_choice {
               case case_1 {
                 leaf cell {
                   description "ATM Layer 2 circuit cell mode";
                   type empty;
                 }
               }
               case case_2 {
                 leaf aal5 {
                   description "ATM Layer 2 circuit AAL5 mode";
                   type empty;
                 }
               }
             }
           }
           container vci-range {
             description "ATM VCI range start <start-vci> end <end-vci>";
             leaf start {
               description "ATM VCI range's start value";
               type union {
                 type string {
                   pattern "<.*>|$.*";
                 }
                 type uint16 {
                   range "32 .. 4094";
                 }
               }
             }
             leaf end {
               description "ATM VCI range's end value";
               type union {
                 type string {
                   pattern "<.*>|$.*";
                 }
                 type uint16 {
                   range "32 .. 4094";
                 }
               }
             }
           }
           leaf trunk-bandwidth {
             description "ATM trunk bandwidth";
             units "bits per second";
             type string;
           }
           leaf multicast-vci {
             description "ATM virtual circuit identifier for multicast packets";
             type jt:atm-vci;
           }
           container shaping {
             description "Virtual circuit traffic-shaping options";
             uses dcd_shaping_config;
           }
           container oam-period {
             description "OAM cell period";
             choice oam_period_choices {
               case case_1 {
                 leaf oam-period {
                   description "OAM cell period";
                   units "seconds";
                   type union {
                     type string {
                       pattern "<.*>|$.*";
                     }
                     type uint32 {
                       range "1 .. 900";
                     }
                   }
                 }
               }
               case case_2 {
                 container disable {
                   presence "enable disable";
                   description "Disable F5 OAM loopback";
                 }
               }
             }
           }
           container oam-liveness {
             description "OAM virtual circuit liveness parameters";
             uses apply-advanced;
             leaf up-count {
               description "Number of OAM cells to consider VC up";
               type union {
                 type string {
                   pattern "<.*>|$.*";
                 }
                 type uint32 {
                   range "1 .. 255";
                 }
               }
             }
             leaf down-count {
               description "Number of OAM cells to consider VC down";
               type union {
                 type string {
                   pattern "<.*>|$.*";
                 }
                 type uint32 {
                   range "1 .. 255";
                 }
               }
             }
           }
           container ppp-options {
             description "Point-to-Point Protocol interface-specific options";
             uses ppp_options_type;
           }
           choice keepalive_choices {
             case case_1 {
               container keepalives {
                 description "Send or demand keepalive messages";
                 uses keepalives_type;
               }
             }
             case case_2 {
               leaf no-keepalives {
                 description "Do not send or demand keepalive messages";
                 type empty;
               }
             }
           }
           leaf inverse-arp {
             description "Enable inverse ARP";
             type empty;
           }
           leaf transmit-weight {
             description "ATM2 transmit weight for VC under VP tunnel";
             type union {
               type string {
                 pattern "<.*>|$.*";
               }
               type uint16 {
                 range "1 .. 32767";
               }
             }
           }
           container epd-threshold {
             description "Early packet discard threshold for ATM2";
             uses epd_threshold_config;
           }
           leaf cell-bundle-size {
             description "L2 circuit cell bundle size";
             units "cells";
             type union {
               type string {
                 pattern "<.*>|$.*";
               }
               type uint32 {
                 range "1 .. 176";
               }
             }
           }
           leaf cell-bundle-timeout {
             description "L2 circuit cell bundle timeout";
             units "microseconds";
             type union {
               type string {
                 pattern "<.*>|$.*";
               }
               type uint32 {
                 range "1 .. 512";
               }
             }
           }
           leaf plp-to-clp {
             description "Enable ATM2 PLP to CLP copy";
             type empty;
           }
           leaf atm-scheduler-map {
             description "Assign ATM2 CoS scheduling map";
             type union {
               type string {
                 pattern "default";
               }
               type string;
             }
           }
           leaf mrru {
             description "Maximum received reconstructed unit";
             units "bytes";
             type union {
               type string {
                 pattern "<.*>|$.*";
               }
               type uint16 {
                 range "1500 .. 4500";
               }
             }
           }
           leaf short-sequence {
             description "Short sequence number header format (MLPPP only)";
             type empty;
           }
           leaf fragment-threshold {
             description "Fragmentation threshold";
             units "bytes";
             type union {
               type string {
                 pattern "<.*>|$.*";
               }
               type uint32 {
                 range "64 .. 4500";
               }
             }
           }
           leaf drop-timeout {
             description "Drop timeout";
             units "milliseconds";
             type union {
               type string {
                 pattern "<.*>|$.*";
               }
               type uint16 {
                 range "0 .. 2000";
               }
             }
           }
           leaf disable-mlppp-inner-ppp-pfc {
             description "Disable compression for inner PPP header in MLPPP payload";
             type empty;
           }
           leaf minimum-links {
             description "Minimum number of links to sustain the bundle";
             type union {
               type string {
                 pattern "<.*>|$.*";
               }
               type uint16;
             }
           }
           leaf multilink-max-classes {
             description "Number of multilink classes";
             type union {
               type string {
                 pattern "<.*>|$.*";
               }
               type uint16;
             }
           }
           leaf interleave-fragments {
             description "Interleave long packets with high priority ones";
             type empty;
           }
           leaf link-layer-overhead {
             description "Link layer bit stuffing overhead (0.0 .. 50.0 percent)";
             type jt:unsigned-float;
           }
           leaf accounting-profile {
             description "Accounting profile name";
             type string;
           }
           leaf peer-unit {
             description "Peer unit number";
             type union {
               type string {
                 pattern "<.*>|$.*";
               }
               type uint32 {
                 range "0 .. 16385";
               }
             }
           }
           container tunnel {
             description "Tunnel parameters";
             uses apply-advanced;
             leaf source {
               description "Tunnel source";
               type jt:ipaddr;
             }
             leaf destination {
               description "Tunnel destination";
               type jt:ipaddr;
             }
             leaf key {
               description "Tunnel key";
               type union {
                 type string {
                   pattern "<.*>|$.*";
                 }
                 type uint32 {
                   range "0 .. 4294967295";
                 }
               }
             }
             leaf backup-destination {
               description "Backup tunnel destination";
               type jt:ipaddr;
             }
             choice fragmentation {
               case case_1 {
                 leaf allow-fragmentation {
                   description "Do not set DF bit on packets";
                   type empty;
                 }
               }
               case case_2 {
                 leaf do-not-fragment {
                   description "Set DF bit on packets";
                   type empty;
                 }
               }
             }
             leaf ttl {
               description "Time to live";
               type union {
                 type string {
                   pattern "<.*>|$.*";
                 }
                 type uint32 {
                   range "1 .. 255";
                 }
               }
             }
             leaf traffic-class {
               description "TOS/Traffic class field of IP-header";
               type union {
                 type string {
                   pattern "<.*>|$.*";
                 }
                 type uint32 {
                   range "0 .. 255";
                 }
               }
             }
             leaf flow-label {
               description "Flow label field of IP6-header";
               type union {
                 type string {
                   pattern "<.*>|$.*";
                 }
                 type uint32 {
                   range "0 .. 1048575";
                 }
               }
             }
             choice path-mtu-discovery-choice {
               leaf path-mtu-discovery {
                 description "Enable path MTU discovery for tunnels";
                 type empty;
               }
               leaf no-path-mtu-discovery {
                 description "Don't enable path MTU discovery for tunnels";
                 type empty;
               }
             }
             container routing-instance {
               description "Routing instance to which tunnel ends belong";
               uses apply-advanced;
               leaf destination {
                 description "Routing instance of tunnel destination";
                 type string;
               }
             }
           }
           leaf compression-device {
             description "Logical interface used for compression";
             type union {
               type jt:interface-unit;
               type string {
                 pattern "<.*>|$.*";
               }
             }
           }
           container layer2-policer {
             description "Layer2 policing for logical interface";
             uses apply-advanced;
             choice layer2-input-policer-choice {
               case case_1 {
                 leaf input-policer {
                   description "Two-color policer for received packets";
                   type string;
                 }
               }
               case case_2 {
               }
               case case_3 {
                 leaf input-three-color {
                   description "Color-blind three-color policer for received packets";
                   type string;
                 }
               }
             }
             choice layer2-output-policer-choice {
               case case_1 {
                 leaf output-policer {
                   description "Two-color policer for transmitted packets";
                   type string;
                 }
               }
               case case_2 {
                 leaf output-three-color {
                   description "Three-color policer for transmitted packets";
                   type string;
                 }
               }
             }
           }
           container service {
             description "Service operations";
             uses apply-advanced;
             list pcef {
               key name;
               ordered-by user;
               description "PCEF configuration";
               leaf name {
                 description "PCEF Profile name";
                 type string;
               }
               uses apply-advanced;
               leaf activate-all {
                 description "Activate all rules and rulebases in the pcef profile";
                 type empty;
               }
               list activate {
                 key name;
                 ordered-by user;
                 description "Name of pcef profile rule or rulebase to activate";
                 leaf name {
                   description "Name of pcef profile rule or rulebase to activate";
                   type string;
                 }
                 uses apply-advanced;
               }
             }
           }
           container family {
             description "Protocol family";
             container inet {
               presence "enable inet";
               description "IPv4 parameters";
               uses apply-advanced;
               container dhcp {
                 presence "enable dhcp";
                 description "Configure DHCP Client";
                 uses apply-advanced;
                 container client-identifier {
                   description "DHCP Server identifies a client by client-identifier value ";
                   choice client-identifier-choice {
                     case case_1 {
                       leaf ascii {
                         description "Client identifier as an ASCII string";
                         type string;
                       }
                     }
                     case case_2 {
                       leaf hexadecimal {
                         description "Client identifier as a hexadecimal string";
                         type string {
                         }
                       }
                     }
                   }
                 }
                 leaf lease-time {
                   description "Default lease time requested in ";
                   units "seconds";
                   type string;
                 }
                 leaf retransmission-attempt {
                   description "Number of attempts to retransmit the DHCP client protocol packet";
                   default "4";
                   type union {
                     type string {
                       pattern "<.*>|$.*";
                     }
                     type uint32 {
                       range "0 .. 6";
                     }
                   }
                 }
                 leaf retransmission-interval {
                   description "Number of seconds between successive retransmission";
                   default "4";
                   units "seconds";
                   type union {
                     type string {
                       pattern "<.*>|$.*";
                     }
                     type uint32 {
                       range "4 .. 64";
                     }
                   }
                 }
                 leaf server-address {
                   description "DHCP Server-address";
                   type jt:ipv4addr;
                 }
                 leaf update-server {
                   description "Propagate TCP/IP settings to DHCP server ";
                   type empty;
                 }
                 leaf vendor-id {
                   description "Vendor class id for the DHCP Client";
                   type string;
                 }
               }
               container targeted-broadcast {
                 presence "enable targeted-broadcast";
                 description "Directed broadcast";
                 uses apply-advanced;
                 choice targeted-bcast-choice {
                   case case_1 {
                     leaf forward-and-send-to-re {
                       description "Allow packets to be forwarded and sent to re";
                       type empty;
                     }
                   }
                   case case_2 {
                     leaf forward-only {
                       description "Allow packets only to be forwarded";
                       type empty;
                     }
                   }
                 }
               }
               leaf destination-class-usage {
                 description "Enable destination class usage on this interface";
                 status deprecated;
                 type empty;
               }
               leaf transit-options-packets {
                 description "Transit IP options packets (don't send to Routing Engine)";
                 status deprecated;
                 type empty;
               }
               leaf transit-ttl-exceeded {
                 description "Transit IP TTL-exceeded packets (don't send to Routing Engine)";
                 status deprecated;
                 type empty;
               }
               leaf receive-options-packets {
                 description "Receive IP options packets (don't send to Routing Engine)";
                 type empty;
               }
               leaf receive-ttl-exceeded {
                 description "Receive IP TTL-exceeded packets (don't send to Routing Engine)";
                 type empty;
               }
               container accounting {
                 description "Configure interface-based accounting options";
                 uses apply-advanced;
                 container source-class-usage {
                   description "Enable source class usage on this interface";
                   uses apply-advanced;
                   leaf input {
                     description "Specify this interface for source-class-usage input";
                     type empty;
                   }
                   leaf output {
                     description "Specify this interface for source-class-usage output";
                     type empty;
                   }
                 }
                 leaf destination-class-usage {
                   description "Enable destination class usage on this interface";
                   type empty;
                 }
               }
               container rpf-check {
                 presence "enable rpf-check";
                 description "Enable reverse-path-forwarding checks on this interface";
                 uses apply-advanced;
                 leaf fail-filter {
                   description "Name of filter applied to packets failing RPF check";
                   type string;
                 }
                 container mode {
                   description "Mode for reverse path forwarding";
                   leaf loose {
                     description "Reverse-path-forwarding loose mode";
                     type empty;
                   }
                 }
               }
               leaf mtu {
                 description "Protocol family maximum transmission unit";
                 type union {
                   type uint32;
                   type string {
                     pattern "<.*>|$.*";
                   }
                 }
               }
               leaf arp-max-cache {
                 description "Max interface ARP nexthop cache size";
                 type union {
                   type string {
                     pattern "<.*>|$.*";
                   }
                   type uint32 {
                     range "1 .. 2000000";
                   }
                 }
               }
               leaf arp-new-hold-limit {
                 description "Max no. of new unresolved nexthops";
                 type union {
                   type string {
                     pattern "<.*>|$.*";
                   }
                   type uint32 {
                     range "1 .. 2000000";
                   }
                 }
               }
               leaf no-redirects {
                 description "Do not redirect traffic";
                 type empty;
               }
               leaf no-neighbor-learn {
                 description "Disable neighbor address learning on interface";
                 type empty;
               }
               leaf unconditional-src-learn {
                 description "Glean from arp packets even when source cannot be validated";
                 type empty;
               }
               leaf multicast-only {
                 description "Allow only multicast traffic (tunnels only)";
                 type empty;
               }
               leaf primary {
                 description "Candidate for primary interface in system";
                 type empty;
               }
               leaf ipsec-sa {
                 description "Name of security association";
                 type string {
                   length "1 .. 32";
                 }
               }
               container filter {
                 description "Packet filtering";
                 uses apply-advanced;
                 choice input_choice {
                   case case_1 {
                     container input {
                       description "Filter to be applied to received packets";
                       leaf filter-name {
                         description "Name of the filter";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       description "List of filter modules applied to received packets ";
                       type string;
                     }
                   }
                 }
                 choice output_choice {
                   case case_1 {
                     container output {
                       description "Filter to be applied to transmitted packets";
                       leaf filter-name {
                         description "Name of the filter";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32 {
                       range "1 .. 255";
                     }
                   }
                 }
               }
               container simple-filter {
                 description "Filter for doing multifield classification";
                 uses apply-advanced;
                 leaf input {
                   description "Name of simple filter applied to received packets";
                   type string;
                 }
               }
               container policer {
                 description "Interface policing";
                 uses apply-advanced;
                 leaf arp {
                   description "Name of policer applied to received ARP packets";
                   type string;
                 }
                 leaf input {
                   description "Name of policer applied to received packets";
                   type string;
                 }
                 leaf output {
                   description "Name of policer applied to transmitted packets";
                   type string;
                 }
               }
               container sampling {
                 description "Interface sampling";
                 uses apply-advanced;
                 leaf input {
                   description "Sample all packets input on this interface";
                   type empty;
                 }
                 leaf output {
                   description "Sample all packets output on this interface";
                   type empty;
                 }
               }
               list next-hop-tunnel {
                 key name;
                 ordered-by user;
                 description "One or more next-hop tunnel tables";
                 leaf name {
                   description "Next-hop tunnel gateway address";
                   type string;
                 }
                 uses apply-advanced;
                 leaf ipsec-vpn {
                   description "Name of IPSec VPN";
                   type string;
                 }
               }
               list address {
                 key name;
                 ordered-by user;
                 description "Interface address/destination prefix";
                 leaf name {
                   description "Interface address/destination prefix";
                   type jt:ipv4prefix;
                 }
                 uses apply-advanced;
                 leaf destination {
                   description "Destination address";
                   type jt:ipv4addr;
                 }
                 leaf destination-profile {
                   description "Profile to use for destination address";
                   type string;
                 }
                 leaf broadcast {
                   description "Broadcast address";
                   type jt:ipv4addr;
                 }
                 leaf primary {
                   description "Candidate for primary address in system";
                   type empty;
                 }
                 leaf preferred {
                   description "Preferred address on interface";
                   type empty;
                 }
                 leaf master-only {
                   description "Master management IP address for router";
                   type empty;
                 }
                 list multipoint-destination {
                   key name;
                   ordered-by user;
                   description "Multipoint NBMA destination";
                   leaf name {
                     description "Destination address";
                     type jt:ipv4addr;
                   }
                   uses apply-advanced;
                   choice link-address {
                     case case_1 {
                       leaf dlci {
                         description "Frame Relay data-link control identifier";
                         type union {
                           type string {
                             pattern "<.*>|$.*";
                           }
                           type uint32 {
                             range "1 .. 1022";
                           }
                         }
                       }
                     }
                     case case_2 {
                       leaf vci {
                         description "ATM virtual circuit identifier ([vpi.]vci)";
                         type jt:atm-vci;
                       }
                     }
                   }
                   container shaping {
                     description "Virtual circuit traffic-shaping options";
                     uses dcd_shaping_config;
                   }
                   container oam-period {
                     description "OAM cell period";
                     choice oam_period_choices {
                       case case_1 {
                         leaf oam_period {
                           description "OAM cell period";
                           units "seconds";
                           type union {
                             type string {
                               pattern "<.*>|$.*";
                             }
                             type uint32 {
                               range "1 .. 900";
                             }
                           }
                         }
                       }
                       case case_2 {
                         container disable {
                           presence "enable disable";
                           description "Disable OAM loopback";
                         }
                       }
                     }
                   }
                   container oam-liveness {
                     description "OAM virtual circuit liveness parameters";
                     uses apply-advanced;
                     leaf up-count {
                       description "Number of OAM cells to consider VC up";
                       type union {
                         type string {
                           pattern "<.*>|$.*";
                         }
                         type uint32 {
                           range "1 .. 255";
                         }
                       }
                     }
                     leaf down-count {
                       description "Number of OAM cells to consider VC down";
                       type union {
                         type string {
                           pattern "<.*>|$.*";
                         }
                         type uint32 {
                           range "1 .. 255";
                         }
                       }
                     }
                   }
                   leaf inverse-arp {
                     description "Enable inverse ARP reply messages";
                     type empty;
                   }
                   leaf transmit-weight {
                     description "ATM2 transmit weight for VC under VP tunnel";
                     type union {
                       type string {
                         pattern "<.*>|$.*";
                       }
                       type uint16 {
                         range "1 .. 32767";
                       }
                     }
                   }
                   container epd-threshold {
                     description "Early packet discard threshold for ATM2";
                     uses epd_threshold_config;
                   }
                 }
                 list arp {
                   key name;
                   ordered-by user;
                   description "Static Address Resolution Protocol entries";
                   leaf name {
                     description "Destination IP address";
                     type jt:ipv4addr;
                   }
                   leaf l2-interface {
                     description "Layer 2 interface name for ARP entry";
                     type union {
                       type jt:interface-name;
                       type string {
                         pattern "<.*>|$.*";
                       }
                     }
                   }
                   choice mac_address_type {
                     case case_1 {
                       leaf mac {
                         description "MAC address";
                         type jt:mac-unicast;
                       }
                     }
                     case case_2 {
                       leaf multicast-mac {
                         description "Multicast MAC address";
                         type jt:mac-multicast;
                       }
                     }
                   }
                   leaf publish {
                     description "Reply to ARP requests for this entry";
                     type empty;
                   }
                 }
                 list vrrp-group {
                   key name;
                   ordered-by user;
                   description "VRRP group";
                   uses vrrp-group;
                 }
                 leaf virtual-gateway-address {
                   description "Virtual Gateway IP address";
                   type jt:ipv4addr;
                 }
               }
               container unnumbered-address {
                 description "Unnumbered interface address/destination prefix";
                 leaf source {
                   description "Interface from which to take local address";
                   type union {
                     type jt:interface-unit;
                     type string {
                       pattern "<.*>|$.*";
                     }
                   }
                 }
                 leaf preferred-source-address {
                   description "Preferred address on the donor interface";
                   type string;
                 }
                 leaf destination {
                   description "Destination address";
                   type jt:ipv4addr;
                 }
                 leaf destination-profile {
                   description "Profile to use for destination address";
                   type string;
                 }
               }
               leaf negotiate-address {
                 description "Negotiate address with remote";
                 type empty;
               }
             }
             container iso {
               presence "enable iso";
               description "OSI ISO protocol parameters";
               uses apply-advanced;
               list address {
                 key name;
                 ordered-by user;
                 description "Interface address";
                 leaf name {
                   description "Interface address";
                   type jt:isoaddr;
                 }
                 uses apply-advanced;
               }
               leaf mtu {
                 description "Protocol family maximum transmission unit";
                 type union {
                   type uint32;
                   type string {
                     pattern "<.*>|$.*";
                   }
                 }
               }
             }
             container inet6 {
               presence "enable inet6";
               description "IPv6 protocol parameters";
               uses apply-advanced;
               container dhcpv6-client {
                 description "Dynamic Host Configuration Protocol DHCPv6 client configuration";
                 uses apply-advanced;
                 leaf client-type {
                   description "DHCPv6 client type";
                   type enumeration {
                     enum "stateful" {
                       description "Stateful client type for address assignment.";
                     }
                     enum "autoconfig" {
                       description "Autoconfig  client type for router-advertisement";
                     }
                   }
                 }
                 list client-ia-type {
                   key name;
                   ordered-by user;
                   description "DHCPv6 client identity association type";
                   leaf name {
                     type enumeration {
                       enum "ia-na" {
                         description "Identity Association-Non-temporary Address";
                       }
                       enum "ia-pd" {
                         description "Identity Association-Prefix Address";
                       }
                     }
                   }
                   uses apply-advanced;
                 }
                 container rapid-commit {
                   presence "enable rapid-commit";
                   description "Option is used to signal the use of the two message exchange for address assignment";
                 }
                 container prefix-delegating {
                   description "Prefix delegating parameters";
                   uses apply-advanced;
                   leaf preferred-prefix-length {
                     description "Client preferred prefix length";
                     type union {
                       type string {
                         pattern "<.*>|$.*";
                       }
                       type uint32 {
                         range "0 .. 64";
                       }
                     }
                   }
                   leaf sub-prefix-length {
                     description "The sub prefix length for LAN interfaces";
                     type union {
                       type string {
                         pattern "<.*>|$.*";
                       }
                       type uint32 {
                         range "1 .. 64";
                       }
                     }
                   }
                 }
                 container client-identifier {
                   description "DHCP Server identifies a client by client-identifier value ";
                   leaf duid-type {
                     description "DUID identifying a client";
                     type enumeration {
                       enum "duid-llt" {
                         description "Link-layer address plus time";
                       }
                       enum "vendor" {
                         description "Vendor-assigned unique ID based on Enterprise Number";
                       }
                       enum "duid-ll" {
                         description "Link-layer address";
                       }
                     }
                   }
                 }
                 list req-option {
                   key name;
                   ordered-by user;
                   description "DHCPV6 client requested option configuration";
                   leaf name {
                     type enumeration {
                       enum "dns-server" {
                         description "Dns-server option";
                       }
                       enum "domain" {
                         description "Dns-server option";
                       }
                       enum "ntp-server" {
                         description "Ntp-server option";
                       }
                       enum "time-zone" {
                         description "Time-zone option";
                       }
                       enum "sip-server" {
                         description "Sip-server option";
                       }
                       enum "sip-domain" {
                         description "Sip-domain option";
                       }
                       enum "nis-server" {
                         description "Nis-server option";
                       }
                       enum "nis-domain" {
                         description "Nis-domain option";
                       }
                       enum "fqdn" {
                         description "Fully-qualified-domain option";
                       }
                       enum "vendor-spec" {
                         description "Vendor-spec option";
                       }
                     }
                   }
                   uses apply-advanced;
                 }
                 leaf retransmission-attempt {
                   description "Number of attempts to retransmit the DHCPV6 client protocol packet";
                   default "9";
                   type union {
                     type string {
                       pattern "<.*>|$.*";
                     }
                     type uint32 {
                       range "0 .. 9";
                     }
                   }
                 }
               }
               container rpf-check {
                 presence "enable rpf-check";
                 description "Enable reverse-path-forwarding checks on this interface";
                 uses apply-advanced;
                 leaf fail-filter {
                   description "Name of filter applied to packets failing RPF check";
                   type string;
                 }
                 container mode {
                   description "Mode for reverse path forwarding";
                   leaf loose {
                     description "Reverse-path-forwarding loose mode";
                     type empty;
                   }
                 }
               }
               container accounting {
                 description "Interface-based accounting options";
                 uses apply-advanced;
                 container source-class-usage {
                   uses apply-advanced;
                   leaf input {
                     description "Interface for source-class-usage input";
                     type empty;
                   }
                   leaf output {
                     description "Interface for source-class-usage output";
                     type empty;
                   }
                 }
                 leaf destination-class-usage {
                   description "Enable destination class usage on this interface";
                   type empty;
                 }
               }
               leaf mtu {
                 description "Protocol family maximum transmission unit";
                 type union {
                   type uint32;
                   type string {
                     pattern "<.*>|$.*";
                   }
                 }
               }
               leaf nd6-stale-time {
                 description "Stale time to reconfirm reachability with inet6 neighbour";
                 units "seconds";
                 type union {
                   type string {
                     pattern "<.*>|$.*";
                   }
                   type uint32 {
                     range "1 .. 18000";
                   }
                 }
               }
               leaf no-neighbor-learn {
                 description "Disable neighbor address learning on interface";
                 type empty;
               }
               leaf nd6-max-cache {
                 description "Max interface ND nexthop cache size";
                 type union {
                   type string {
                     pattern "<.*>|$.*";
                   }
                   type uint32 {
                     range "1 .. 2000000";
                   }
                 }
               }
               leaf nd6-new-hold-limit {
                 description "Max no. of new unresolved nexthops";
                 type union {
                   type string {
                     pattern "<.*>|$.*";
                   }
                   type uint32 {
                     range "1 .. 2000000";
                   }
                 }
               }
               leaf no-redirects {
                 description "Do not redirect traffic";
                 type empty;
               }
               container filter {
                 description "Packet filtering";
                 uses apply-advanced;
                 choice input_choice {
                   case case_1 {
                     container input {
                       description "Filter to be applied to received packets";
                       leaf filter-name {
                         description "Name of the filter";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       description "List of filter modules applied to received packets ";
                       type string;
                     }
                   }
                 }
                 choice output_choice {
                   case case_1 {
                     container output {
                       description "Filter to be applied to transmitted packets";
                       leaf filter-name {
                         description "Name of the filter";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32 {
                       range "1 .. 255";
                     }
                   }
                 }
               }
               container policer {
                 description "Interface policing";
                 uses apply-advanced;
                 leaf input {
                   description "Name of policer applied to received packets";
                   type string;
                 }
                 leaf output {
                   description "Name of policer applied to transmitted packets";
                   type string;
                 }
               }
               container sampling {
                 description "Interface sampling";
                 uses apply-advanced;
                 leaf input {
                   description "Sample all packets input on this interface";
                   type empty;
                 }
                 leaf output {
                   description "Sample all packets output on this interface";
                   type empty;
                 }
               }
               list address {
                 key name;
                 ordered-by user;
                 description "Interface address or destination prefix";
                 leaf name {
                   description "Interface address or destination prefix";
                   type jt:ipv6prefix;
                 }
                 uses apply-advanced;
                 leaf destination {
                   description "Destination address";
                   type jt:ipv6addr;
                 }
                 leaf eui-64 {
                   description "Generate EUI-64 interface ID";
                   type empty;
                 }
                 leaf primary {
                   description "Candidate for primary address in system";
                   type empty;
                 }
                 leaf preferred {
                   description "Preferred address on interface";
                   type empty;
                 }
                 leaf master-only {
                   description "Master management IP address for router";
                   type empty;
                 }
                 list ndp {
                   key name;
                   ordered-by user;
                   description "Static Neighbor Discovery Protocol  entries";
                   leaf name {
                     description "Destination IP address";
                     type jt:ipv6addr;
                   }
                   leaf l2-interface {
                     description "Layer 2 interface name for NDP entry";
                     type union {
                       type jt:interface-name;
                       type string {
                         pattern "<.*>|$.*";
                       }
                     }
                   }
                   choice mac_address_type {
                     case case_1 {
                       leaf mac {
                         description "MAC address";
                         type jt:mac-unicast;
                       }
                     }
                     case case_2 {
                       leaf multicast-mac {
                         description "Multicast MAC address";
                         type jt:mac-multicast;
                       }
                     }
                   }
                   leaf publish {
                     description "Reply to NDP requests for this entry";
                     type empty;
                   }
                 }
                 list vrrp-inet6-group {
                   key name;
                   ordered-by user;
                   description "VRRP group";
                   uses vrrp-group;
                 }
                 leaf virtual-gateway-address {
                   description "Virtual Gateway IP address";
                   type jt:ipv6addr;
                 }
                 leaf subnet-router-anycast {
                   description "Create a subnet roter anycast address for this address.";
                   type empty;
                 }
               }
               choice dad-disable-choice {
                 leaf dad-disable {
                   description "Disable duplicate-address-detection";
                   type empty;
                 }
                 leaf no-dad-disable {
                   description "Don't disable duplicate-address-detection";
                   type empty;
                 }
               }
             }
             container mpls {
               presence "enable mpls";
               description "MPLS protocol parameters";
               uses apply-advanced;
               leaf mtu {
                 description "Protocol family maximum transmission unit";
                 type union {
                   type uint32;
                   type string {
                     pattern "<.*>|$.*";
                   }
                 }
               }
               leaf maximum-labels {
                 description "Protocol family maximum number of labels";
                 default "3";
                 type union {
                   type string {
                     pattern "<.*>|$.*";
                   }
                   type uint32 {
                     range "3 .. 5";
                   }
                 }
               }
               container filter {
                 description "Packet filtering";
                 uses apply-advanced;
                 choice input_choice {
                   case case_1 {
                     leaf input {
                       description "Name of filter applied to received packets";
                       type string;
                     }
                   }
                   case case_2 {
                     leaf-list input-list {
                       description "List of filter modules applied to received packets ";
                       type string;
                     }
                   }
                 }
                 choice output_choice {
                   case case_1 {
                     leaf output {
                       description "Name of filter applied to transmitted packets";
                       type string;
                     }
                   }
                   case case_2 {
                     leaf-list output-list {
                       description "List of filter modules applied to transmitted packets ";
                       type string;
                     }
                   }
                 }
                 leaf group {
                   description "Interface group to which interface belongs";
                   type union {
                     type string {
                       pattern "<.*>|$.*";
                     }
                     type uint32 {
                       range "1 .. 255";
                     }
                   }
                 }
               }
               container ingress-queuing-filter {
                 description "Protocol family ingress-queuing-filter";
                 leaf filter-name {
                   description "Name of the ingress-queuing-filter";
                   type string;
                 }
               }
               container policer {
                 description "Interface policing";
                 uses apply-advanced;
                 leaf input {
                   description "Name of policer applied to received packets";
                   type string;
                 }
                 leaf output {
                   description "Name of policer applied to transmitted packets";
                   type string;
                 }
               }
             }
             container mlppp {
               description "Multilink PPP protocol parameters";
               uses apply-advanced;
               leaf bundle {
                 description "Logical interface name this link will join";
                 type string;
               }
               choice anchor-points {
                 case case_1 {
                 }
                 case case_2 {
                 }
               }
               leaf dynamic-profile {
                 description " dynamic profile for interface to use";
                 type string {
                   length "1 .. 80";
                 }
               }
             }
             container mlfr-end-to-end {
               presence "enable mlfr-end-to-end";
               description "Multilink Frame Relay end-to-end protocol parameters";
               uses apply-advanced;
               leaf bundle {
                 description "Logical interface name this link will join";
                 type union {
                   type jt:interface-unit;
                   type string {
                     pattern "<.*>|$.*";
                   }
                 }
               }
             }
             container mlfr-uni-nni {
               presence "enable mlfr-uni-nni";
               description "Multilink Frame Relay UNI NNI protocol parameters";
               uses apply-advanced;
               leaf bundle {
                 description "Logical interface name this link will join";
                 type union {
                   type jt:interface-unit;
                   type string {
                     pattern "<.*>|$.*";
                   }
                 }
               }
             }
             container ccc {
               presence "enable ccc";
               description "Circuit cross-connect parameters";
               uses apply-advanced;
               container filter {
                 description "Packet filtering";
                 uses apply-advanced;
                 choice input_choice {
                   case case_1 {
                     leaf input {
                       description "Name of filter applied to received packets";
                       type string;
                     }
                   }
                   case case_2 {
                     leaf-list input-list {
                       description "List of filter modules applied to received packets ";
                       type string;
                     }
                   }
                 }
                 choice output_choice {
                   case case_1 {
                     leaf output {
                       description "Name of filter applied to transmitted packets";
                       type string;
                     }
                   }
                   case case_2 {
                     leaf-list output-list {
                       description "List of filter modules applied to transmitted packets ";
                       type string;
                     }
                   }
                 }
                 leaf group {
                   description "Interface group to which interface belongs";
                   type union {
                     type string {
                       pattern "<.*>|$.*";
                     }
                     type uint32 {
                       range "1 .. 255";
                     }
                   }
                 }
               }
               container policer {
                 description "Interface policing";
                 uses apply-advanced;
                 leaf input {
                   description "Name of policer applied to received packets";
                   type string;
                 }
                 leaf output {
                   description "Name of policer applied to transmitted packets";
                   type string;
                 }
               }
               leaf translate-fecn-and-becn {
                 description "Translate FECN and BECN bits";
                 type empty;
               }
               choice de-or-plp {
                 case case_1 {
                   leaf translate-discard-eligible {
                     description "Translate DE bit";
                     type empty;
                   }
                 }
                 case case_2 {
                 }
               }
               leaf keep-address-and-control {
                 description "Don't strip PPP address and control bytes";
                 type empty;
               }
             }
             container tcc {
               presence "enable tcc";
               description "Translational cross-connect parameters";
               uses apply-advanced;
               container policer {
                 description "Interface policing";
                 uses apply-advanced;
                 leaf input {
                   description "Name of policer applied to received packets";
                   type string;
                 }
                 leaf output {
                   description "Name of policer applied to transmitted packets";
                   type string;
                 }
               }
               container proxy {
                 presence "enable proxy";
                 uses apply-advanced;
                 leaf inet-address {
                   description "Remote host address on non-Ethernet side of Ethernet TCC";
                   type jt:ipv4addr;
                 }
               }
               container remote {
                 presence "enable remote";
                 uses apply-advanced;
                 leaf inet-address {
                   description "Remote host address on Ethernet side of Ethernet TCC";
                   type jt:ipv4addr;
                 }
                 leaf mac-address {
                   description "Remote host MAC address on Ethernet side of Ethernet TCC";
                   type jt:mac-addr;
                 }
               }
             }
             container vpls {
               presence "enable vpls";
               description "Virtual private LAN service parameters";
               uses apply-advanced;
               leaf core-facing {
                 description "Interface is core facing";
                 type empty;
               }
             }
             container bridge {
               presence "enable bridge";
               description "Layer-2 bridging parameters";
               uses apply-advanced;
               leaf core-facing {
                 description "Interface is core facing";
                 type empty;
               }
               leaf interface-mode {
                 description "Interface mode (access or trunk)";
                 type enumeration {
                   enum "access" {
                     description "Interface mode is access";
                   }
                   enum "trunk" {
                     description "Interface mode is trunk";
                   }
                 }
               }
               leaf vlan-auto-sense {
                 description "Enable VLAN auto sense on this interface";
                 type empty;
               }
               leaf bridge-domain-type {
                 description "Bridge domain type (svlan or bvlan)";
                 type enumeration {
                   enum "svlan" {
                     description "Bridge domain type svlan";
                   }
                   enum "bvlan" {
                     description "Bridge domain type bvlan";
                   }
                 }
               }
               leaf inter-switch-link {
                 description "PVLAN inter switch link";
                 type empty;
               }
               choice vlan_list {
                 case case_1 {
                   leaf vlan-id {
                     description "Access mode and trunk mode VLAN membership";
                     type union {
                       type string {
                         pattern "<.*>|$.*";
                       }
                       type uint32 {
                         range "1 .. 4094";
                       }
                     }
                   }
                 }
                 case case_2 {
                   leaf-list vlan-id-list {
                     description "Trunk mode VLAN membership for this interface";
                     type string;
                   }
                 }
                 case case_3 {
                   leaf-list inner-vlan-id-list {
                     description "Trunk mode VLAN membership for this interface based on inner VLAN tag";
                     type string;
                   }
                 }
               }
               container vlan-rewrite {
                 description "Specify vlan translation";
                 uses apply-advanced;
                 list translate {
                   key name;
                   ordered-by user;
                   description "Translate incoming VLAN tag";
                   leaf name {
                     description "Specify the incoming VLAN tag";
                     type union {
                       type string {
                         pattern "<.*>|$.*";
                       }
                       type uint32 {
                         range "1 .. 4094";
                       }
                     }
                   }
                   leaf to-vlan-id {
                     description "Specify the bridge-domain VLAN-ID";
                     type union {
                       type string {
                         pattern "<.*>|$.*";
                       }
                       type uint32 {
                         range "1 .. 4094";
                       }
                     }
                   }
                 }
               }
               choice isid_list {
                 case case_1 {
                   leaf isid-list {
                     description "Specify the ISID list";
                     type enumeration {
                       enum "all-service-groups" {
                         description "Map all ISIDs specified under the service-groups";
                       }
                       enum "all" {
                         description "Map all ISIDs";
                       }
                     }
                   }
                 }
               }
               container recovery-timeout {
                 description "Recovery timeout for this interface";
                 leaf time-in-seconds {
                   units "seconds";
                   type union {
                     type string {
                       pattern "<.*>|$.*";
                     }
                     type uint32 {
                       range "10 .. 3600";
                     }
                   }
                 }
               }
             }
             container ethernet-switching {
               description "Ethernet switching parameters";
               uses ethernet-switching-type;
             }
             container fibre-channel {
               description "Fibre channel switching parameters";
               uses fibre-channel-type;
             }
             container any {
               presence "enable any";
               description "Parameters for 'any' family";
               uses apply-advanced;
               container filter {
                 description "Layer 2 packet filtering";
                 uses apply-advanced;
                 leaf input {
                   description "Name of filter applied to received packets";
                   type string {
                   }
                 }
                 leaf group {
                   description "Group to which interface belongs";
                   type union {
                     type string {
                       pattern "<.*>|$.*";
                     }
                     type uint32 {
                       range "1 .. 255";
                     }
                   }
                 }
               }
             }
             uses apply-advanced;
           }
           leaf service-domain {
             description "Service domain to which interface belongs";
             type enumeration {
               enum "inside" {
                 description "Inside network";
               }
               enum "outside" {
                 description "Outside network";
               }
             }
           }
           leaf copy-tos-to-outer-ip-header {
             description "Copy IP payload header's ToS field to GRE delivery header";
             type empty;
           }
           container load-balancing-options {
             description "AMS subunit load balancing options";
             uses apply-advanced;
             leaf preferred-active {
               description "Preferred active Interface name";
               type union {
                 type jt:interface-device;
                 type string {
                   pattern "<.*>|$.*";
                 }
               }
             }
             container hash-keys {
               uses apply-advanced;
               leaf-list ingress-key {
                 description "Hash Key for the ingress direction";
                 type enumeration {
                   enum "source-ip" {
                     description "Source Ip Address";
                   }
                   enum "destination-ip" {
                     description "Destination Ip Address";
                   }
                   enum "protocol" {
                     description "Protocol";
                   }
                   enum "iif" {
                     description "Incoming Interface";
                   }
                 }
               }
               leaf-list egress-key {
                 description "Hash Key for the egress direction";
                 status deprecated;
                 type enumeration {
                   enum "source-ip" {
                     description "Source Ip Address";
                     status deprecated;
                   }
                   enum "destination-ip" {
                     description "Destination Ip Address";
                     status deprecated;
                   }
                   enum "protocol" {
                     description "Protocol";
                     status deprecated;
                   }
                   enum "oif" {
                     description "Outgoing Interface";
                     status deprecated;
                   }
                 }
               }
             }
           }
           leaf mac {
             description "Configure logical interface MAC address";
             type jt:mac-unicast;
           }
           leaf virtual-gateway-v4-mac {
             description "Configure virtual gateway IPV4 virtual MAC address";
             type jt:mac-unicast;
           }
           leaf virtual-gateway-v6-mac {
             description "Configure virtual gateway IPV6 virtual MAC address";
             type jt:mac-unicast;
           }
           leaf etree-ac-role {
             description "ETREE attachment circuit role";
             type enumeration {
               enum "root" {
                 description "ETREE root interface";
               }
               enum "leaf" {
                 description "ETREE leaf interface";
               }
             }
           }
         }
         container no-partition {
           description "Use channelizable interface as clear channel";
           leaf interface-type {
             description "Interface type";
             type enumeration {
               enum "e1" {
                 description "E1 interface";
               }
               enum "t1" {
                 description "T1 interface";
               }
               enum "at" {
                 description "ATM interface";
               }
               enum "t3" {
                 description "T3 interface";
               }
               enum "e3" {
                 description "E3 interface";
               }
               enum "ct3" {
                 description "Channelized T3 interface";
               }
               enum "so" {
                 description "SONET interface";
               }
               enum "cau4" {
                 description "CAU4 interface";
               }
             }
           }
         }
         list partition {
           key name;
           ordered-by user;
           description "Channelized interface partition";
           leaf name {
             description "Sublevel interface partition index (for example, 1, 3-4)";
             type string;
           }
           leaf oc-slice {
             description "Range of SONET/SDH slices (for example, 1, 7-9)";
             type string;
           }
           leaf timeslots {
             description "Timeslots [(1..24) for T1, (1..31) for E1]; for example, 1-3,4,9,22-24 (no spaces)";
             type string;
           }
           leaf interface-type {
             description "Sublevel interface type";
             type enumeration {
               enum "ds" {
                 description "DS0 interface";
               }
               enum "e1" {
                 description "E1 interface";
               }
               enum "t1" {
                 description "T1 interface";
               }
               enum "at" {
                 description "ATM interface";
               }
               enum "ct1" {
                 description "Channelized T1 interface";
               }
               enum "ce1" {
                 description "Channelized E1 interface";
               }
               enum "t3" {
                 description "T3 interface";
               }
               enum "ct3" {
                 description "Channelized T3 interface";
               }
               enum "e3" {
                 description "E3 interface";
               }
               enum "so" {
                 description "SONET interface";
               }
               enum "coc1" {
                 description "Channelized OC1 interface";
               }
               enum "cau4" {
                 description "Channelized AU4 interface";
               }
               enum "dc" {
                 description "D channel interface";
               }
               enum "bc" {
                 description "B channel interface";
               }
             }
           }
         }
       }
       list interface {
         key name;
         uses interfaces_type;
       }
     }
   }
   grouping aggregate-load-balance {
     description "Load balancing parameters";
     uses apply-advanced;
     choice adaptive_option {
       case case_1 {
       }
       case case_2 {
       }
       case case_3 {
         container adaptive {
           presence "enable adaptive";
           description "Enable adaptive load balancing by re-programming selector table";
           uses apply-advanced;
           leaf tolerance {
             description "Target tolerance in percentage (default 20%)";
             units "percent";
             type union {
               type string {
                 pattern "<.*>|$.*";
               }
               type uint32 {
                 range "1 .. 100";
               }
             }
           }
           leaf pps {
             description "Adaptive load balance based on packet per second (default bps)";
             type empty;
           }
           leaf scan-interval {
             description "Scan interval for multiple of 30 seconds (default 30 seconds)";
             type union {
               type string {
                 pattern "<.*>|$.*";
               }
               type uint32 {
                 range "1 .. 5";
               }
             }
           }
         }
       }
     }
   }
   grouping apply-advanced {
     description "Apply advanced configuration logic";
     leaf-list apply-groups {
       description "Groups from which to inherit configuration data";
       type string;
     }
     leaf-list apply-groups-except {
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping aps_type {
     uses apply-advanced;
     choice aps_mode {
       case case_1 {
         leaf working-circuit {
           description "Working circuit group name";
           type string;
         }
       }
       case case_2 {
         leaf protect-circuit {
           description "Protect circuit group name";
           type string;
         }
       }
     }
     leaf annex-b {
       description "Annex-b mode";
       type empty;
     }
     leaf wait-to-restore-time {
       description "Circuit wait-to-restore time for annex-b";
       units "seconds";
       type union {
         type string {
           pattern "<.*>|$.*";
         }
         type uint32 {
           range "1 .. 4294967295";
         }
       }
     }
     leaf preserve-interface {
       description "Preserve interface state for fast failover";
       type empty;
     }
     leaf neighbor {
       description "Neighbor address";
       type jt:ipv4addr;
     }
     leaf paired-group {
       description "Name of paired APS group";
       type string;
     }
     container authentication-key {
       presence "enable authentication-key";
       description "Authentication parameters";
       leaf auth_key {
         description "Authentication key";
         type jt:unreadable;
       }
     }
     leaf switching-mode {
       description "APS switching mode";
       type enumeration {
         enum "bidirectional" {
           description "Bidirectional";
         }
         enum "unidirectional" {
           description "Unidirectional";
         }
       }
     }
     leaf advertise-interval {
       description "Advertise interval";
       units "milliseconds";
       type union {
         type string {
           pattern "<.*>|$.*";
         }
         type uint32 {
           range "1 .. 65534";
         }
       }
     }
     leaf hold-time {
       description "Hold time";
       units "milliseconds";
       type union {
         type string {
           pattern "<.*>|$.*";
         }
         type uint32 {
           range "1 .. 65534";
         }
       }
     }
     leaf revert-time {
       description "Circuit revert time";
       units "seconds";
       type union {
         type string {
           pattern "<.*>|$.*";
         }
         type uint32 {
           range "0 .. 65534";
         }
       }
     }
     choice break-before-make-choice {
       leaf break-before-make {
         description "Ensure only one interface is active at a time";
         type empty;
       }
       leaf no-break-before-make {
         description "Don't ensure only one interface is active at a time";
         type empty;
       }
     }
     choice manual_mode {
       case case_1 {
         leaf request {
           description "Request circuit state";
           type enumeration {
             enum "protect" {
               description "Request protect circuit";
             }
             enum "working" {
               description "Request working circuit";
             }
           }
         }
       }
       case case_2 {
         leaf force {
           description "Force circuit state";
           type enumeration {
             enum "protect" {
               description "Force protect circuit";
             }
             enum "working" {
               description "Force working circuit";
             }
           }
         }
       }
       case case_3 {
         leaf lockout {
           description "Lockout protection";
           type empty;
         }
       }
     }
     leaf fast-aps-switch {
       description "Fast aps switch";
       type empty;
     }
   }
   grouping cos_policer {
     description "Define a CoS based policer";
     leaf name {
       description "Policer name";
       type string {
       }
     }
     uses apply-advanced;
     container premium {
       description "Policer to apply to premium traffic";
       uses ethernet_policer;
     }
     container aggregate {
       description "Policer to apply to aggregate traffic";
       uses ethernet_policer;
     }
   }
   grouping cos_policer_input_priority_map {
     description "Input policer priority map";
     uses apply-advanced;
     container ieee-802.1p {
       description "Use IEEE 802.1p to determine policer priority map";
       uses apply-advanced;
       leaf-list premium {
         description "Input traffic's IEEE 802.1p value to which premium policer is applied";
         type union {
           type string {
             pattern "<.*>|$.*";
           }
           type uint32 {
             range "0 .. 7";
           }
         }
       }
     }
   }
   grouping cos_policer_output_priority_map {
     description "Output policer priority map";
     uses apply-advanced;
     container classifier {
       description "Use classifier as policer priority map";
       uses apply-advanced;
       container premium {
         description "Output traffic classifier to which premium policer is applied";
         uses apply-advanced;
         list forwarding-class {
           key name;
           ordered-by user;
           description "Select a classification for this priority map";
           leaf name {
             description "Forwarding class name";
             type string {
             }
           }
           uses apply-advanced;
           list loss-priority {
             key name;
             ordered-by user;
             description "Select a loss priority";
             leaf name {
               type enumeration {
                 enum "low" {
                   description "Select low loss priority as premium policer";
                 }
                 enum "high" {
                   description "Select high loss priority as premium policer";
                 }
               }
             }
           }
         }
       }
     }
   }
   grouping dcd_rx_bucket_config {
     uses apply-advanced;
     leaf overflow {
       description "Overflow behavior";
       type enumeration {
         enum "tag" {
           description "Tag and count overflow packets";
         }
         enum "discard" {
           description "Discard overflow packets";
         }
       }
     }
     leaf rate {
       description "Bucket rate";
       type union {
         type string {
           pattern "<.*>|$.*";
         }
         type uint32 {
           range "0 .. 100";
         }
       }
     }
     leaf threshold {
       description "Bucket threshold";
       type union {
         type string {
           pattern "<.*>|$.*";
         }
         type uint32 {
           range "0 .. 65535";
         }
       }
     }
   }
   grouping dcd_shaping_config {
     description "Traffic-shaping profile";
     uses apply-advanced;
     choice useless_shaping_choice {
       case case_1 {
         container cbr {
           presence "enable cbr";
           description "Constant bandwidth utilization";
           leaf cbr-value {
             description "Constant bandwidth utilization";
             type string;
           }
         }
       }
       case case_2 {
         container vbr {
           description "Variable bandwidth utilization";
           leaf peak {
             description "Peak rate";
             type string;
           }
           leaf sustained {
             description "Sustained rate";
             type string;
           }
           leaf burst {
             description "Burst size";
             type string;
           }
         }
       }
       case case_3 {
         container rtvbr {
           description "ATM2 real-time variable bandwidth utilization";
           leaf peak {
             description "Peak rate";
             type string;
           }
           leaf sustained {
             description "Sustained rate";
             type string;
           }
           leaf burst {
             description "Burst size";
             type string;
           }
         }
       }
     }
     leaf queue-length {
       description "Queue length";
       type union {
         type string {
           pattern "<.*>|$.*";
         }
         type uint32 {
           range "1 .. 16383";
         }
       }
     }
   }
   grouping dcd_tx_bucket_config {
     uses apply-advanced;
     leaf overflow {
       description "Overflow behavior";
       type enumeration {
         enum "discard" {
           description "Discard overflow packets";
         }
       }
     }
     leaf rate {
       description "Bucket rate";
       type union {
         type string {
           pattern "<.*>|$.*";
         }
         type uint32 {
           range "0 .. 100";
         }
       }
     }
     leaf threshold {
       description "Bucket threshold";
       type union {
         type string {
           pattern "<.*>|$.*";
         }
         type uint32 {
           range "0 .. 65535";
         }
       }
     }
   }
   grouping epd_threshold_config {
     uses apply-advanced;
     leaf epd-threshold-plp0 {
       description "Early packet discard threshold value";
       units "cells";
       type string;
     }
     leaf plp1 {
       description "Early packet drop threshold value for PLP 1";
       units "cells";
       type string;
     }
   }
   grouping ethernet-switching-type {
     description "Ethernet switching family";
     uses apply-advanced;
     leaf port-mode {
       description "Type of port mode";
       type enumeration {
         enum "access" {
           description "Interface mode is access";
         }
         enum "tagged-access" {
           description "Interface mode is tagged-access";
         }
         enum "trunk" {
           description "Interface mode is trunk";
         }
       }
     }
     leaf interface-mode {
       description "Type of interface mode";
       default "access";
       type enumeration {
         enum "access" {
           description "Interface mode is access";
         }
         enum "trunk" {
           description "Interface mode is trunk";
         }
       }
     }
     leaf inter-switch-link {
       description "PVLAN inter switch link";
       type empty;
     }
     leaf reflective-relay {
       description "Reflective-relay mode for this interface";
       type empty;
     }
     choice vlan_choice_list {
       case case_1 {
         container vlan {
           description "Virtual LAN parameters";
           uses apply-advanced;
           leaf-list members {
             description "Membership for this interface (name or id)";
             type string;
           }
         }
       }
       case case_2 {
         container inner-vlan {
           description "Trunk mode vlan membership for this interface";
           uses apply-advanced;
           leaf-list members {
             description "Membership for this interface (name or id)";
             type string;
           }
         }
       }
       case case_3 {
         leaf-list inner-vlan-id-list {
           description "Trunk mode VLAN membership for this interface based on inner VLAN tag";
           type string;
         }
       }
     }
     leaf vlan-auto-sense {
       description "Enable VLAN auto sense on this interface";
       type empty;
     }
     leaf bridge-domain-type {
       description "Bridge domain type";
       type enumeration {
         enum "svlan" {
           description "Bridge domain type SVLAN";
         }
         enum "bvlan" {
           description "Bridge domain type BVLAN";
         }
       }
     }
     container vlan-rewrite {
       description "Specify VLAN translation";
       uses apply-advanced;
       list translate {
         key name;
         ordered-by user;
         description "Translate incoming VLAN tag";
         leaf name {
           description "Specify the incoming VLAN tag";
           type union {
             type string {
               pattern "<.*>|$.*";
             }
             type uint32 {
               range "1 .. 4094";
             }
           }
         }
         leaf to-vlan-id {
           description "Specify the bridge-domain VLAN-ID";
           type union {
             type string {
               pattern "<.*>|$.*";
             }
             type uint32 {
               range "1 .. 4094";
             }
           }
         }
       }
     }
     leaf native-vlan-id {
       description "Untagged packets on a trunk/tagged-access interface belong to this vlan";
       type string {
       }
     }
     choice isid_list {
       case case_1 {
         leaf isid-list {
           description "Specify the ISID list";
           type enumeration {
             enum "all-service-groups" {
               description "Map all ISIDs specified under the service-groups";
             }
             enum "all" {
               description "Map all ISIDs";
             }
           }
         }
       }
     }
     leaf core-facing {
       description "Interface is core facing";
       type empty;
     }
     container filter {
       description "Packet filtering";
       uses apply-advanced;
       leaf input {
         description "Name of filter applied to received packets";
         type string;
       }
       leaf input-precedence {
         description "Precedence of the filter";
         type union {
           type string {
             pattern "<.*>|$.*";
           }
           type uint32 {
             range "0 .. 255";
           }
         }
       }
       leaf-list input-list {
         description "List of filter modules applied to received packets ";
         type string;
       }
       leaf output {
         description "Name of filter applied to transmitted packets";
         type string;
       }
       leaf output-precedence {
         description "Precedence of the filter";
         type union {
           type string {
             pattern "<.*>|$.*";
           }
           type uint32 {
             range "0 .. 255";
           }
         }
       }
       leaf-list output-list {
         description "List of filter modules applied to transmitted packets ";
         type string;
       }
       container adf {
         description "Ascend Data Filter definition";
         uses apply-advanced;
         list rule {
           key name;
           ordered-by user;
           description "Set of ADF rules";
           leaf name {
             description "Value for a single rule";
             type string;
           }
           uses apply-advanced;
         }
         leaf counter {
           description "Add a counter to each rule";
           type empty;
         }
         leaf input-precedence {
           description "Precedence of the input rules";
           type union {
             type string {
               pattern "<.*>|$.*";
             }
             type uint32 {
               range "0 .. 255";
             }
           }
         }
         leaf not-mandatory {
           description "No errors will be reported if no rules are present";
           type empty;
         }
         leaf output-precedence {
           description "Precedence of the output rules";
           type union {
             type string {
               pattern "<.*>|$.*";
             }
             type uint32 {
               range "0 .. 255";
             }
           }
         }
       }
       leaf group {
         description "Group to which interface belongs";
         type union {
           type string {
             pattern "<.*>|$.*";
           }
           type uint32 {
             range "1 .. 255";
           }
         }
       }
     }
     container storm-control {
       description "Storm control profile name to bind";
       uses apply-advanced;
       leaf profile-name {
         description "Profile name";
         type string;
       }
     }
     container recovery-timeout {
       description "Recovery timeout for this interface";
       leaf time-in-seconds {
         units "seconds";
         type union {
           type string {
             pattern "<.*>|$.*";
           }
           type uint32 {
             range "10 .. 3600";
           }
         }
       }
     }
   }
   grouping ethernet_policer {
     description "Define a policer";
     uses apply-advanced;
     choice bandwidth {
       case case_1 {
         leaf bandwidth-limit {
           description "Bandwidth limit";
           units "bits per second";
           type string;
         }
       }
     }
     leaf burst-size-limit {
       description "Burst size limit";
       units "bytes";
       type string;
     }
   }
   grouping fibre-channel-type {
     description "Fibre Channel switching family";
     uses apply-advanced;
     leaf port-mode {
       description "Port mode";
       type enumeration {
         enum "f-port" {
           description "Fabric port";
         }
         enum "e-port" {
           description "Inter-switch port";
         }
         enum "np-port" {
           description "Proxy node port";
         }
         enum "auto" {
           description "Interface mode (F/E) is determined at runtime";
         }
       }
     }
     leaf no-npiv {
       description "Disable NPIV";
       type empty;
     }
     container fc-fabric {
       description "Virtual fabric parameters";
       uses apply-advanced;
       leaf-list members {
         description "Virtual Fabric Membership for this interface (name or id)";
         type string;
       }
     }
     leaf native-fabric {
       description "FC frames with no virtual fabric header on a interface belong to this fabric";
       type string {
       }
     }
   }
   grouping interfaces_type {
     description "Physical interface";
     leaf name {
       type string;
     }
     uses apply-advanced;
     leaf description {
       description "Text description of interface";
       type string;
     }
     leaf metadata {
       description "Text metadata attached to interface";
       type string;
     }
     choice enable-disable {
       case case_1 {
         leaf disable {
           description "Disable this interface";
           type empty;
         }
       }
     }
     container traceoptions {
       presence "enable traceoptions";
       description "Interface trace options";
       uses apply-advanced;
       list flag {
         key name;
         ordered-by user;
         description "Tracing parameters";
         leaf name {
           type enumeration {
             enum "ipc" {
               description "Trace interface IPC messages";
             }
             enum "event" {
               description "Trace interface events";
             }
             enum "media" {
               description "Trace interface media changes";
             }
             enum "all" {
               description "Enable all interface trace flags";
             }
           }
         }
       }
     }
     leaf passive-monitor-mode {
       description "Use interface to tap packets from another router";
       type empty;
     }
     choice keepalive_choices {
       case case_1 {
         container keepalives {
           description "Send or demand keepalive messages";
           uses keepalives_type;
         }
       }
       case case_2 {
         leaf no-keepalives {
           description "Do not send keepalive messages";
           type empty;
         }
       }
     }
     choice traps-choice {
       leaf traps {
         description "Enable SNMP notifications on state changes";
         type empty;
       }
       leaf no-traps {
         description "Don't enable SNMP notifications on state changes";
         type empty;
       }
     }
     choice interface-mib-choice {
       leaf interface-mib {
         description "Enable interface-related MIBs";
         type empty;
       }
       leaf no-interface-mib {
         description "Don't enable interface-related MIBs";
         type empty;
       }
     }
     leaf accounting-profile {
       description "Accounting profile name";
       type string;
     }
     choice scheduler_type {
       case case_1 {
         choice per-unit-scheduler-choice {
           leaf per-unit-scheduler {
             description "Enable subunit queuing on Frame Relay or VLAN IQ interface";
             type empty;
           }
           leaf no-per-unit-scheduler {
             description "Don't enable subunit queuing on Frame Relay or VLAN IQ interface";
             type empty;
           }
         }
       }
       case case_2 {
         leaf shared-scheduler {
           description "Enabled shared queuing on an IQ2 interface";
           type empty;
         }
       }
       case case_3 {
         container hierarchical-scheduler {
           presence "enable hierarchical-scheduler";
           description "Enable hierarchical scheduling";
           leaf maximum-hierarchy-levels {
             description "Maximum hierarchy levels";
             type union {
               type string {
                 pattern "<.*>|$.*";
               }
               type uint32 {
                 range "2 .. 4";
               }
             }
           }
           leaf implicit-hierarchy {
             description "Implicit hierarchy (follows interface hierarchy)";
             type empty;
           }
         }
       }
     }
     leaf l2tp-maximum-session {
       description "Maximum L2TP session";
       type union {
         type string {
           pattern "<.*>|$.*";
         }
         type uint32 {
           range "0 .. 64000";
         }
       }
     }
     leaf schedulers {
       description "Number of schedulers to allocate for interface";
       type union {
         type uint32;
         type string {
           pattern "<.*>|$.*";
         }
       }
     }
     leaf cascade-port {
       description "Cascade port";
       type empty;
     }
     leaf dce {
       description "Respond to Frame Relay status enquiry messages";
       type empty;
     }
     choice vlan_tag_mode {
       case case_1 {
         leaf vlan-tagging {
           description "802.1q VLAN tagging support";
           type empty;
         }
       }
       case case_2 {
         leaf stacked-vlan-tagging {
           description "Stacked 802.1q VLAN tagging support";
           type empty;
         }
       }
       case case_3 {
         leaf flexible-vlan-tagging {
           description "Support for no tagging, or single and double 802.1q VLAN tagging";
           type empty;
         }
       }
       case case_4 {
         leaf vlan-vci-tagging {
           description "CCC for VLAN Q-in-Q and ATM VPI/VCI interworking";
           type empty;
         }
       }
     }
     leaf native-vlan-id {
       description "Virtual LAN identifier for untagged frames";
       type union {
         type string {
           pattern "<.*>|$.*";
         }
         type uint32 {
           range "0 .. 4094";
         }
       }
     }
     leaf speed {
       description "Link speed";
       type enumeration {
         enum "auto" {
           description "Enable auto negotiation of interface speed";
         }
         enum "auto-10m-100m" {
           description "Enable auto negotiation of limiting interface speed to 10m/100m";
         }
         enum "10m" {
         }
         enum "100m" {
         }
         enum "1g" {
         }
         enum "2.5g" {
         }
         enum "5g" {
         }
         enum "10g" {
         }
         enum "40g" {
         }
         enum "oc3" {
         }
         enum "oc12" {
         }
         enum "oc48" {
         }
       }
     }
     leaf mtu {
       description "Maximum transmit packet size";
       type union {
         type string {
           pattern "<.*>|$.*";
         }
         type uint32;
       }
     }
     container hold-time {
       description "Hold time for link up and link down";
       leaf up {
         description "Link up hold time";
         units "milliseconds";
         type union {
           type uint32;
           type string {
             pattern "<.*>|$.*";
           }
         }
       }
       leaf down {
         description "Link down hold time";
         units "milliseconds";
         type union {
           type uint32;
           type string {
             pattern "<.*>|$.*";
           }
         }
       }
     }
     container link-degrade-monitor {
       presence "enable link-degrade-monitor";
       description "Enable link degrade monitoring";
       uses apply-advanced;
       container actions {
         description "Action upon link degrade event";
         uses apply-advanced;
         choice action_choice {
           case case_1 {
             leaf media-based {
               description "Media based";
               type empty;
             }
           }
         }
       }
       container recovery {
         description "Link degrade recovery mechanism";
         uses apply-advanced;
         leaf timer {
           description "Auto recovery timer in seconds";
           default "1800";
           type union {
             type uint32;
             type string {
               pattern "<.*>|$.*";
             }
           }
         }
         choice receovery_choice {
           case case_1 {
             leaf auto {
               description "Automatic recovery";
               type empty;
             }
           }
           case case_2 {
             leaf manual {
               description "Manual recovery";
               type empty;
             }
           }
         }
       }
       container thresholds {
         description "Link degrade threshold parameters";
         uses apply-advanced;
         leaf set {
           description "BER at which link considered degraded(1..16)";
           default "1e-7";
           type string {
           }
         }
         leaf clear {
           description "BER at which link considered improved(1..16)";
           default "1e-12";
           type string {
           }
         }
         leaf warning-set {
           description "BER at which link degrade warning raised(1..16)";
           default "1e-9";
           type string {
           }
         }
         leaf warning-clear {
           description "BER at which link degrade warning cleared(1..16)";
           default "1e-11";
           type string {
           }
         }
         leaf interval {
           description "Consecutive link degrade events";
           default "10";
           type union {
             type string {
               pattern "<.*>|$.*";
             }
             type uint32 {
               range "1 .. 256";
             }
           }
         }
       }
     }
     container satop-options {
       description "Structure-Agnostic TDM over Packet protocol options";
       uses apply-advanced;
       leaf idle-pattern {
         description "An 8-bit hexadecimal pattern to replace TDM data in a lost packet";
         type union {
           type string {
             pattern "<.*>|$.*";
           }
           type uint32 {
             range "0 .. 255";
           }
         }
       }
       leaf payload-size {
         description "Number of payload bytes per packet";
         type union {
           type string {
             pattern "<.*>|$.*";
           }
           type uint32 {
             range "64 .. 1024";
           }
         }
       }
       container excessive-packet-loss-rate {
         description "Packet loss options";
         uses apply-advanced;
         leaf threshold {
           description "Percentile designating the threshold of excessive packet loss rate";
           type union {
             type string {
               pattern "<.*>|$.*";
             }
             type uint8 {
               range "1 .. 100";
             }
           }
         }
         leaf sample-period {
           description "Number of milliseconds over which excessive packet loss rate is calculated";
           type union {
             type string {
               pattern "<.*>|$.*";
             }
             type uint32 {
               range "1000 .. 65535";
             }
           }
         }
       }
       choice jitter-buffer-size {
         case case_1 {
           leaf jitter-buffer-packets {
             description "Number of packets in jitter buffer before packet data is played out in the line";
             type union {
               type string {
                 pattern "<.*>|$.*";
               }
               type uint32 {
                 range "1 .. 64";
               }
             }
           }
         }
         case case_2 {
           leaf jitter-buffer-latency {
             description "Number of milliseconds delay in jitter buffer before packet data is played out in the line";
             units "milliseconds";
             type union {
               type string {
                 pattern "<.*>|$.*";
               }
               type uint32 {
                 range "1 .. 1000";
               }
             }
           }
         }
         case case_3 {
           leaf jitter-buffer-auto-adjust {
             description "Automatically adjust jitter buffer";
             type empty;
           }
         }
       }
       leaf bit-rate {
         description "In multiples of DS0";
         type union {
           type string {
             pattern "<.*>|$.*";
           }
           type uint32 {
             range "1 .. 10240";
           }
         }
       }
     }
     container cesopsn-options {
       description "Structure-Aware TDM over Packet protocol options";
       uses apply-advanced;
       leaf idle-pattern {
         description "An 8-bit hexadecimal pattern to replace TDM data in a lost packet";
         type union {
           type string {
             pattern "<.*>|$.*";
           }
           type uint32 {
             range "0 .. 255";
           }
         }
       }
       leaf packetization-latency {
         description "Number of microseconds to create packets";
         units "microseconds";
         type union {
           type string {
             pattern "<.*>|$.*";
           }
           type uint32 {
             range "1000 .. 8000";
           }
         }
       }
       leaf payload-size {
         description "Number of payload bytes per packet";
         type union {
           type string {
             pattern "<.*>|$.*";
           }
           type uint32 {
             range "64 .. 1024";
           }
         }
       }
       container excessive-packet-loss-rate {
         description "Packet loss options";
         uses apply-advanced;
         leaf threshold {
           description "Percentile designating the threshold of excessive packet loss rate";
           type union {
             type string {
               pattern "<.*>|$.*";
             }
             type uint8 {
               range "1 .. 100";
             }
           }
         }
         leaf sample-period {
           description "Number of milliseconds over which excessive packet loss rate is calculated";
           type union {
             type string {
               pattern "<.*>|$.*";
             }
             type uint32 {
               range "1000 .. 65535";
             }
           }
         }
       }
       choice jitter-buffer-size {
         case case_1 {
           leaf jitter-buffer-packets {
             description "Number of packets in jitter buffer before packet data is played out in the line";
             type union {
               type string {
                 pattern "<.*>|$.*";
               }
               type uint32 {
                 range "1 .. 64";
               }
             }
           }
         }
         case case_2 {
           leaf jitter-buffer-latency {
             description "Number of milliseconds delay in jitter buffer before packet data is played out in the line";
             units "milliseconds";
             type union {
               type string {
                 pattern "<.*>|$.*";
               }
               type uint32 {
                 range "1 .. 1000";
               }
             }
           }
         }
         case case_3 {
           leaf jitter-buffer-auto-adjust {
             description "Automatically adjust jitter buffer";
             type empty;
           }
         }
       }
       leaf bit-rate {
         description "In multiples of DS0";
         type union {
           type string {
             pattern "<.*>|$.*";
           }
           type uint32 {
             range "1 .. 10240";
           }
         }
       }
     }
     container clocking {
       description "Interface clock source";
       choice clocking_choices {
         case case_1 {
           leaf internal {
             description "Clocking provided by local system";
             type empty;
           }
         }
         case case_2 {
           container external {
             presence "enable external";
             description "Clocking provided by DCE (loop timing)";
           }
         }
       }
     }
     leaf link-mode {
       description "Link operational mode";
       type enumeration {
         enum "automatic" {
           description "Automatically negotiate duplex";
         }
         enum "half-duplex" {
           description "Half-duplex operation";
         }
         enum "full-duplex" {
           description "Full-duplex operation";
         }
       }
     }
     leaf encapsulation {
       description "Physical link-layer encapsulation";
       type enumeration {
         enum "ethernet" {
           description "Ethernet physical media";
         }
         enum "fddi" {
           description "FDDI physical media";
         }
         enum "token-ring" {
           description "Token Ring physical media";
         }
         enum "ppp" {
           description "Serial PPP device";
         }
         enum "ppp-ccc" {
           description "Serial PPP device for a cross-connect";
         }
         enum "ppp-tcc" {
           description "Serial PPP device for a translational cross-connect";
         }
         enum "ether-vpls-ppp" {
           description "Ethernet VPLS over PPP (bridging) device";
         }
         enum "frame-relay" {
           description "Frame Relay encapsulation";
         }
         enum "frame-relay-ccc" {
           description "Frame Relay for cross-connect";
         }
         enum "frame-relay-tcc" {
           description "Frame Relay for translational cross-connect";
         }
         enum "extended-frame-relay-ccc" {
           description "Any Frame Relay DLCI for cross-connect";
         }
         enum "extended-frame-relay-tcc" {
           description "Any Frame Relay DLCI for translational cross-connect";
         }
         enum "flexible-frame-relay" {
           description "Multiple Frame Relay encapsulations";
         }
         enum "frame-relay-port-ccc" {
           description "Frame Relay port encapsulation for a cross-connect";
         }
         enum "frame-relay-ether-type" {
           description "Cisco-compatible Frame Relay encapsulation";
         }
         enum "frame-relay-ether-type-tcc" {
           description "Cisco-compatible Frame Relay encapsulation for translational cross-connect";
         }
         enum "extended-frame-relay-ether-type-tcc" {
           description "Cisco-compatible Frame Relay encapsulation any DLCI for translational cross-connect";
         }
         enum "cisco-hdlc" {
           description "Cisco-compatible HDLC framing";
         }
         enum "cisco-hdlc-ccc" {
           description "Cisco-compatible HDLC framing for a cross-connect";
         }
         enum "cisco-hdlc-tcc" {
           description "Cisco-compatible HDLC framing for a translational cross-connect";
         }
         enum "vlan-ccc" {
           description "802.1q tagging for a cross-connect";
         }
         enum "extended-vlan-ccc" {
           description "Nonstandard TPID tagging for a cross-connect";
         }
         enum "ethernet-ccc" {
           description "Ethernet cross-connect";
         }
         enum "flexible-ethernet-services" {
           description "Allows per-unit Ethernet encapsulation configuration";
         }
         enum "smds-dxi" {
           description "SMDS DXI framing";
         }
         enum "atm-pvc" {
           description "ATM permanent virtual circuits";
         }
         enum "atm-ccc-cell-relay" {
           description "ATM cell relay encapsulation for cross-connect";
         }
         enum "ethernet-over-atm" {
           description "Ethernet over ATM encapsulation";
         }
         enum "ethernet-tcc" {
           description "Ethernet translational cross-connect";
         }
         enum "extended-vlan-tcc" {
           description "802.1q tagging for a translational cross-connect";
         }
         enum "multilink-frame-relay-uni-nni" {
           description "Multilink Frame Relay UNI NNI (FRF.16) encapsulation";
         }
         enum "satop" {
           description "Structure-Agnostic TDM over Packet encapsulation";
         }
         enum "cesopsn" {
           description "Structure-Agnostic TDM over Packet encapsulation";
         }
         enum "ima" {
           description "Inverse Multiplexing for ATM";
         }
         enum "ethernet-vpls" {
           description "Ethernet virtual private LAN service";
         }
         enum "ethernet-bridge" {
           description "Ethernet layer-2 bridging";
         }
         enum "vlan-vpls" {
           description "VLAN virtual private LAN service";
         }
         enum "vlan-vci-ccc" {
           description "CCC for VLAN Q-in-Q and ATM VPI/VCI interworking";
         }
         enum "extended-vlan-vpls" {
           description "Extended VLAN virtual private LAN service";
         }
         enum "extended-vlan-bridge" {
           description "VLAN layer-2 bridging";
         }
         enum "multilink-ppp" {
           description "Multilink PPP";
         }
         enum "generic-services" {
           description "Generic services";
         }
       }
     }
     container esi {
       description "ESI configuration of multi-homed interface";
       uses apply-advanced;
       leaf identifier {
         description "ESI value for the interface";
         type jt:esi;
       }
       choice mode {
         case case_1 {
           leaf single-active {
             description "Single-active mode";
             type empty;
           }
         }
         case case_2 {
           leaf all-active {
             description "All-active mode";
             type empty;
           }
         }
       }
       leaf source-bmac {
         description "Unicast Source B-MAC address per ESI for PBB-EVPN";
         type jt:mac-unicast;
       }
     }
     container framing {
       description "Frame type";
       uses apply-advanced;
       choice frame {
         case case_1 {
           leaf lan-phy {
             description "802.3ae 10-Gbps LAN-mode interface";
             type empty;
           }
         }
         case case_2 {
           leaf wan-phy {
             description "802.3ae 10-Gbps WAN-mode interface";
             type empty;
           }
         }
         case case_3 {
           leaf sonet {
             description "SONET framing";
             type empty;
           }
         }
         case case_4 {
           leaf sdh {
             description "SDH framing";
             type empty;
           }
         }
       }
     }
     container lmi {
       description "Local Management Interface settings";
       uses apply-advanced;
       leaf n391dte {
         description "DTE full status polling interval";
         type union {
           type string {
             pattern "<.*>|$.*";
           }
           type uint16 {
             range "1 .. 255";
           }
         }
       }
       leaf n392dce {
         description "DCE error threshold";
         type union {
           type string {
             pattern "<.*>|$.*";
           }
           type uint16 {
             range "1 .. 10";
           }
         }
       }
       leaf n392dte {
         description "DTE error threshold";
         type union {
           type string {
             pattern "<.*>|$.*";
           }
           type uint16 {
             range "1 .. 10";
           }
         }
       }
       leaf n393dce {
         description "DCE monitored event count";
         type union {
           type string {
             pattern "<.*>|$.*";
           }
           type uint16 {
             range "1 .. 10";
           }
         }
       }
       leaf n393dte {
         description "DTE monitored event count";
         type union {
           type string {
             pattern "<.*>|$.*";
           }
           type uint16 {
             range "1 .. 10";
           }
         }
       }
       leaf t391dte {
         description "DTE polling timer";
         units "seconds";
         type union {
           type string {
             pattern "<.*>|$.*";
           }
           type uint16 {
             range "5 .. 30";
           }
         }
       }
       leaf t392dce {
         description "DCE polling verification timer";
         units "seconds";
         type union {
           type string {
             pattern "<.*>|$.*";
           }
           type uint16 {
             range "5 .. 30";
           }
         }
       }
       leaf lmi-type {
         description "Specify the Frame Relay LMI type";
         type enumeration {
           enum "ansi" {
             description "Use ANSI Annex D LMI";
           }
           enum "itu" {
             description "Use ITU Q933a Annex A LMI";
           }
           enum "c-lmi" {
             description "Use Consortium LMI";
           }
         }
       }
     }
     container mlfr-uni-nni-bundle-options {
       description "Multilink Frame Relay UNI NNI (FRF.16) management settings";
       uses apply-advanced;
       container cisco-interoperability {
         description "FRF.16 Cisco interoperability settings";
         uses apply-advanced;
         leaf send-lip-remove-link-for-link-reject {
           description "Send Link Integrity Protocol remove link on receiving add-link rejection";
           type empty;
         }
       }
       leaf mrru {
         description "Maximum received reconstructed unit";
         units "bytes";
         type union {
           type string {
             pattern "<.*>|$.*";
           }
           type uint16 {
             range "1500 .. 4500";
           }
         }
       }
       leaf yellow-differential-delay {
         description "Yellow differential delay among bundle links to give warning";
         units "milliseconds";
         type union {
           type string {
             pattern "<.*>|$.*";
           }
           type uint16 {
             range "3 .. 2000";
           }
         }
       }
       leaf red-differential-delay {
         description "Red differential delay among bundle links to take action";
         units "milliseconds";
         type union {
           type string {
             pattern "<.*>|$.*";
           }
           type uint16 {
             range "5 .. 2000";
           }
         }
       }
       leaf action-red-differential-delay {
         description "Type of actions when differential delay exceeds red limit";
         type enumeration {
           enum "remove-link" {
             description "Remove bundle link from service when exceeding red limit";
           }
           enum "disable-tx" {
             description "Disable transfer of bundle link when exceeding red limit";
           }
         }
       }
       leaf fragment-threshold {
         description "Fragmentation threshold";
         units "bytes";
         type union {
           type string {
             pattern "<.*>|$.*";
           }
           type uint32 {
             range "64 .. 16320";
           }
         }
       }
       leaf drop-timeout {
         description "Drop timeout";
         units "milliseconds";
         type union {
           type string {
             pattern "<.*>|$.*";
           }
           type uint16 {
             range "0 .. 2000";
           }
         }
       }
       leaf link-layer-overhead {
         description "Link layer bit stuffing overhead (0.0 .. 50.0 percent)";
         type jt:unsigned-float;
       }
       leaf lmi-type {
         description "Specify the multilink Frame Relay UNI NNI LMI type";
         type enumeration {
           enum "ansi" {
             description "Use ANSI Annex D LMI";
           }
           enum "itu" {
             description "Use ITU Q933a Annex A LMI";
           }
           enum "c-lmi" {
             description "Use Consortium LMI";
           }
         }
       }
       leaf minimum-links {
         description "Minimum number of links to sustain the bundle";
         type union {
           type string {
             pattern "<.*>|$.*";
           }
           type uint16 {
             range "1 .. 8";
           }
         }
       }
       leaf hello-timer {
         description "LIP hello timer";
         type union {
           type string {
             pattern "<.*>|$.*";
           }
           type uint16 {
             range "5 .. 180";
           }
         }
       }
       leaf acknowledge-timer {
         description "LIP ack timer";
         type union {
           type string {
             pattern "<.*>|$.*";
           }
           type uint16 {
             range "1 .. 10";
           }
         }
       }
       leaf acknowledge-retries {
         description "LIP ack retry times";
         type union {
           type string {
             pattern "<.*>|$.*";
           }
           type uint16 {
             range "1 .. 5";
           }
         }
       }
       leaf n391 {
         description "Multilink Frame Relay UNI NNI full status polling counter";
         type union {
           type string {
             pattern "<.*>|$.*";
           }
           type uint16 {
             range "1 .. 255";
           }
         }
       }
       leaf n392 {
         description "Multilink Frame Relay UNI NNI LMI error threshold";
         type union {
           type string {
             pattern "<.*>|$.*";
           }
           type uint16 {
             range "1 .. 10";
           }
         }
       }
       leaf n393 {
         description "Multilink Frame Relay UNI NNI LMI monitored event count";
         type union {
           type string {
             pattern "<.*>|$.*";
           }
           type uint16 {
             range "1 .. 10";
           }
         }
       }
       leaf t391 {
         description "Multilink Frame Relay UNI NNI link integrity verify polling timer";
         type union {
           type string {
             pattern "<.*>|$.*";
           }
           type uint16 {
             range "5 .. 30";
           }
         }
       }
       leaf t392 {
         description "Multilink Frame Relay UNI NNI polling verification timer";
         type union {
           type string {
             pattern "<.*>|$.*";
           }
           type uint16 {
             range "5 .. 30";
           }
         }
       }
     }
     leaf mac {
       description "Hardware MAC address";
       type jt:mac-unicast;
     }
     container receive-bucket {
       description "Set receive bucket parameters";
       uses dcd_rx_bucket_config;
     }
     container transmit-bucket {
       description "Set transmit bucket parameters";
       uses dcd_tx_bucket_config;
     }
     leaf shared-interface {
       description "Enable shared interface on the interface";
       type empty;
     }
     container sonet-options {
       description "SONET interface-specific options";
       uses sonet_options_type;
     }
     container logical-tunnel-options {
       description "Logical Tunnel interface-specific options";
       uses apply-advanced;
       container link-protection {
         presence "enable link-protection";
         description "Enable link protection mode";
         uses apply-advanced;
         leaf revertive {
           description "Revert back (Default mode) from active backup link to primary, if primary is UP";
           type empty;
         }
         leaf non-revertive {
           description "Do not revert back from active backup link to primary, if primary is UP";
           type empty;
         }
       }
       leaf per-unit-mac-disable {
         description "Disable the creation of per unit mac address on LT IFLs for VPLS/CCC encaps";
         type empty;
       }
     }
     container aggregated-sonet-options {
       description "Aggregated SONET interface-specific options";
       uses apply-advanced;
       leaf minimum-links {
         description "Minimum number of aggregated links";
         type union {
           type string {
             pattern "<.*>|$.*";
           }
           type uint16;
         }
       }
       leaf link-speed {
         description "Aggregated links speed";
         type enumeration {
           enum "oc3" {
             description "Links are OC-3c or STM-1c";
           }
           enum "oc12" {
             description "Links are OC-12c or STM-4c";
           }
           enum "oc48" {
             description "Links are OC-48c or STM-16c";
           }
           enum "oc192" {
             description "Links are OC-192c or STM-64c";
           }
           enum "oc768" {
             description "Links are OC-768c or STM-256c";
           }
           enum "mixed" {
             description "Links are various speeds";
           }
         }
       }
       leaf minimum-bandwidth {
         description "Minimum bandwidth necessary to sustain bundle";
         units "bps";
         type union {
           type string {
             pattern "<.*>|$.*";
           }
           type uint64 {
             range "0 .. 159232000000";
           }
         }
       }
     }
     container atm-options {
       description "ATM interface-specific options";
       uses apply-advanced;
       leaf pic-type {
         description "Type of ATM PIC (ATM I, ATM II or ATM CE)";
         type enumeration {
           enum "atm-ce" {
             description "CE PIC";
           }
           enum "atm2" {
             description "ATM II IQ PIC";
           }
           enum "atm1" {
             description "ATM I PIC";
           }
         }
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf use-null-cw {
         description "Always insert/strip null control words with cell-relay";
         type empty;
       }
       container promiscuous-mode {
         presence "enable promiscuous-mode";
         description "Set ATM interface to promiscuous mode";
         uses apply-advanced;
         list vpi {
           key name;
           ordered-by user;
           description "Open this VPI in promiscuous mode";
           leaf name {
             description "Virtual path index";
             type union {
               type string {
                 pattern "<.*>|$.*";
               }
               type uint32 {
                 range "0 .. 255";
               }
             }
           }
         }
       }
       list vpi {
         key name;
         ordered-by user;
         description "Define a virtual path";
         leaf name {
           description "Virtual path index";
           type union {
             type string {
               pattern "<.*>|$.*";
             }
             type uint32 {
               range "0 .. 255";
             }
           }
         }
         uses apply-advanced;
         leaf maximum-vcs {
           description "Maximum number of virtual circuits on this VP";
           type union {
             type uint32;
             type string {
               pattern "<.*>|$.*";
             }
           }
         }
         container shaping {
           description "Virtual path traffic-shaping options";
           uses dcd_shaping_config;
         }
         container oam-period {
           description "F4 OAM cell period";
           choice oam_period_choices {
             case case_1 {
               leaf oam-period {
                 description "F4 OAM cell period";
                 units "seconds";
                 type union {
                   type string {
                     pattern "<.*>|$.*";
                   }
                   type uint32 {
                     range "1 .. 900";
                   }
                 }
               }
             }
             case case_2 {
               container disable {
                 presence "enable disable";
                 description "Disable F4 OAM loopback";
               }
             }
           }
         }
         container oam-liveness {
           description "F4 OAM virtual path liveness parameters";
           uses apply-advanced;
           leaf up-count {
             description "Number of F4 OAM cells to consider VP up";
             type union {
               type string {
                 pattern "<.*>|$.*";
               }
               type uint32 {
                 range "1 .. 255";
               }
             }
           }
           leaf down-count {
             description "Number of F4 OAM cells to consider VP down";
             type union {
               type string {
                 pattern "<.*>|$.*";
               }
               type uint32 {
                 range "1 .. 255";
               }
             }
           }
         }
       }
       container ilmi {
         presence "enable ilmi";
         description "Enable Interim Local Management Interface";
         uses apply-advanced;
       }
       list linear-red-profiles {
         key name;
         ordered-by user;
         description "ATM2 CoS virtual circuit drop profiles";
         leaf name {
           description "Linear RED profile name";
           type string {
           }
         }
         leaf queue-depth {
           description "Maximum queue depth";
           units "cells";
           type string;
         }
         leaf high-plp-threshold {
           description "Fill level percentage when linear RED is applied for high PLP";
           type union {
             type string {
               pattern "<.*>|$.*";
             }
             type uint32 {
               range "0 .. 100";
             }
           }
         }
         leaf low-plp-threshold {
           description "Fill level percentage when linear RED is applied for low PLP";
           type union {
             type string {
               pattern "<.*>|$.*";
             }
             type uint32 {
               range "0 .. 100";
             }
           }
         }
         leaf high-plp-max-threshold {
           description "Fill level percentage with 100 percent packet drop for high PLP";
           type union {
             type string {
               pattern "<.*>|$.*";
             }
             type uint32 {
               range "0 .. 100";
             }
           }
         }
         leaf low-plp-max-threshold {
           description "Fill level percentage with 100 percent packet drop for low PLP";
           type union {
             type string {
               pattern "<.*>|$.*";
             }
             type uint32 {
               range "0 .. 100";
             }
           }
         }
       }
       list scheduler-maps {
         key name;
         ordered-by user;
         description "ATM2 CoS parameters assigned to forwarding classes";
         leaf name {
           description "ATM2 CoS scheduler map name";
           type string {
           }
         }
         uses apply-advanced;
         leaf vc-cos-mode {
           description "ATM2 virtual circuit CoS mode";
           type enumeration {
             enum "strict" {
               description "Always schedule high priority queue first";
             }
             enum "alternate" {
               description "Every other packet from high priority queue (default)";
             }
           }
         }
         list forwarding-class {
           key name;
           ordered-by user;
           description "Scheduling parameters associated with forwarding class";
           leaf name {
             description "Forwarding class name";
             type string {
             }
           }
           uses apply-advanced;
           leaf priority {
             description "Queuing priority assigned to forwarding class";
             type enumeration {
               enum "low" {
                 description "Low priority queuing";
               }
               enum "high" {
                 description "High priority queuing";
               }
             }
           }
           container transmit-weight {
             description "Transmit weight";
             choice weight-method {
               case case_1 {
                 leaf percent {
                   description "Transmit weight as percentage";
                   type union {
                     type string {
                       pattern "<.*>|$.*";
                     }
                     type uint32 {
                       range "5 .. 100";
                     }
                   }
                 }
               }
               case case_2 {
                 leaf cells {
                   description "Transmit weight by cells count";
                   type string;
                 }
               }
             }
           }
           choice drop-profile-method {
             case case_1 {
               container epd-threshold {
                 description "Early packet discard threshold for ATM2";
                 uses epd_threshold_config;
               }
             }
             case case_2 {
               leaf linear-red-profile {
                 description "Linear RED profile profile name";
                 type string;
               }
             }
           }
         }
       }
       container mpls {
         description "MPLS options";
         uses mpls_ifd_options;
       }
       choice payload-scrambler-choice {
         leaf payload-scrambler {
           description "Enable payload scrambling";
           type empty;
         }
         leaf no-payload-scrambler {
           description "Don't enable payload scrambling";
           type empty;
         }
       }
     }
     container multiservice-options {
       description "Multiservice interface-specific options";
       uses apply-advanced;
       choice syslog-choice {
         leaf syslog {
           description "Enable system logging on this interface";
           type empty;
         }
         leaf no-syslog {
           description "Don't enable system logging on this interface";
           type empty;
         }
       }
       choice core-dump-choice {
         leaf core-dump {
           description "Enable core dumping on this interface";
           type empty;
         }
         leaf no-core-dump {
           description "Don't enable core dumping on this interface";
           type empty;
         }
       }
       choice dump-on-flow-control-choice {
         leaf dump-on-flow-control {
           description "Enable dumping for this interface on prolonged flow-control";
           status deprecated;
           type empty;
         }
         leaf no-dump-on-flow-control {
           description "Don't enable dumping for this interface on prolonged flow-control";
           status deprecated;
           type empty;
         }
       }
       choice reset-on-flow-control-choice {
         leaf reset-on-flow-control {
           description "Enable resetting this interface on prolonged flow-control";
           status deprecated;
           type empty;
         }
         leaf no-reset-on-flow-control {
           description "Don't enable resetting this interface on prolonged flow-control";
           status deprecated;
           type empty;
         }
       }
       container flow-control-options {
         description "Flow control configuration";
         uses apply-advanced;
         leaf dump-on-flow-control {
           description "Cause core dump during prolonged flow-control";
           type empty;
         }
         leaf reset-on-flow-control {
           description "Reset interface during prolonged flow-control";
           type empty;
         }
         leaf down-on-flow-control {
           description "Bring interface down during prolonged flow-control";
           type empty;
         }
       }
     }
     container ggsn-options {
       description "GGSN interface-specific options";
       uses apply-advanced;
       choice syslog-choice {
         leaf syslog {
           description "Enable system logging on this interface";
           type empty;
         }
         leaf no-syslog {
           description "Don't enable system logging on this interface";
           type empty;
         }
       }
       choice core-dump-choice {
         leaf core-dump {
           description "Enable core dumping on this interface";
           type empty;
         }
         leaf no-core-dump {
           description "Don't enable core dumping on this interface";
           type empty;
         }
       }
     }
     container ppp-options {
       description "Point-to-Point Protocol (PPP) interface-specific options";
       uses ppp_options_type;
     }
     container redundancy-options {
       description "Redundancy options";
       uses apply-advanced;
       leaf primary {
         description "Specify the primary interface";
         type union {
           type jt:interface-device;
           type string {
             pattern "<.*>|$.*";
           }
         }
       }
       leaf secondary {
         description "Specify the secondary interface";
         type union {
           type jt:interface-device;
           type string {
             pattern "<.*>|$.*";
           }
         }
       }
       container redundancy-peer {
         description "Specify information for peer";
         uses apply-advanced;
         leaf ipaddress {
           description "Specify the IP address";
           type jt:ipv4addr;
         }
       }
       container redundancy-local {
         description "Specify information for the local peer";
         uses apply-advanced;
         leaf data-address {
           description "Specify the HA local data IP address";
           type jt:ipv4addr;
         }
       }
       leaf routing-instance {
         description "Specify routing-instance for the HA traffic";
         type string;
       }
       leaf replication-threshold {
         description "Duration for which flow should remain active for replication";
         default "180";
         units "seconds";
         type union {
           type string {
             pattern "<.*>|$.*";
           }
           type uint32 {
             range "60 .. 3600";
           }
         }
       }
       container replication-options {
         description "Specify state replication attributes";
         uses apply-advanced;
         leaf mtu {
           description "Specify the maximal packet size for replicated data";
           default "1500";
           type union {
             type string {
               pattern "<.*>|$.*";
             }
             type uint32 {
               range "1500 .. 8000";
             }
           }
         }
       }
       container replicate-services {
         description "Replicate services state from active to backup";
         uses apply-advanced;
         leaf pgcp {
           description "Replicate the PGCP service state";
           type empty;
         }
       }
     }
     container lsq-failure-options {
       description "Link services queuing failure options";
       uses apply-advanced;
       list trigger-link-failure {
         key name;
         ordered-by user;
         description "Link on which to trigger failure";
         leaf name {
           description "Interface name";
           type union {
             type jt:interface-device;
             type string {
               pattern "<.*>|$.*";
             }
           }
         }
         uses apply-advanced;
       }
       choice no-termination-request-choice {
         leaf no-termination-request {
           description "Do not send PPP termination requests";
           type empty;
         }
         leaf no-no-termination-request {
           description "Don't do not send PPP termination requests";
           type empty;
         }
       }
     }
     container services-options {
       description "Services interface-specific options";
       uses apply-advanced;
       container syslog {
         description "Define system log parameters";
         uses service_set_syslog_object;
       }
       container jflow-log {
         description "Define Jflow-log parameters.";
         uses apply-advanced;
         leaf message-rate-limit {
           description "Maximum jflow-log NAT error events allowed per second from this interface";
           units "messages per second";
           type union {
             type string {
               pattern "<.*>|$.*";
             }
             type uint32 {
               range "1 .. 2147483647";
             }
           }
         }
       }
       container deterministic-nat-configuration-log-interval {
         presence "enable deterministic-nat-configuration-log-interval";
         description "Define Deterministic NAT parameters";
         uses apply-advanced;
         leaf interval {
           description "Interval in which deterministic NAT logs are generated";
           units "seconds";
           type union {
             type string {
               pattern "<.*>|$.*";
             }
             type uint32 {
               range "1800 .. 86400";
             }
           }
         }
       }
       leaf open-timeout {
         description "Timeout period for TCP session establishment";
         units "seconds";
         type union {
           type string {
             pattern "<.*>|$.*";
           }
           type uint32 {
             range "4 .. 300";
           }
         }
       }
       leaf close-timeout {
         description "Timeout period for TCP session tear-down";
         units "seconds";
         type union {
           type string {
             pattern "<.*>|$.*";
           }
           type uint32 {
             range "2 .. 300";
           }
         }
       }
       leaf inactivity-timeout {
         description "Inactivity timeout period for established sessions (4..86400)";
         units "seconds";
         type union {
           type uint32;
           type string {
             pattern "<.*>|$.*";
           }
         }
       }
       leaf inactivity-tcp-timeout {
         description "Inactivity timeout period for TCP established sessions";
         units "seconds";
         type union {
           type string {
             pattern "<.*>|$.*";
           }
           type uint32 {
             range "4 .. 86400";
           }
         }
       }
       leaf inactivity-asymm-tcp-timeout {
         description "Inactivity timeout period for asymmetric TCP established sessions";
         units "seconds";
         type union {
           type string {
             pattern "<.*>|$.*";
           }
           type uint32 {
             range "4 .. 86400";
           }
         }
       }
       leaf inactivity-non-tcp-timeout {
         description "Inactivity timeout period for non-TCP established sessions";
         units "seconds";
         type union {
           type string {
             pattern "<.*>|$.*";
           }
           type uint32 {
             range "4 .. 86400";
           }
         }
       }
       leaf session-timeout {
         description "Session timeout period for established sessions";
         units "seconds";
         type union {
           type string {
             pattern "<.*>|$.*";
           }
           type uint32 {
             range "4 .. 86400";
           }
         }
       }
       leaf disable-global-timeout-override {
         description "Disallow overriding  global inactivity or session timeout";
         type empty;
       }
       leaf tcp-tickles {
         description "Number of TCP keep-alive packets to be sent for bi-directional TCP flows";
         default "4";
         type union {
           type string {
             pattern "<.*>|$.*";
           }
           type uint8 {
             range "0 .. 30";
           }
         }
       }
       leaf fragment-limit {
         description "Maximum number of fragments allowed for a packet";
         default "250";
         type union {
           type string {
             pattern "<.*>|$.*";
           }
           type uint8 {
             range "1 .. 250";
           }
         }
       }
       leaf reassembly-timeout {
         description "Re-assembly timeout (seconds) for fragments of a packet";
         default "4";
         units "seconds";
         type union {
           type string {
             pattern "<.*>|$.*";
           }
           type uint8 {
             range "1 .. 60";
           }
         }
       }
       leaf cgn-pic {
         description "PIC will be used for Carrier Grade NAT configuration only";
         type empty;
       }
       leaf pba-interim-logging-interval {
         description "Interim logging interval in seconds";
         default "0";
         units "seconds";
         type union {
           type string {
             pattern "<.*>|$.*";
           }
           type uint32 {
             range "0 .. 86400";
           }
         }
       }
       container session-limit {
         presence "enable session-limit";
         description "Session limit";
         uses apply-advanced;
         leaf maximum {
           description "Maximum number of sessions allowed simultaneously";
           type string;
         }
         leaf rate {
           description "Maximum number of new sessions allowed per second";
           type string;
         }
         leaf cpu-load-threshold {
           description "CPU limit in percentage for auto-tuning of session rate";
           units "percent";
           type union {
             type string {
               pattern "<.*>|$.*";
             }
             type uint8 {
               range "1 .. 100";
             }
           }
         }
       }
       container ignore-errors {
         presence "enable ignore-errors";
         description "Ignore anomalies or errors";
         leaf tcp {
           description "TCP protocol errors";
           type empty;
         }
         leaf alg {
           description "ALG anomalies or errors";
           type empty;
         }
       }
       container capture {
         description "Packet capture for SFW and NAT on the Services PIC";
         uses apply-advanced;
         leaf capture-size {
           description "The number of packets to store";
           type union {
             type string {
               pattern "<.*>|$.*";
             }
             type uint32 {
               range "1 .. 344000";
             }
           }
         }
         leaf pkt-size {
           description "Number of bytes to be saved from each packet";
           type union {
             type string {
               pattern "<.*>|$.*";
             }
             type uint16 {
               range "64 .. 15000";
             }
           }
         }
         leaf logs-per-packet {
           description "The number of trace messages stored for each packet";
           type union {
             type string {
               pattern "<.*>|$.*";
             }
             type uint16 {
               range "0 .. 500";
             }
           }
         }
         leaf max-log-line-size {
           description "The maximum length of a stored trace message";
           type union {
             type uint8;
             type string {
               pattern "<.*>|$.*";
             }
           }
         }
         container filter {
           presence "enable filter";
           description "Filtering options for the packet capture";
           uses apply-advanced;
           container source-ip {
             description "Filter based on source-ip (and wildcard)";
             leaf ip {
               description "Source IP";
               type jt:ipaddr;
             }
             leaf wildcard {
               description "Source IP wildcard";
               type jt:ipaddr;
             }
           }
           container dest-ip {
             description "Filter based on dest-ip (and wildcard)";
             leaf ip {
               description "Dest IP";
               type jt:ipaddr;
             }
             leaf wildcard {
               description "Dest IP wildcard";
               type jt:ipaddr;
             }
           }
           container sw-sip {
             description "Filter based on source softwire ip (and wildcard)";
             leaf ip {
               description "Source softwire IP";
               type jt:ipv6addr;
             }
             leaf wildcard {
               description "Source IP wildcard";
               type jt:ipv6addr;
             }
           }
           container sw-dip {
             description "Filter based on destination softwire ip (and wildcard)";
             leaf ip {
               description "Destination softwire IP";
               type jt:ipaddr;
             }
             leaf wildcard {
               description "Destination IP wildcard";
               type jt:ipaddr;
             }
           }
           container sport-range {
             description "Filter based on source port";
             leaf low {
               description "Source port range start";
               type union {
                 type uint16;
                 type string {
                   pattern "<.*>|$.*";
                 }
               }
             }
             leaf high {
               description "Source port range end";
               type union {
                 type uint16;
                 type string {
                   pattern "<.*>|$.*";
                 }
               }
             }
           }
           container dport-range {
             description "Filter based on destination port";
             leaf low {
               description "Destination port range start";
               type union {
                 type uint16;
                 type string {
                   pattern "<.*>|$.*";
                 }
               }
             }
             leaf high {
               description "Destination port range end";
               type union {
                 type uint16;
                 type string {
                   pattern "<.*>|$.*";
                 }
               }
             }
           }
           leaf proto {
             description "Filter based on L4 protocol";
             type enumeration {
               enum "icmp" {
               }
               enum "tcp" {
               }
               enum "udp" {
               }
             }
           }
         }
       }
     }
     container t3-options {
       description "T3 interface-specific options";
       uses apply-advanced;
       leaf loopback {
         description "Loopback mode";
         type enumeration {
           enum "local" {
             description "Local loopback";
           }
           enum "remote" {
             description "Remote loopback";
           }
           enum "payload" {
             description "Payload loopback";
           }
         }
       }
       choice long-buildout-choice {
         leaf long-buildout {
           description "Set hardware to drive line longer than 255 feet";
           type empty;
         }
         leaf no-long-buildout {
           description "Don't set hardware to drive line longer than 255 feet";
           type empty;
         }
       }
       choice loop-timing-choice {
         leaf loop-timing {
           description "Set loop timing for T3";
           type empty;
         }
         leaf no-loop-timing {
           description "Don't set loop timing for T3";
           type empty;
         }
       }
       container compatibility-mode {
         description "Set CSU compatibility mode";
         choice vendor {
           case case_1 {
             container larscom {
               presence "enable larscom";
               description "Compatible with Larscom CSU";
               leaf subrate {
                 description "Set subrate value";
                 type union {
                   type string {
                     pattern "<.*>|$.*";
                   }
                   type uint32 {
                     range "1 .. 14";
                   }
                 }
               }
             }
           }
           case case_2 {
             container verilink {
               presence "enable verilink";
               description "Compatible with Verilink CSU (not on 2/4-port T3 PIC)";
               leaf subrate {
                 description "Set subrate value";
                 type union {
                   type string {
                     pattern "<.*>|$.*";
                   }
                   type uint32 {
                     range "1 .. 28";
                   }
                 }
               }
             }
           }
           case case_3 {
             container adtran {
               presence "enable adtran";
               description "Compatible with Adtran CSU (not on 2/4-port T3 PIC)";
               leaf subrate {
                 description "Set subrate value";
                 type union {
                   type string {
                     pattern "<.*>|$.*";
                   }
                   type uint32 {
                     range "1 .. 588";
                   }
                 }
               }
             }
           }
           case case_4 {
             container kentrox {
               presence "enable kentrox";
               description "Compatible with Kentrox CSU";
               leaf subrate {
                 description "Set subrate value (not on 2/4-port T3 PIC)";
                 type union {
                   type string {
                     pattern "<.*>|$.*";
                   }
                   type uint32 {
                     range "1 .. 69";
                   }
                 }
               }
             }
           }
           case case_5 {
             container digital-link {
               presence "enable digital-link";
               description "Compatible with Digital Link CSU";
               leaf subrate {
                 description "Set subrate value";
                 type enumeration {
                   enum "301Kb" {
                     description "301 Kbps";
                   }
                   enum "601Kb" {
                     description "601 Kbps";
                   }
                   enum "902Kb" {
                     description "902 Kbps";
                   }
                   enum "1.2Mb" {
                     description "1.2 Mbps";
                   }
                   enum "1.5Mb" {
                     description "1.5 Mbps";
                   }
                   enum "1.8Mb" {
                     description "1.8 Mbps";
                   }
                   enum "2.1Mb" {
                     description "2.1 Mbps";
                   }
                   enum "2.4Mb" {
                     description "2.4 Mbps";
                   }
                   enum "2.7Mb" {
                     description "2.7 Mbps";
                   }
                   enum "3.0Mb" {
                     description "3.0 Mbps";
                   }
                   enum "3.3Mb" {
                     description "3.3 Mbps";
                   }
                   enum "3.6Mb" {
                     description "3.6 Mbps";
                   }
                   enum "3.9Mb" {
                     description "3.9 Mbps";
                   }
                   enum "4.2Mb" {
                     description "4.2 Mbps";
                   }
                   enum "4.5Mb" {
                     description "4.5 Mbps";
                   }
                   enum "4.8Mb" {
                     description "4.8 Mbps";
                   }
                   enum "5.1Mb" {
                     description "5.1 Mbps";
                   }
                   enum "5.4Mb" {
                     description "5.4 Mbps";
                   }
                   enum "5.7Mb" {
                     description "5.7 Mbps";
                   }
                   enum "6.0Mb" {
                     description "6.0 Mbps";
                   }
                   enum "6.3Mb" {
                     description "6.3 Mbps";
                   }
                   enum "6.6Mb" {
                     description "6.6 Mbps";
                   }
                   enum "6.9Mb" {
                     description "6.9 Mbps";
                   }
                   enum "7.2Mb" {
                     description "7.2 Mbps";
                   }
                   enum "7.5Mb" {
                     description "7.5 Mbps";
                   }
                   enum "7.8Mb" {
                     description "7.8 Mbps";
                   }
                   enum "8.1Mb" {
                     description "8.1 Mbps";
                   }
                   enum "8.4Mb" {
                     description "8.4 Mbps";
                   }
                   enum "8.7Mb" {
                     description "8.7 Mbps";
                   }
                   enum "9.0Mb" {
                     description "9.0 Mbps";
                   }
                   enum "9.3Mb" {
                     description "9.3 Mbps";
                   }
                   enum "9.6Mb" {
                     description "9.6 Mbps";
                   }
                   enum "9.9Mb" {
                     description "9.9 Mbps";
                   }
                   enum "10.2Mb" {
                     description "10.2 Mbps";
                   }
                   enum "10.5Mb" {
                     description "10.5 Mbps";
                   }
                   enum "10.8Mb" {
                     description "10.8 Mbps";
                   }
                   enum "11.1Mb" {
                     description "11.1 Mbps";
                   }
                   enum "11.4Mb" {
                     description "11.4 Mbps";
                   }
                   enum "11.7Mb" {
                     description "11.7 Mbps";
                   }
                   enum "12.0Mb" {
                     description "12.0 Mbps";
                   }
                   enum "12.3Mb" {
                     description "12.3 Mbps";
                   }
                   enum "12.6Mb" {
                     description "12.6 Mbps";
                   }
                   enum "12.9Mb" {
                     description "12.9 Mbps";
                   }
                   enum "13.2Mb" {
                     description "13.2 Mbps";
                   }
                   enum "13.5Mb" {
                     description "13.5 Mbps";
                   }
                   enum "13.8Mb" {
                     description "13.8 Mbps";
                   }
                   enum "14.1Mb" {
                     description "14.1 Mbps";
                   }
                   enum "14.4Mb" {
                     description "14.4 Mbps";
                   }
                   enum "14.7Mb" {
                     description "14.7 Mbps";
                   }
                   enum "15.0Mb" {
                     description "15.0 Mbps";
                   }
                   enum "15.3Mb" {
                     description "15.3 Mbps";
                   }
                   enum "15.6Mb" {
                     description "15.6 Mbps";
                   }
                   enum "15.9Mb" {
                     description "15.9 Mbps";
                   }
                   enum "16.2Mb" {
                     description "16.2 Mbps";
                   }
                   enum "16.5Mb" {
                     description "16.5 Mbps";
                   }
                   enum "16.8Mb" {
                     description "16.8 Mbps";
                   }
                   enum "17.1Mb" {
                     description "17.1 Mbps";
                   }
                   enum "17.4Mb" {
                     description "17.4 Mbps";
                   }
                   enum "17.7Mb" {
                     description "17.7 Mbps";
                   }
                   enum "18.0Mb" {
                     description "18.0 Mbps";
                   }
                   enum "18.3Mb" {
                     description "18.3 Mbps";
                   }
                   enum "18.6Mb" {
                     description "18.6 Mbps";
                   }
                   enum "18.9Mb" {
                     description "18.9 Mbps";
                   }
                   enum "19.2Mb" {
                     description "19.2 Mbps";
                   }
                   enum "19.5Mb" {
                     description "19.5 Mbps";
                   }
                   enum "19.8Mb" {
                     description "19.8 Mbps";
                   }
                   enum "20.1Mb" {
                     description "20.1 Mbps";
                   }
                   enum "20.5Mb" {
                     description "20.5 Mbps";
                   }
                   enum "20.8Mb" {
                     description "20.8 Mbps";
                   }
                   enum "21.1Mb" {
                     description "21.1 Mbps";
                   }
                   enum "21.4Mb" {
                     description "21.4 Mbps";
                   }
                   enum "21.7Mb" {
                     description "21.7 Mbps";
                   }
                   enum "22.0Mb" {
                     description "22.0 Mbps";
                   }
                   enum "22.3Mb" {
                     description "22.3 Mbps";
                   }
                   enum "22.6Mb" {
                     description "22.6 Mbps";
                   }
                   enum "22.9Mb" {
                     description "22.9 Mbps";
                   }
                   enum "23.2Mb" {
                     description "23.2 Mbps";
                   }
                   enum "23.5Mb" {
                     description "23.5 Mbps";
                   }
                   enum "23.8Mb" {
                     description "23.8 Mbps";
                   }
                   enum "24.1Mb" {
                     description "24.1 Mbps";
                   }
                   enum "24.4Mb" {
                     description "24.4 Mbps";
                   }
                   enum "24.7Mb" {
                     description "24.7 Mbps";
                   }
                   enum "25.0Mb" {
                     description "25.0 Mbps";
                   }
                   enum "25.3Mb" {
                     description "25.3 Mbps";
                   }
                   enum "25.6Mb" {
                     description "25.6 Mbps";
                   }
                   enum "25.9Mb" {
                     description "25.9 Mbps";
                   }
                   enum "26.2Mb" {
                     description "26.2 Mbps";
                   }
                   enum "26.5Mb" {
                     description "26.5 Mbps";
                   }
                   enum "26.8Mb" {
                     description "26.8 Mbps";
                   }
                   enum "27.1Mb" {
                     description "27.1 Mbps";
                   }
                   enum "27.4Mb" {
                     description "27.4 Mbps";
                   }
                   enum "27.7Mb" {
                     description "27.7 Mbps";
                   }
                   enum "28.0Mb" {
                     description "28.0 Mbps";
                   }
                   enum "28.3Mb" {
                     description "28.3 Mbps";
                   }
                   enum "28.6Mb" {
                     description "28.6 Mbps";
                   }
                   enum "28.9Mb" {
                     description "28.9 Mbps";
                   }
                   enum "29.2Mb" {
                     description "29.2 Mbps";
                   }
                   enum "29.5Mb" {
                     description "29.5 Mbps";
                   }
                   enum "29.8Mb" {
                     description "29.8 Mbps";
                   }
                   enum "30.1Mb" {
                     description "30.1 Mbps";
                   }
                   enum "30.4Mb" {
                     description "30.4 Mbps";
                   }
                   enum "30.7Mb" {
                     description "30.7 Mbps";
                   }
                   enum "31.0Mb" {
                     description "31.0 Mbps";
                   }
                   enum "31.3Mb" {
                     description "31.3 Mbps";
                   }
                   enum "31.6Mb" {
                     description "31.6 Mbps";
                   }
                   enum "31.9Mb" {
                     description "31.9 Mbps";
                   }
                   enum "32.2Mb" {
                     description "32.2 Mbps";
                   }
                   enum "32.5Mb" {
                     description "32.5 Mbps";
                   }
                   enum "32.8Mb" {
                     description "32.8 Mbps";
                   }
                   enum "33.1Mb" {
                     description "33.1 Mbps";
                   }
                   enum "33.4Mb" {
                     description "33.4 Mbps";
                   }
                   enum "33.7Mb" {
                     description "33.7 Mbps";
                   }
                   enum "34.0Mb" {
                     description "34.0 Mbps";
                   }
                   enum "34.3Mb" {
                     description "34.3 Mbps";
                   }
                   enum "34.6Mb" {
                     description "34.6 Mbps";
                   }
                   enum "34.9Mb" {
                     description "34.9 Mbps";
                   }
                   enum "35.2Mb" {
                     description "35.2 Mbps";
                   }
                   enum "35.5Mb" {
                     description "35.5 Mbps";
                   }
                   enum "35.8Mb" {
                     description "35.8 Mbps";
                   }
                   enum "36.1Mb" {
                     description "36.1 Mbps";
                   }
                   enum "36.4Mb" {
                     description "36.4 Mbps";
                   }
                   enum "36.7Mb" {
                     description "36.7 Mbps";
                   }
                   enum "37.0Mb" {
                     description "37.0 Mbps";
                   }
                   enum "37.3Mb" {
                     description "37.3 Mbps";
                   }
                   enum "37.6Mb" {
                     description "37.6 Mbps";
                   }
                   enum "37.9Mb" {
                     description "37.9 Mbps";
                   }
                   enum "38.2Mb" {
                     description "38.2 Mbps";
                   }
                   enum "38.5Mb" {
                     description "38.5 Mbps";
                   }
                   enum "38.8Mb" {
                     description "38.8 Mbps";
                   }
                   enum "39.1Mb" {
                     description "39.1 Mbps";
                   }
                   enum "39.4Mb" {
                     description "39.4 Mbps";
                   }
                   enum "39.7Mb" {
                     description "39.7 Mbps";
                   }
                   enum "40.0Mb" {
                     description "40.0 Mbps";
                   }
                   enum "40.3Mb" {
                     description "40.3 Mbps";
                   }
                   enum "40.6Mb" {
                     description "40.6 Mbps";
                   }
                   enum "40.9Mb" {
                     description "40.9 Mbps";
                   }
                   enum "41.2Mb" {
                     description "41.2 Mbps";
                   }
                   enum "41.5Mb" {
                     description "41.5 Mbps";
                   }
                   enum "41.8Mb" {
                     description "41.8 Mbps";
                   }
                   enum "42.1Mb" {
                     description "42.1 Mbps";
                   }
                   enum "42.4Mb" {
                     description "42.4 Mbps";
                   }
                   enum "42.7Mb" {
                     description "42.7 Mbps";
                   }
                   enum "43.0Mb" {
                     description "43.0 Mbps";
                   }
                   enum "43.3Mb" {
                     description "43.3 Mbps";
                   }
                   enum "43.6Mb" {
                     description "43.6 Mbps";
                   }
                   enum "43.9Mb" {
                     description "43.9 Mbps";
                   }
                   enum "44.2Mb" {
                     description "44.2 Mbps";
                   }
                 }
               }
             }
           }
         }
       }
       choice payload-scrambler-choice {
         leaf payload-scrambler {
           description "Enable payload scrambling";
           type empty;
         }
         leaf no-payload-scrambler {
           description "Don't enable payload scrambling";
           type empty;
         }
       }
       choice cbit-parity-choice {
         leaf cbit-parity {
           description "Enable C-bit parity mode";
           type empty;
         }
         leaf no-cbit-parity {
           description "Don't enable C-bit parity mode";
           type empty;
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       choice feac-loop-respond-choice {
         leaf feac-loop-respond {
           description "Respond to FEAC loop requests";
           type empty;
         }
         leaf no-feac-loop-respond {
           description "Don't respond to FEAC loop requests";
           type empty;
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
       leaf buildout {
         description "Line buildout";
         units "feet";
         type union {
           type string {
             pattern "<.*>|$.*";
           }
           type uint32 {
             range "0 .. 450";
           }
         }
       }
       leaf atm-encapsulation {
         description "DS-3 interface encapsulation";
         type enumeration {
           enum "plcp" {
             description "PLCP encapsulation";
           }
           enum "direct" {
             description "ATM direct mapping";
           }
         }
       }
     }
     container e3-options {
       description "E3 interface-specific options";
       uses apply-advanced;
       leaf loopback {
         description "Loopback mode";
         type enumeration {
           enum "local" {
             description "Local loopback";
           }
           enum "remote" {
             description "Remote loopback";
           }
         }
       }
       choice unframed-choice {
         leaf unframed {
           description "Enable unframed mode";
           type empty;
         }
         leaf no-unframed {
           description "Don't enable unframed mode";
           type empty;
         }
       }
       container compatibility-mode {
         description "Set CSU compatibility mode";
         choice vendor {
           case case_1 {
             leaf larscom {
               description "Compatible with Larscom CSU (only non IQ E3 interfaces)";
               type empty;
             }
           }
           case case_2 {
             container digital-link {
               presence "enable digital-link";
               description "Compatible with Digital Link CSU";
               leaf subrate {
                 description "Set subrate value";
                 type enumeration {
                   enum "358Kb" {
                     description "358 Kbps";
                   }
                   enum "716Kb" {
                     description "716 Kbps";
                   }
                   enum "1.1Mb" {
                     description "1.1 Mbps";
                   }
                   enum "1.4Mb" {
                     description "1.4 Mbps";
                   }
                   enum "1.8Mb" {
                     description "1.8 Mbps";
                   }
                   enum "2.1Mb" {
                     description "2.1 Mbps";
                   }
                   enum "2.5Mb" {
                     description "2.5 Mbps";
                   }
                   enum "2.9Mb" {
                     description "2.9 Mbps";
                   }
                   enum "3.2Mb" {
                     description "3.2 Mbps";
                   }
                   enum "3.6Mb" {
                     description "3.6 Mbps";
                   }
                   enum "3.9Mb" {
                     description "3.9 Mbps";
                   }
                   enum "4.3Mb" {
                     description "4.3 Mbps";
                   }
                   enum "4.7Mb" {
                     description "4.7 Mbps";
                   }
                   enum "5.0Mb" {
                     description "5.0 Mbps";
                   }
                   enum "5.4Mb" {
                     description "5.4 Mbps";
                   }
                   enum "5.7Mb" {
                     description "5.7 Mbps";
                   }
                   enum "6.1Mb" {
                     description "6.1 Mbps";
                   }
                   enum "6.4Mb" {
                     description "6.4 Mbps";
                   }
                   enum "6.8Mb" {
                     description "6.8 Mbps";
                   }
                   enum "7.2Mb" {
                     description "7.2 Mbps";
                   }
                   enum "7.5Mb" {
                     description "7.5 Mbps";
                   }
                   enum "7.9Mb" {
                     description "7.9 Mbps";
                   }
                   enum "8.2Mb" {
                     description "8.2 Mbps";
                   }
                   enum "8.6Mb" {
                     description "8.6 Mbps";
                   }
                   enum "9.0Mb" {
                     description "9.0 Mbps";
                   }
                   enum "9.3Mb" {
                     description "9.3 Mbps";
                   }
                   enum "9.7Mb" {
                     description "9.7 Mbps";
                   }
                   enum "10.0Mb" {
                     description "10.0 Mbps";
                   }
                   enum "10.4Mb" {
                     description "10.4 Mbps";
                   }
                   enum "10.7Mb" {
                     description "10.7 Mbps";
                   }
                   enum "11.1Mb" {
                     description "11.1 Mbps";
                   }
                   enum "11.5Mb" {
                     description "11.5 Mbps";
                   }
                   enum "11.8Mb" {
                     description "11.8 Mbps";
                   }
                   enum "12.2Mb" {
                     description "12.2 Mbps";
                   }
                   enum "12.5Mb" {
                     description "12.5 Mbps";
                   }
                   enum "12.9Mb" {
                     description "12.9 Mbps";
                   }
                   enum "13.2Mb" {
                     description "13.2 Mbps";
                   }
                   enum "13.6Mb" {
                     description "13.6 Mbps";
                   }
                   enum "14.0Mb" {
                     description "14.0 Mbps";
                   }
                   enum "14.3Mb" {
                     description "14.3 Mbps";
                   }
                   enum "14.7Mb" {
                     description "14.7 Mbps";
                   }
                   enum "15.0Mb" {
                     description "15.0 Mbps";
                   }
                   enum "15.4Mb" {
                     description "15.4 Mbps";
                   }
                   enum "15.8Mb" {
                     description "15.8 Mbps";
                   }
                   enum "16.1Mb" {
                     description "16.1 Mbps";
                   }
                   enum "16.5Mb" {
                     description "16.5 Mbps";
                   }
                   enum "16.8Mb" {
                     description "16.8 Mbps";
                   }
                   enum "17.2Mb" {
                     description "17.2 Mbps";
                   }
                   enum "17.5Mb" {
                     description "17.5 Mbps";
                   }
                   enum "17.9Mb" {
                     description "17.9 Mbps";
                   }
                   enum "18.3Mb" {
                     description "18.3 Mbps";
                   }
                   enum "18.6Mb" {
                     description "18.6 Mbps";
                   }
                   enum "19.0Mb" {
                     description "19.0 Mbps";
                   }
                   enum "19.3Mb" {
                     description "19.3 Mbps";
                   }
                   enum "19.7Mb" {
                     description "19.7 Mbps";
                   }
                   enum "20.0Mb" {
                     description "20.0 Mbps";
                   }
                   enum "20.4Mb" {
                     description "20.4 Mbps";
                   }
                   enum "20.8Mb" {
                     description "20.8 Mbps";
                   }
                   enum "21.1Mb" {
                     description "21.1 Mbps";
                   }
                   enum "21.5Mb" {
                     description "21.5 Mbps";
                   }
                   enum "21.8Mb" {
                     description "21.8 Mbps";
                   }
                   enum "22.2Mb" {
                     description "22.2 Mbps";
                   }
                   enum "22.6Mb" {
                     description "22.6 Mbps";
                   }
                   enum "22.9Mb" {
                     description "22.9 Mbps";
                   }
                   enum "23.3Mb" {
                     description "23.3 Mbps";
                   }
                   enum "23.6Mb" {
                     description "23.6 Mbps";
                   }
                   enum "24.0Mb" {
                     description "24.0 Mbps";
                   }
                   enum "24.3Mb" {
                     description "24.3 Mbps";
                   }
                   enum "24.7Mb" {
                     description "24.7 Mbps";
                   }
                   enum "25.1Mb" {
                     description "25.1 Mbps";
                   }
                   enum "25.4Mb" {
                     description "25.4 Mbps";
                   }
                   enum "25.8Mb" {
                     description "25.8 Mbps";
                   }
                   enum "26.1Mb" {
                     description "26.1 Mbps";
                   }
                   enum "26.5Mb" {
                     description "26.5 Mbps";
                   }
                   enum "26.9Mb" {
                     description "26.9 Mbps";
                   }
                   enum "27.2Mb" {
                     description "27.2 Mbps";
                   }
                   enum "27.6Mb" {
                     description "27.6 Mbps";
                   }
                   enum "27.9Mb" {
                     description "27.9 Mbps";
                   }
                   enum "28.3Mb" {
                     description "28.3 Mbps";
                   }
                   enum "28.6Mb" {
                     description "28.6 Mbps";
                   }
                   enum "29.0Mb" {
                     description "29.0 Mbps";
                   }
                   enum "29.4Mb" {
                     description "29.4 Mbps";
                   }
                   enum "29.7Mb" {
                     description "29.7 Mbps";
                   }
                   enum "30.1Mb" {
                     description "30.1 Mbps";
                   }
                   enum "30.4Mb" {
                     description "30.4 Mbps";
                   }
                   enum "30.8Mb" {
                     description "30.8 Mbps";
                   }
                   enum "31.1Mb" {
                     description "31.1 Mbps";
                   }
                   enum "31.5Mb" {
                     description "31.5 Mbps";
                   }
                   enum "31.9Mb" {
                     description "31.9 Mbps";
                   }
                   enum "32.2Mb" {
                     description "32.2 Mbps";
                   }
                   enum "32.6Mb" {
                     description "32.6 Mbps";
                   }
                   enum "32.9Mb" {
                     description "32.9 Mbps";
                   }
                   enum "33.3Mb" {
                     description "33.3 Mbps";
                   }
                   enum "33.7Mb" {
                     description "33.7 Mbps";
                   }
                   enum "34.0Mb" {
                     description "34.0 Mbps";
                   }
                 }
               }
             }
           }
           case case_3 {
             container kentrox {
               presence "enable kentrox";
               description "Compatible with Kentrox CSU";
               leaf subrate {
                 description "Set subrate value (only for E3 IQ interfaces)";
                 type union {
                   type string {
                     pattern "<.*>|$.*";
                   }
                   type uint32 {
                     range "1 .. 48";
                   }
                 }
               }
             }
           }
         }
       }
       choice payload-scrambler-choice {
         leaf payload-scrambler {
           description "Enable payload scrambling";
           type empty;
         }
         leaf no-payload-scrambler {
           description "Don't enable payload scrambling";
           type empty;
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf invert-data {
         description "Invert data";
         type empty;
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
       leaf buildout {
         description "Line buildout";
         units "feet";
         type union {
           type string {
             pattern "<.*>|$.*";
           }
           type uint32 {
             range "0 .. 450";
           }
         }
       }
       leaf atm-encapsulation {
         description "E3 interface encapsulation";
         type enumeration {
           enum "plcp" {
             description "PLCP encapsulation";
           }
           enum "direct" {
             description "ATM direct mapping";
           }
         }
       }
       leaf framing {
         description "E3 line format";
         type enumeration {
           enum "g.751" {
             description "G.751 format";
           }
           enum "g.832" {
             description "G.832 format";
           }
         }
       }
     }
     container e1-options {
       description "E1 interface-specific options";
       uses apply-advanced;
       leaf timeslots {
         description "Timeslots (1..32); for example, 1-4,6,9-11,32 (no space)";
         type string;
       }
       leaf loopback {
         description "Loopback mode";
         type enumeration {
           enum "local" {
             description "Local loopback";
           }
           enum "remote" {
             description "Remote loopback";
           }
         }
       }
       leaf framing {
         description "Framing mode";
         type enumeration {
           enum "g704" {
             description "G704 mode with CRC4";
           }
           enum "unframed" {
             description "Unframed mode";
           }
           enum "g704-no-crc4" {
             description "G704 mode without CRC4";
           }
         }
       }
       leaf fcs {
         description "Frame checksum";
         type enumeration {
           enum "32" {
             description "32-bit mode";
           }
           enum "16" {
             description "16-bit mode";
           }
         }
       }
       leaf invert-data {
         description "Invert data";
         type empty;
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 86400";
           }
         }
       }
     }
     container t1-options {
       description "T1 interface-specific options";
       uses apply-advanced;
       leaf timeslots {
         description "Timeslots (1..24; for example, 1-3,4,9,22-24 (no space)";
         type string;
       }
       leaf loopback {
         description "Loopback mode";
         type enumeration {
           enum "local" {
             description "Local loopback";
           }
           enum "remote" {
             description "Remote loopback";
           }
           enum "payload" {
             description "Payload loopback";
           }
         }
       }
       leaf buildout {
         description "Line buildout";
         type enumeration {
           enum "0-132" {
             description "Line buildout is between 0-132 feet";
           }
           enum "133-265" {
             description "Line buildout is between 133-265 feet";
           }
           enum "266-398" {
             description "Line buildout is between 266-398 feet";
           }
           enum "399-531" {
             description "Line buildout is between 399-531 feet";
           }
           enum "532-655" {
             description "Line buildout is between 532-655 feet";
           }
           enum "long-0db" {
             description "Long buildout with 0 dB transmit attenuation";
           }
           enum "long-7.5db" {
             description "Long buildout with 7.5 dB transmit attenuation";
           }
           enum "long-15db" {
             description "Long buildout with 15 dB transmit attenuation";
           }
           enum "long-22.5db" {
             description "Long buildout with 22.5 dB transmit attenuation";
           }
         }
       }
       leaf byte-encoding {
         description "Byte encoding";
         type enumeration {
           enum "nx64" {
             description "8 bits per byte";
           }
           enum "nx56" {
             description "7 bits per byte";
           }
         }
       }
       leaf line-encoding {
         description "Line encoding";
         type enumeration {
           enum "ami" {
             description "Automatic mark inversion";
           }
           enum "b8zs" {
             description "8-bit zero suppression";
           }
         }
       }
       leaf invert-data {
         description "Invert data";
         type empty;
       }
       leaf framing {
         description "Framing mode";
         type enumeration {
           enum "sf" {
             description "Super frame";
           }
           enum "esf" {
             description "Extended super frame";
           }
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 86400";
           }
         }
       }
       leaf remote-loopback-respond {
         description "Respond to loop requests from remote end";
         type empty;
       }
       leaf crc-major-alarm-threshold {
         description "CRC Major alarm threshold value";
         default "5e-5";
         type enumeration {
           enum "1e-3" {
             description "1 crc error in 10^3 bits";
           }
           enum "5e-4" {
             description "5 crc errors in 10^4 bits";
           }
           enum "1e-4" {
             description "1 crc error in 10^4 bits";
           }
           enum "5e-5" {
             description "5 crc errors in 10^5 bits";
           }
           enum "1e-5" {
             description "1 crc error in 10^5 bits";
           }
         }
       }
       leaf crc-minor-alarm-threshold {
         description "CRC Minor alarm threshold value";
         default "5e-6";
         type enumeration {
           enum "1e-3" {
             description "1 crc error in 10^3 bits";
           }
           enum "5e-4" {
             description "5 crc errors in 10^4 bits";
           }
           enum "1e-4" {
             description "1 crc error in 10^4 bits";
           }
           enum "5e-5" {
             description "5 crc errors in 10^5 bits";
           }
           enum "1e-5" {
             description "1 crc error in 10^5 bits";
           }
           enum "5e-6" {
             description "5 crc errors in 10^6 bits";
           }
           enum "1e-6" {
             description "1 crc error in 10^6 bits";
           }
         }
       }
     }
     container ds0-options {
       description "DS-0 interface-specific options";
       uses apply-advanced;
       leaf loopback {
         description "Loopback mode";
         type enumeration {
           enum "payload" {
             description "Payload loopback";
           }
         }
       }
       leaf byte-encoding {
         description "Byte encoding";
         type enumeration {
           enum "nx64" {
             description "8 bits per byte";
           }
           enum "nx56" {
             description "7 bits per byte";
           }
         }
       }
       leaf invert-data {
         description "Invert data";
         type empty;
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e11-o152" {
             description "Pattern is 2^11 -1 (per O.152 standard)";
           }
           enum "pseudo-2e15-o151" {
             description "Pattern is 2^15 - 1 (per O.151 standard)";
           }
           enum "pseudo-2e20-o153" {
             description "Pattern is 2^20 - 1 (per O.153 standard)";
           }
           enum "pseudo-2e20-o151" {
             description "Pattern is 2^20 - 1 (per O.151 standard)";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
           enum "repeating-1-in-16" {
             description "1 bit in 16 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
     }
     container serial-options {
       description "Serial interface-specific options";
       uses apply-advanced;
       leaf line-protocol {
         description "Line protocol to be used";
         default "eia530";
         type enumeration {
           enum "eia530" {
             description "Line protocol EIA530";
           }
           enum "v.35" {
             description "Line protocol V.35";
           }
           enum "x.21" {
             description "Line protocol X.21";
           }
         }
       }
       choice control_leads_choice {
         case case_1 {
           container dte-options {
             description "DTE options/control leads";
             uses apply-advanced;
             leaf ignore-all {
               description "Ignore all control leads";
               type empty;
             }
             container dtr {
               description "Data Transmit Ready signal handling";
               choice dtr_choices {
                 case case_1 {
                   leaf assert {
                     description "Assert DTR signal";
                     type empty;
                   }
                 }
                 case case_2 {
                   leaf de-assert {
                     description "Deassert DTR signal";
                     type empty;
                   }
                 }
                 case case_3 {
                   leaf normal {
                     description "Normal DTR signal";
                     type empty;
                   }
                 }
                 case case_4 {
                   container auto-synchronize {
                     presence "enable auto-synchronize";
                     description "Normal DTR signal, with autoresynchronization";
                     uses apply-advanced;
                     leaf duration {
                       description "Duration of autoresynchronization";
                       units "milliseconds";
                       type union {
                         type string {
                           pattern "<.*>|$.*";
                         }
                         type uint16 {
                           range "1 .. 1000";
                         }
                       }
                     }
                     leaf interval {
                       description "Interval for autoresynchronization";
                       units "seconds";
                       type union {
                         type string {
                           pattern "<.*>|$.*";
                         }
                         type uint16 {
                           range "1 .. 31";
                         }
                       }
                     }
                   }
                 }
               }
             }
             leaf control-signal {
               description "X.21 control signal handling";
               type enumeration {
                 enum "assert" {
                   description "Assert control signal";
                 }
                 enum "de-assert" {
                   description "Deassert control signal";
                 }
                 enum "normal" {
                   description "Normal control signal";
                 }
               }
             }
             leaf rts {
               description "Request To Send signal handling";
               type enumeration {
                 enum "assert" {
                   description "Assert RTS signal";
                 }
                 enum "de-assert" {
                   description "Deassert RTS signal";
                 }
                 enum "normal" {
                   description "Normal RTS signal";
                 }
               }
             }
             leaf dcd {
               description "Data Carrier Detect signal handling";
               type enumeration {
                 enum "require" {
                   description "Require DCD signal";
                 }
                 enum "ignore" {
                   description "Ignore DCD signal";
                 }
                 enum "normal" {
                   description "Normal DCD signal";
                 }
               }
             }
             leaf dsr {
               description "Data Set Ready signal handling";
               type enumeration {
                 enum "require" {
                   description "Require DSR signal";
                 }
                 enum "ignore" {
                   description "Ignore DSR signal";
                 }
                 enum "normal" {
                   description "Normal DSR signal";
                 }
               }
             }
             leaf cts {
               description "Clear To Send signal handling";
               type enumeration {
                 enum "require" {
                   description "Require CTS signal";
                 }
                 enum "ignore" {
                   description "Ignore CTS signal";
                 }
                 enum "normal" {
                   description "Normal CTS signal";
                 }
               }
             }
             leaf indication {
               description "X.21 Indication signal handling";
               type enumeration {
                 enum "require" {
                   description "Require Indication signal";
                 }
                 enum "ignore" {
                   description "Ignore Indication signal";
                 }
                 enum "normal" {
                   description "Normal Indication signal";
                 }
               }
             }
             leaf tm {
               description "Test Mode signal handling";
               type enumeration {
                 enum "require" {
                   description "Require TM signal";
                 }
                 enum "ignore" {
                   description "Ignore TM signal";
                 }
                 enum "normal" {
                   description "Normal TM signal";
                 }
               }
             }
           }
         }
         case case_2 {
         }
       }
       leaf dtr-circuit {
         description "Data Transmit Ready circuit mode";
         type enumeration {
           enum "balanced" {
             description "Balanced signal";
           }
           enum "unbalanced" {
             description "Unbalanced signal";
           }
         }
       }
       leaf dtr-polarity {
         description "Data Transmit Ready signal polarity";
         type enumeration {
           enum "positive" {
             description "Positive polarity";
           }
           enum "negative" {
             description "Negative polarity";
           }
         }
       }
       leaf rts-polarity {
         description "Request To Send signal polarity";
         type enumeration {
           enum "positive" {
             description "Positive polarity";
           }
           enum "negative" {
             description "Negative polarity";
           }
         }
       }
       leaf control-polarity {
         description "X.21 Control signal polarity";
         type enumeration {
           enum "positive" {
             description "Positive polarity";
           }
           enum "negative" {
             description "Negative polarity";
           }
         }
       }
       leaf dcd-polarity {
         description "Data Carrier Detect signal polarity";
         type enumeration {
           enum "positive" {
             description "Positive polarity";
           }
           enum "negative" {
             description "Negative polarity";
           }
         }
       }
       leaf dsr-polarity {
         description "Data Set Ready signal polarity";
         type enumeration {
           enum "positive" {
             description "Positive polarity";
           }
           enum "negative" {
             description "Negative polarity";
           }
         }
       }
       leaf cts-polarity {
         description "Clear To Send signal polarity";
         type enumeration {
           enum "positive" {
             description "Positive polarity";
           }
           enum "negative" {
             description "Negative polarity";
           }
         }
       }
       leaf indication-polarity {
         description "X.21 Indication signal polarity";
         type enumeration {
           enum "positive" {
             description "Positive polarity";
           }
           enum "negative" {
             description "Negative polarity";
           }
         }
       }
       leaf tm-polarity {
         description "Test Mode signal polarity";
         type enumeration {
           enum "positive" {
             description "Positive polarity";
           }
           enum "negative" {
             description "Negative polarity";
           }
         }
       }
       leaf clocking-mode {
         description "Clock mode";
         type enumeration {
           enum "dce" {
             description "DCE timing (DTE mode only, not valid for X.21)";
           }
           enum "internal" {
             description "Internal baud timing";
           }
           enum "loop" {
             description "Loop timing";
           }
         }
       }
       leaf transmit-clock {
         description "Transmit clock phase";
         type enumeration {
           enum "invert" {
             description "Shift clock phase 180 degrees";
           }
         }
       }
       leaf clock-rate {
         description "Interface clock rate";
         type enumeration {
           enum "2.048mhz" {
             description "2.048 MHz";
           }
           enum "2.341mhz" {
             description "2.341 MHz";
           }
           enum "2.731mhz" {
             description "2.731 MHz";
           }
           enum "3.277mhz" {
             description "3.277 MHz";
           }
           enum "4.096mhz" {
             description "4.096 MHz";
           }
           enum "5.461mhz" {
             description "5.461 MHz";
           }
           enum "8.192mhz" {
             description "8.192 MHz";
           }
           enum "16.384mhz" {
             description "16.384 MHz";
           }
           enum "1.2khz" {
             description "1.2 KHz";
           }
           enum "2.4khz" {
             description "2.4 KHz";
           }
           enum "9.6khz" {
             description "9.6 KHz";
           }
           enum "19.2khz" {
             description "19.2 KHz";
           }
           enum "38.4khz" {
             description "38.4 KHz";
           }
           enum "56.0khz" {
             description "56.0 KHz";
           }
           enum "64.0khz" {
             description "64.0 KHz";
           }
           enum "72.0khz" {
             description "72.0 KHz";
           }
           enum "125.0khz" {
             description "125.0 KHz";
           }
           enum "148.0khz" {
             description "148.0 KHz";
           }
           enum "250.0khz" {
             description "250.0 KHz";
           }
           enum "500.0khz" {
             description "500.0 KHz";
           }
           enum "800.0khz" {
             description "800.0 KHz";
           }
           enum "1.0mhz" {
             description "1.0 MHz";
           }
           enum "1.3mhz" {
             description "1.3 MHz";
           }
           enum "2.0mhz" {
             description "2.0 MHz";
           }
           enum "4.0mhz" {
             description "4.0 MHz";
           }
           enum "8.0mhz" {
             description "8.0 MHz";
           }
         }
       }
       leaf loopback {
         description "Loopback mode";
         type enumeration {
           enum "local" {
             description "Local loopback";
           }
           enum "remote" {
             description "Remote/LIU loopback";
           }
           enum "dce-local" {
             description "DCE local loopback (DTE mode only)";
           }
           enum "dce-remote" {
             description "DCE remote loopback";
           }
         }
       }
       leaf encoding {
         description "Line encoding";
         type enumeration {
           enum "nrz" {
             description "Non-Return-To-Zero";
           }
           enum "nrzi" {
             description "Non-Return-To-Zero-Invertible";
           }
         }
       }
     }
     choice gratuitous-arp-reply-choice {
       leaf gratuitous-arp-reply {
         description "Enable gratuitous ARP reply";
         type empty;
       }
       leaf no-gratuitous-arp-reply {
         description "Don't enable gratuitous ARP reply";
         type empty;
       }
     }
     choice no-gratuitous-arp-request-choice {
       leaf no-gratuitous-arp-request {
         description "Ignore gratuitous ARP request";
         type empty;
       }
       leaf no-no-gratuitous-arp-request {
         description "Don't ignore gratuitous ARP request";
         type empty;
       }
     }
     leaf arp-l2-validate {
       description "Validate ARP against L2";
       type empty;
     }
     container ether-options {
       description "Ethernet interface-specific options";
       uses apply-advanced;
       choice loopback-choice {
         leaf loopback {
           description "Enable loopback";
           type empty;
         }
         leaf no-loopback {
           description "Don't enable loopback";
           type empty;
         }
       }
       choice source-filtering-choice {
         leaf source-filtering {
           description "Enable source address filtering";
           type empty;
         }
         leaf no-source-filtering {
           description "Don't enable source address filtering";
           type empty;
         }
       }
       container ethernet-switch-profile {
         description "Ethernet virtual LAN/media access control-level options";
         uses apply-advanced;
         leaf-list tag-protocol-id {
           description "IEEE 802.1q Tag Protocol Identifier values for VLAN-tagged frames";
           type string;
         }
         container ethernet-policer-profile {
           description "Ethernet level CoS-based policer configuration";
           uses apply-advanced;
           container input-priority-map {
             description "Input policer priority map";
             uses cos_policer_input_priority_map;
           }
           container output-priority-map {
             description "Output policer priority map";
             uses cos_policer_output_priority_map;
           }
           list policer {
             key name;
             ordered-by user;
             description "Policer template definition";
             uses cos_policer;
           }
         }
         container storm-control {
           description "Storm control profile name to bind";
           uses apply-advanced;
           leaf profile-name {
             description "Profile name";
             type string;
           }
         }
         container recovery-timeout {
           description "Recovery timeout for this interface";
           leaf time-in-seconds {
             units "seconds";
             type union {
               type string {
                 pattern "<.*>|$.*";
               }
               type uint32 {
                 range "10 .. 3600";
               }
             }
           }
         }
         choice mac-learn-enable-choice {
           leaf mac-learn-enable {
             description "Learn MAC addresses dynamically";
             type empty;
           }
           leaf no-mac-learn-enable {
             description "Don't learn MAC addresses dynamically";
             type empty;
           }
         }
       }
       leaf asynchronous-notification {
         description "Enable sending asynchronous notification to peer on CCC-down";
         type empty;
       }
       list source-address-filter {
         key name;
         description "Source address filters";
         leaf name {
           description "Remote MAC address";
           type jt:mac-addr;
         }
       }
       choice auto-negotiation-choice {
         leaf auto-negotiation {
           description "Enable auto-negotiation";
           type empty;
         }
         leaf no-auto-negotiation {
           description "Don't enable auto-negotiation";
           type empty;
         }
       }
       choice flow-control-choice {
         leaf flow-control {
           description "Enable flow control";
           type empty;
         }
         leaf no-flow-control {
           description "Don't enable flow control";
           type empty;
         }
       }
       container configured-flow-control {
         presence "enable configured-flow-control";
         description "Enable flow control";
         uses apply-advanced;
         leaf rx-buffers {
           description "Enable/Disable Rx buffers";
           type enumeration {
             enum "on" {
               description "Enable Rx buffers";
             }
             enum "off" {
               description "Disable Rx buffers";
             }
           }
         }
         leaf tx-buffers {
           description "Enable/Disable Tx buffers";
           type enumeration {
             enum "on" {
               description "Enable Tx buffers";
             }
             enum "off" {
               description "Disable Tx buffers";
             }
           }
         }
       }
       leaf link-mode {
         description "Link duplex";
         type enumeration {
           enum "automatic" {
             description "Automatic negotiate duplex ";
           }
           enum "half-duplex" {
             description "Half-duplex operation";
           }
           enum "full-duplex" {
             description "Full-duplex operation";
           }
         }
       }
       container mpls {
         description "MPLS options";
         uses mpls_ifd_options;
       }
       leaf ignore-l3-incompletes {
         description "Ignore L3 incomplete errors";
         type empty;
       }
       leaf no-auto-mdix {
         description "Disable auto MDI/MDIX";
         type empty;
       }
       container speed {
         description "Specify speed";
         choice automatic {
           case case_1 {
             container auto-negotiation {
               presence "enable auto-negotiation";
               description "Enable auto-negotiation";
               leaf auto-negotiate-10-100 {
                 description "Limits the auto-negotiation to 10m/100m only";
                 type empty;
               }
             }
           }
           case case_2 {
             leaf ethernet-10m {
               description "10Mbps";
               type empty;
             }
           }
           case case_3 {
             leaf ethernet-100m {
               description "100Mbps";
               type empty;
             }
           }
           case case_4 {
             leaf ethernet-1g {
               description "1Gbps";
               type empty;
             }
           }
           case case_5 {
             leaf ethernet-10g {
               description "10Gbps";
               type empty;
             }
           }
         }
       }
       container ieee-802.3ad {
         description "IEEE 802.3ad";
         uses apply-advanced;
         container lacp {
           description "Link Aggregation Control Protocol configuration";
           uses apply-advanced;
           leaf force-up {
             description "Keep the port up in absence of received LACPDU";
             type empty;
           }
           leaf port-priority {
             description "Priority of the port (0 ... 65535)";
             type union {
               type uint16;
               type string {
                 pattern "<.*>|$.*";
               }
             }
           }
         }
         leaf bundle {
           description "Join an aggregated Ethernet interface";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
         container link-protection-sub-group {
           description "Link Protection subgroup configuration";
           uses apply-advanced;
           leaf subgroup-name {
             description "Name of the subgroup";
             type string {
               length "2 .. 64";
             }
           }
         }
         leaf port-priority {
           description "Link protection Priority of the port (0 ... 65535)";
           type union {
             type uint16;
             type string {
               pattern "<.*>|$.*";
             }
           }
         }
       }
       leaf ieee-802-3az-eee {
         description "IEEE 802.3az Energy Efficient Ethernet(EEE)";
         type empty;
       }
       leaf autostate-exclude {
         description "Interface will not contribute to IRB state";
         type empty;
       }
     }
     container fibrechannel-options {
       description "Fibre Channel interface-specific options";
       uses apply-advanced;
       choice loopback-choice {
         leaf loopback {
           description "Enable loopback";
           type empty;
         }
         leaf no-loopback {
           description "Don't enable loopback";
           type empty;
         }
       }
       leaf bb-sc-n {
         description "B2B state change number";
         type union {
           type string {
             pattern "<.*>|$.*";
           }
           type uint16 {
             range "0 .. 15";
           }
         }
       }
       leaf speed {
         description "Specify speed";
         type enumeration {
           enum "auto-negotiation" {
             description "Enable auto-negotiation";
           }
           enum "1g" {
             description "1Gbps";
           }
           enum "2g" {
             description "2Gbps";
           }
           enum "4g" {
             description "4Gbps";
           }
           enum "8g" {
             description "8Gbps";
           }
         }
       }
     }
     container gigether-options {
       description "Gigabit Ethernet interface-specific options";
       uses apply-advanced;
       choice loopback-choice {
         leaf loopback {
           description "Enable loopback";
           type empty;
         }
         leaf no-loopback {
           description "Don't enable loopback";
           type empty;
         }
       }
       leaf loopback-remote {
         description "Enable remote loopback";
         type empty;
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       choice auto_negotiation_option {
         case case_1 {
           leaf no-auto-negotiation {
             description "Disable auto-negotiation";
             type empty;
           }
         }
         case case_2 {
           container auto-negotiation {
             presence "enable auto-negotiation";
             description "Enable auto-negotiation";
             leaf remote-fault {
               type enumeration {
                 enum "local-interface-offline" {
                   description "Disable local interface";
                 }
                 enum "local-interface-online" {
                   description "Enable local interface";
                 }
               }
             }
           }
         }
       }
       leaf asynchronous-notification {
         description "Enable sending asynchronous notification to peer on CCC-down";
         type empty;
       }
       list source-address-filter {
         key name;
         description "Source address filters";
         leaf name {
           description "Remote MAC address";
           type jt:mac-addr;
         }
       }
       container ieee-802.3ad {
         description "IEEE 802.3ad";
         uses apply-advanced;
         container lacp {
           description "Link Aggregation Control Protocol configuration";
           uses apply-advanced;
           leaf port-priority {
             description "Priority of the port (0 ... 65535)";
             type union {
               type uint16;
               type string {
                 pattern "<.*>|$.*";
               }
             }
           }
         }
         leaf bundle {
           description "Join an aggregated Ethernet interface";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
       }
       container ethernet-switch-profile {
         description "Ethernet virtual LAN/media access control-level options";
         uses apply-advanced;
         leaf-list tag-protocol-id {
           description "IEEE 802.1q Tag Protocol Identifier values for VLAN-tagged frames";
           type string;
         }
         container ethernet-policer-profile {
           description "Ethernet level CoS-based policer configuration";
           uses apply-advanced;
           container ieee802.1-priority-map {
             presence "enable ieee802.1-priority-map";
             description "Premium priority values for IEEE 802.1p bits";
             status deprecated;
             uses apply-advanced;
             leaf-list premium {
               description "Premium policer priority map";
               type union {
                 type string {
                   pattern "<.*>|$.*";
                 }
                 type uint32 {
                   range "0 .. 7";
                 }
               }
             }
           }
           container input-priority-map {
             description "Input policer priority map";
             uses cos_policer_input_priority_map;
           }
           container output-priority-map {
             description "Output policer priority map";
             uses cos_policer_output_priority_map;
           }
           list policer {
             key name;
             ordered-by user;
             description "Policer template definition";
             uses cos_policer;
           }
         }
         container accept-from {
           description "Accept traffic from or to specified remote MAC";
           status deprecated;
           uses apply-advanced;
           list mac-address {
             key name;
             description "Remote MAC";
             uses mac_list;
           }
         }
         choice reject-the-rest-choice {
           leaf reject-the-rest {
             description "Accept traffic from only the specified MAC addresses";
             status deprecated;
             type empty;
           }
           leaf no-reject-the-rest {
             description "Don't accept traffic from only the specified MAC addresses";
             status deprecated;
             type empty;
           }
         }
         leaf mac-learn-enable {
           description "Learn MAC addresses dynamically";
           type empty;
         }
       }
       container mpls {
         description "MPLS options";
         uses mpls_ifd_options;
       }
       leaf ignore-l3-incompletes {
         description "Ignore L3 incomplete errors";
         type empty;
       }
       leaf ieee-802-3az-eee {
         description "IEEE 802.3az Energy Efficient Ethernet(EEE)";
         type empty;
       }
       leaf fec {
         description "Forward Error Correction mode";
         type enumeration {
           enum "none" {
             description "FEC disabled";
           }
           enum "fec91" {
             description "IEEE 802.3bj Clause 91, Reed-Solomon FEC (RS-FEC)";
           }
           enum "fec74" {
             description "FEC74 enabled";
           }
         }
       }
     }
     container optics-options {
       description "Optics options";
       uses apply-advanced;
       leaf wavelength {
         description "Wavelength of the optics (nanometers) for 50Ghz/100Ghz spacing";
         type enumeration {
           enum "1568.77" {
             description "1568.77 nm/191.1003 THz 50/100Ghz spacing";
           }
           enum "1568.36" {
             description "1568.36 nm/191.1500 THz 12.5/50GHz spacing";
           }
           enum "1568.26" {
             description "1568.26 nm/191.1625 THz 12.5GHz spacing";
           }
           enum "1568.16" {
             description "1568.16 nm/191.1750 THz 12.5GHz spacing";
           }
           enum "1568.05" {
             description "1568.05 nm/191.1875 THz 12.5GHz spacing";
           }
           enum "1567.95" {
             description "1567.95 nm/191.2000 THz 12.5/50/100GHz spacing";
           }
           enum "1567.85" {
             description "1567.85 nm/191.2125 THz 12.5GHz spacing";
           }
           enum "1567.75" {
             description "1567.75 nm/191.2250 THz 12.5GHz spacing";
           }
           enum "1567.64" {
             description "1567.64 nm/191.2375 THz 12.5GHz spacing";
           }
           enum "1567.54" {
             description "1567.54 nm/191.2500 THz 12.5/50GHz spacing";
           }
           enum "1567.44" {
             description "1567.44 nm/191.2625 THz 12.5GHz spacing";
           }
           enum "1567.34" {
             description "1567.34 nm/191.2750 THz 12.5GHz spacing";
           }
           enum "1567.23" {
             description "1567.23 nm/191.2875 THz 12.5GHz spacing";
           }
           enum "1567.13" {
             description "1567.13 nm/191.3000 THz 12.5/50/100GHz spacing";
           }
           enum "1567.03" {
             description "1567.03 nm/191.3125 THz 12.5GHz spacing";
           }
           enum "1566.93" {
             description "1566.93 nm/191.3250 THz 12.5GHz spacing";
           }
           enum "1566.83" {
             description "1566.83 nm/191.3375 THz 12.5GHz spacing";
           }
           enum "1566.72" {
             description "1566.72 nm/191.3500 THz 12.5/50GHz spacing";
           }
           enum "1566.62" {
             description "1566.62 nm/191.3625 THz 12.5GHz spacing";
           }
           enum "1566.52" {
             description "1566.52 nm/191.3750 THz 12.5GHz spacing";
           }
           enum "1566.42" {
             description "1566.42 nm/191.3875 THz 12.5GHz spacing";
           }
           enum "1566.31" {
             description "1566.31 nm/191.4000 THz 12.5/50/100GHz spacing";
           }
           enum "1566.21" {
             description "1566.21 nm/191.4125 THz 12.5GHz spacing";
           }
           enum "1566.11" {
             description "1566.11 nm/191.4250 THz 12.5GHz spacing";
           }
           enum "1566.01" {
             description "1566.01 nm/191.4375 THz 12.5GHz spacing";
           }
           enum "1565.90" {
             description "1565.90 nm/191.4500 THz 12.5/50GHz spacing";
           }
           enum "1565.80" {
             description "1565.80 nm/191.4625 THz 12.5GHz spacing";
           }
           enum "1565.70" {
             description "1565.70 nm/191.4750 THz 12.5GHz spacing";
           }
           enum "1565.60" {
             description "1565.60 nm/191.4875 THz 12.5GHz spacing";
           }
           enum "1565.50" {
             description "1565.50 nm/191.5000 THz 12.5/50/100GHz spacing";
           }
           enum "1565.39" {
             description "1565.39 nm/191.5125 THz 12.5GHz spacing";
           }
           enum "1565.29" {
             description "1565.29 nm/191.5250 THz 12.5GHz spacing";
           }
           enum "1565.19" {
             description "1565.19 nm/191.5375 THz 12.5GHz spacing";
           }
           enum "1565.09" {
             description "1565.09 nm/191.5500 THz 12.5/50GHz spacing";
           }
           enum "1564.99" {
             description "1564.99 nm/191.5625 THz 12.5GHz spacing";
           }
           enum "1564.88" {
             description "1564.88 nm/191.5750 THz 12.5GHz spacing";
           }
           enum "1564.78" {
             description "1564.78 nm/191.5875 THz 12.5GHz spacing";
           }
           enum "1564.68" {
             description "1564.68 nm/191.6000 THz 12.5/50/100GHz spacing";
           }
           enum "1564.58" {
             description "1564.58 nm/191.6125 THz 12.5GHz spacing";
           }
           enum "1564.47" {
             description "1564.47 nm/191.6250 THz 12.5GHz spacing";
           }
           enum "1564.37" {
             description "1564.37 nm/191.6375 THz 12.5GHz spacing";
           }
           enum "1564.27" {
             description "1564.27 nm/191.6500 THz 12.5/50GHz spacing";
           }
           enum "1564.17" {
             description "1564.17 nm/191.6625 THz 12.5GHz spacing";
           }
           enum "1564.07" {
             description "1564.07 nm/191.6750 THz 12.5GHz spacing";
           }
           enum "1563.96" {
             description "1563.96 nm/191.6875 THz 12.5GHz spacing";
           }
           enum "1563.86" {
             description "1563.86 nm/191.7000 THz 12.5/50/100GHz spacing";
           }
           enum "1563.76" {
             description "1563.76 nm/191.7125 THz 12.5GHz spacing";
           }
           enum "1563.66" {
             description "1563.66 nm/191.7250 THz 12.5GHz spacing";
           }
           enum "1563.56" {
             description "1563.56 nm/191.7375 THz 12.5GHz spacing";
           }
           enum "1563.45" {
             description "1563.45 nm/191.7500 THz 12.5/50GHz spacing";
           }
           enum "1563.35" {
             description "1563.35 nm/191.7625 THz 12.5GHz spacing";
           }
           enum "1563.25" {
             description "1563.25 nm/191.7750 THz 12.5GHz spacing";
           }
           enum "1563.15" {
             description "1563.15 nm/191.7875 THz 12.5GHz spacing";
           }
           enum "1563.05" {
             description "1563.05 nm/191.8000 THz 12.5/50/100GHz spacing";
           }
           enum "1562.95" {
             description "1562.95 nm/191.8125 THz 12.5GHz spacing";
           }
           enum "1562.84" {
             description "1562.84 nm/191.8250 THz 12.5GHz spacing";
           }
           enum "1562.74" {
             description "1562.74 nm/191.8375 THz 12.5GHz spacing";
           }
           enum "1562.64" {
             description "1562.64 nm/191.8500 THz 12.5/50GHz spacing";
           }
           enum "1562.54" {
             description "1562.54 nm/191.8625 THz 12.5GHz spacing";
           }
           enum "1562.44" {
             description "1562.44 nm/191.8750 THz 12.5GHz spacing";
           }
           enum "1562.33" {
             description "1562.33 nm/191.8875 THz 12.5GHz spacing";
           }
           enum "1562.23" {
             description "1562.23 nm/191.9000 THz 12.5/50/100GHz spacing";
           }
           enum "1562.13" {
             description "1562.13 nm/191.9125 THz 12.5GHz spacing";
           }
           enum "1562.03" {
             description "1562.03 nm/191.9250 THz 12.5GHz spacing";
           }
           enum "1561.93" {
             description "1561.93 nm/191.9375 THz 12.5GHz spacing";
           }
           enum "1561.83" {
             description "1561.83 nm/191.9500 THz 12.5/50GHz spacing";
           }
           enum "1561.72" {
             description "1561.72 nm/191.9625 THz 12.5GHz spacing";
           }
           enum "1561.62" {
             description "1561.62 nm/191.9750 THz 12.5GHz spacing";
           }
           enum "1561.52" {
             description "1561.52 nm/191.9875 THz 12.5GHz spacing";
           }
           enum "1561.42" {
             description "1561.42 nm/192.0000 THz 12.5/50/100GHz spacing";
           }
           enum "1561.32" {
             description "1561.32 nm/192.0125 THz 12.5GHz spacing";
           }
           enum "1561.22" {
             description "1561.22 nm/192.0250 THz 12.5GHz spacing";
           }
           enum "1561.11" {
             description "1561.11 nm/192.0375 THz 12.5GHz spacing";
           }
           enum "1561.01" {
             description "1561.01 nm/192.0500 THz 12.5/50GHz spacing";
           }
           enum "1560.91" {
             description "1560.91 nm/192.0625 THz 12.5GHz spacing";
           }
           enum "1560.81" {
             description "1560.81 nm/192.0750 THz 12.5GHz spacing";
           }
           enum "1560.71" {
             description "1560.71 nm/192.0875 THz 12.5GHz spacing";
           }
           enum "1560.61" {
             description "1560.61 nm/192.1000 THz 12.5/50/100GHz spacing";
           }
           enum "1560.50" {
             description "1560.50 nm/192.1125 THz 12.5GHz spacing";
           }
           enum "1560.40" {
             description "1560.40 nm/192.1250 THz 12.5GHz spacing";
           }
           enum "1560.30" {
             description "1560.30 nm/192.1375 THz 12.5GHz spacing";
           }
           enum "1560.20" {
             description "1560.20 nm/192.1500 THz 12.5/50GHz spacing";
           }
           enum "1560.10" {
             description "1560.10 nm/192.1625 THz 12.5GHz spacing";
           }
           enum "1560.00" {
             description "1560.00 nm/192.1750 THz 12.5GHz spacing";
           }
           enum "1559.90" {
             description "1559.90 nm/192.1875 THz 12.5GHz spacing";
           }
           enum "1559.79" {
             description "1559.79 nm/192.2000 THz 12.5/50/100GHz spacing";
           }
           enum "1559.69" {
             description "1559.69 nm/192.2125 THz 12.5GHz spacing";
           }
           enum "1559.59" {
             description "1559.59 nm/192.2250 THz 12.5GHz spacing";
           }
           enum "1559.49" {
             description "1559.49 nm/192.2375 THz 12.5GHz spacing";
           }
           enum "1559.39" {
             description "1559.39 nm/192.2500 THz 12.5/50GHz spacing";
           }
           enum "1559.29" {
             description "1559.29 nm/192.2625 THz 12.5GHz spacing";
           }
           enum "1559.19" {
             description "1559.19 nm/192.2750 THz 12.5GHz spacing";
           }
           enum "1559.08" {
             description "1559.08 nm/192.2875 THz 12.5GHz spacing";
           }
           enum "1558.98" {
             description "1558.98 nm/192.3000 THz 12.5/50/100GHz spacing";
           }
           enum "1558.88" {
             description "1558.88 nm/192.3125 THz 12.5GHz spacing";
           }
           enum "1558.78" {
             description "1558.78 nm/192.3250 THz 12.5GHz spacing";
           }
           enum "1558.68" {
             description "1558.68 nm/192.3375 THz 12.5GHz spacing";
           }
           enum "1558.58" {
             description "1558.58 nm/192.3500 THz 12.5/50GHz spacing";
           }
           enum "1558.48" {
             description "1558.48 nm/192.3625 THz 12.5GHz spacing";
           }
           enum "1558.38" {
             description "1558.38 nm/192.3750 THz 12.5GHz spacing";
           }
           enum "1558.27" {
             description "1558.27 nm/192.3875 THz 12.5GHz spacing";
           }
           enum "1558.17" {
             description "1558.17 nm/192.4000 THz 12.5/50/100GHz spacing";
           }
           enum "1558.07" {
             description "1558.07 nm/192.4125 THz 12.5GHz spacing";
           }
           enum "1557.97" {
             description "1557.97 nm/192.4250 THz 12.5GHz spacing";
           }
           enum "1557.87" {
             description "1557.87 nm/192.4375 THz 12.5GHz spacing";
           }
           enum "1557.77" {
             description "1557.77 nm/192.4500 THz 12.5/50GHz spacing";
           }
           enum "1557.67" {
             description "1557.67 nm/192.4625 THz 12.5GHz spacing";
           }
           enum "1557.57" {
             description "1557.57 nm/192.4750 THz 12.5GHz spacing";
           }
           enum "1557.46" {
             description "1557.46 nm/192.4875 THz 12.5GHz spacing";
           }
           enum "1557.36" {
             description "1557.36 nm/192.5000 THz 12.5/50/100GHz spacing";
           }
           enum "1557.26" {
             description "1557.26 nm/192.5125 THz 12.5GHz spacing";
           }
           enum "1557.16" {
             description "1557.16 nm/192.5250 THz 12.5GHz spacing";
           }
           enum "1557.06" {
             description "1557.06 nm/192.5375 THz 12.5GHz spacing";
           }
           enum "1556.96" {
             description "1556.96 nm/192.5500 THz 12.5/50GHz spacing";
           }
           enum "1556.86" {
             description "1556.86 nm/192.5625 THz 12.5GHz spacing";
           }
           enum "1556.76" {
             description "1556.76 nm/192.5750 THz 12.5GHz spacing";
           }
           enum "1556.66" {
             description "1556.66 nm/192.5875 THz 12.5GHz spacing";
           }
           enum "1556.55" {
             description "1556.55 nm/192.6000 THz 12.5/50/100GHz spacing";
           }
           enum "1556.45" {
             description "1556.45 nm/192.6125 THz 12.5GHz spacing";
           }
           enum "1556.35" {
             description "1556.35 nm/192.6250 THz 12.5GHz spacing";
           }
           enum "1556.25" {
             description "1556.25 nm/192.6375 THz 12.5GHz spacing";
           }
           enum "1556.15" {
             description "1556.15 nm/192.6500 THz 12.5/50GHz spacing";
           }
           enum "1556.05" {
             description "1556.05 nm/192.6625 THz 12.5GHz spacing";
           }
           enum "1555.95" {
             description "1555.95 nm/192.6750 THz 12.5GHz spacing";
           }
           enum "1555.85" {
             description "1555.85 nm/192.6875 THz 12.5GHz spacing";
           }
           enum "1555.75" {
             description "1555.75 nm/192.7000 THz 12.5/50/100GHz spacing";
           }
           enum "1555.65" {
             description "1555.65 nm/192.7125 THz 12.5GHz spacing";
           }
           enum "1555.55" {
             description "1555.55 nm/192.7250 THz 12.5GHz spacing";
           }
           enum "1555.44" {
             description "1555.44 nm/192.7375 THz 12.5GHz spacing";
           }
           enum "1555.34" {
             description "1555.34 nm/192.7500 THz 12.5/50GHz spacing";
           }
           enum "1555.24" {
             description "1555.24 nm/192.7625 THz 12.5GHz spacing";
           }
           enum "1555.14" {
             description "1555.14 nm/192.7750 THz 12.5GHz spacing";
           }
           enum "1555.04" {
             description "1555.04 nm/192.7875 THz 12.5GHz spacing";
           }
           enum "1554.94" {
             description "1554.94 nm/192.8000 THz 12.5/50/100GHz spacing";
           }
           enum "1554.84" {
             description "1554.84 nm/192.8125 THz 12.5GHz spacing";
           }
           enum "1554.74" {
             description "1554.74 nm/192.8250 THz 12.5GHz spacing";
           }
           enum "1554.64" {
             description "1554.64 nm/192.8375 THz 12.5GHz spacing";
           }
           enum "1554.54" {
             description "1554.54 nm/192.8500 THz 12.5/50GHz spacing";
           }
           enum "1554.44" {
             description "1554.44 nm/192.8625 THz 12.5GHz spacing";
           }
           enum "1554.34" {
             description "1554.34 nm/192.8750 THz 12.5GHz spacing";
           }
           enum "1554.23" {
             description "1554.23 nm/192.8875 THz 12.5GHz spacing";
           }
           enum "1554.13" {
             description "1554.13 nm/192.9000 THz 12.5/50/100GHz spacing";
           }
           enum "1554.03" {
             description "1554.03 nm/192.9125 THz 12.5GHz spacing";
           }
           enum "1553.93" {
             description "1553.93 nm/192.9250 THz 12.5GHz spacing";
           }
           enum "1553.83" {
             description "1553.83 nm/192.9375 THz 12.5GHz spacing";
           }
           enum "1553.73" {
             description "1553.73 nm/192.9500 THz 12.5/50GHz spacing";
           }
           enum "1553.63" {
             description "1553.63 nm/192.9625 THz 12.5GHz spacing";
           }
           enum "1553.53" {
             description "1553.53 nm/192.9750 THz 12.5GHz spacing";
           }
           enum "1553.43" {
             description "1553.43 nm/192.9875 THz 12.5GHz spacing";
           }
           enum "1553.33" {
             description "1553.33 nm/193.0000 THz 12.5/50/100GHz spacing";
           }
           enum "1553.23" {
             description "1553.23 nm/193.0125 THz 12.5GHz spacing";
           }
           enum "1553.13" {
             description "1553.13 nm/193.0250 THz 12.5GHz spacing";
           }
           enum "1553.03" {
             description "1553.03 nm/193.0375 THz 12.5GHz spacing";
           }
           enum "1552.93" {
             description "1552.93 nm/193.0500 THz 12.5/50GHz spacing";
           }
           enum "1552.83" {
             description "1552.83 nm/193.0625 THz 12.5GHz spacing";
           }
           enum "1552.73" {
             description "1552.73 nm/193.0750 THz 12.5GHz spacing";
           }
           enum "1552.62" {
             description "1552.62 nm/193.0875 THz 12.5GHz spacing";
           }
           enum "1552.52" {
             description "1552.52 nm/193.1000 THz 12.5/50/100GHz spacing";
           }
           enum "1552.42" {
             description "1552.42 nm/193.1125 THz 12.5GHz spacing";
           }
           enum "1552.32" {
             description "1552.32 nm/193.1250 THz 12.5GHz spacing";
           }
           enum "1552.22" {
             description "1552.22 nm/193.1375 THz 12.5GHz spacing";
           }
           enum "1552.12" {
             description "1552.12 nm/193.1500 THz 12.5/50GHz spacing";
           }
           enum "1552.02" {
             description "1552.02 nm/193.1625 THz 12.5GHz spacing";
           }
           enum "1551.92" {
             description "1551.92 nm/193.1750 THz 12.5GHz spacing";
           }
           enum "1551.82" {
             description "1551.82 nm/193.1875 THz 12.5GHz spacing";
           }
           enum "1551.72" {
             description "1551.72 nm/193.2000 THz 12.5/50/100GHz spacing";
           }
           enum "1551.62" {
             description "1551.62 nm/193.2125 THz 12.5GHz spacing";
           }
           enum "1551.52" {
             description "1551.52 nm/193.2250 THz 12.5GHz spacing";
           }
           enum "1551.42" {
             description "1551.42 nm/193.2375 THz 12.5GHz spacing";
           }
           enum "1551.32" {
             description "1551.32 nm/193.2500 THz 12.5/50GHz spacing";
           }
           enum "1551.22" {
             description "1551.22 nm/193.2625 THz 12.5GHz spacing";
           }
           enum "1551.12" {
             description "1551.12 nm/193.2750 THz 12.5GHz spacing";
           }
           enum "1551.02" {
             description "1551.02 nm/193.2875 THz 12.5GHz spacing";
           }
           enum "1550.92" {
             description "1550.92 nm/193.3000 THz 12.5/50/100GHz spacing";
           }
           enum "1550.82" {
             description "1550.82 nm/193.3125 THz 12.5GHz spacing";
           }
           enum "1550.72" {
             description "1550.72 nm/193.3250 THz 12.5GHz spacing";
           }
           enum "1550.62" {
             description "1550.62 nm/193.3375 THz 12.5GHz spacing";
           }
           enum "1550.52" {
             description "1550.52 nm/193.3500 THz 12.5/50GHz spacing";
           }
           enum "1550.42" {
             description "1550.42 nm/193.3625 THz 12.5GHz spacing";
           }
           enum "1550.32" {
             description "1550.32 nm/193.3750 THz 12.5GHz spacing";
           }
           enum "1550.22" {
             description "1550.22 nm/193.3875 THz 12.5GHz spacing";
           }
           enum "1550.12" {
             description "1550.12 nm/193.4000 THz 12.5/50/100GHz spacing";
           }
           enum "1550.02" {
             description "1550.02 nm/193.4125 THz 12.5GHz spacing";
           }
           enum "1549.92" {
             description "1549.92 nm/193.4250 THz 12.5GHz spacing";
           }
           enum "1549.82" {
             description "1549.82 nm/193.4375 THz 12.5GHz spacing";
           }
           enum "1549.72" {
             description "1549.72 nm/193.4500 THz 12.5/50GHz spacing";
           }
           enum "1549.62" {
             description "1549.62 nm/193.4625 THz 12.5GHz spacing";
           }
           enum "1549.52" {
             description "1549.52 nm/193.4750 THz 12.5GHz spacing";
           }
           enum "1549.42" {
             description "1549.42 nm/193.4875 THz 12.5GHz spacing";
           }
           enum "1549.32" {
             description "1549.32 nm/193.5000 THz 12.5/50/100GHz spacing";
           }
           enum "1549.21" {
             description "1549.21 nm/193.5125 THz 12.5GHz spacing";
           }
           enum "1549.11" {
             description "1549.11 nm/193.5250 THz 12.5GHz spacing";
           }
           enum "1549.01" {
             description "1549.01 nm/193.5375 THz 12.5GHz spacing";
           }
           enum "1548.91" {
             description "1548.91 nm/193.5500 THz 12.5/50GHz spacing";
           }
           enum "1548.81" {
             description "1548.81 nm/193.5625 THz 12.5GHz spacing";
           }
           enum "1548.71" {
             description "1548.71 nm/193.5750 THz 12.5GHz spacing";
           }
           enum "1548.61" {
             description "1548.61 nm/193.5875 THz 12.5GHz spacing";
           }
           enum "1548.51" {
             description "1548.51 nm/193.6000 THz 12.5/50/100GHz spacing";
           }
           enum "1548.41" {
             description "1548.41 nm/193.6125 THz 12.5GHz spacing";
           }
           enum "1548.31" {
             description "1548.31 nm/193.6250 THz 12.5GHz spacing";
           }
           enum "1548.21" {
             description "1548.21 nm/193.6375 THz 12.5GHz spacing";
           }
           enum "1548.11" {
             description "1548.11 nm/193.6500 THz 12.5/50GHz spacing";
           }
           enum "1548.02" {
             description "1548.02 nm/193.6625 THz 12.5GHz spacing";
           }
           enum "1547.92" {
             description "1547.92 nm/193.6750 THz 12.5GHz spacing";
           }
           enum "1547.82" {
             description "1547.82 nm/193.6875 THz 12.5GHz spacing";
           }
           enum "1547.72" {
             description "1547.72 nm/193.7000 THz 12.5/50/100GHz spacing";
           }
           enum "1547.62" {
             description "1547.62 nm/193.7125 THz 12.5GHz spacing";
           }
           enum "1547.52" {
             description "1547.52 nm/193.7250 THz 12.5GHz spacing";
           }
           enum "1547.42" {
             description "1547.42 nm/193.7375 THz 12.5GHz spacing";
           }
           enum "1547.32" {
             description "1547.32 nm/193.7500 THz 12.5/50GHz spacing";
           }
           enum "1547.22" {
             description "1547.22 nm/193.7625 THz 12.5GHz spacing";
           }
           enum "1547.12" {
             description "1547.12 nm/193.7750 THz 12.5GHz spacing";
           }
           enum "1547.02" {
             description "1547.02 nm/193.7875 THz 12.5GHz spacing";
           }
           enum "1546.92" {
             description "1546.92 nm/193.8000 THz 12.5/50/100GHz spacing";
           }
           enum "1546.82" {
             description "1546.82 nm/193.8125 THz 12.5GHz spacing";
           }
           enum "1546.72" {
             description "1546.72 nm/193.8250 THz 12.5GHz spacing";
           }
           enum "1546.62" {
             description "1546.62 nm/193.8375 THz 12.5GHz spacing";
           }
           enum "1546.52" {
             description "1546.52 nm/193.8500 THz 12.5/50GHz spacing";
           }
           enum "1546.42" {
             description "1546.42 nm/193.8625 THz 12.5GHz spacing";
           }
           enum "1546.32" {
             description "1546.32 nm/193.8750 THz 12.5GHz spacing";
           }
           enum "1546.22" {
             description "1546.22 nm/193.8875 THz 12.5GHz spacing";
           }
           enum "1546.12" {
             description "1546.12 nm/193.9000 THz 12.5/50/100GHz spacing";
           }
           enum "1546.02" {
             description "1546.02 nm/193.9125 THz 12.5GHz spacing";
           }
           enum "1545.92" {
             description "1545.92 nm/193.9250 THz 12.5GHz spacing";
           }
           enum "1545.82" {
             description "1545.82 nm/193.9375 THz 12.5GHz spacing";
           }
           enum "1545.72" {
             description "1545.72 nm/193.9500 THz 12.5/50GHz spacing";
           }
           enum "1545.62" {
             description "1545.62 nm/193.9625 THz 12.5GHz spacing";
           }
           enum "1545.52" {
             description "1545.52 nm/193.9750 THz 12.5GHz spacing";
           }
           enum "1545.42" {
             description "1545.42 nm/193.9875 THz 12.5GHz spacing";
           }
           enum "1545.32" {
             description "1545.32 nm/194.0000 THz 12.5/50/100GHz spacing";
           }
           enum "1545.22" {
             description "1545.22 nm/194.0125 THz 12.5GHz spacing";
           }
           enum "1545.12" {
             description "1545.12 nm/194.0250 THz 12.5GHz spacing";
           }
           enum "1545.02" {
             description "1545.02 nm/194.0375 THz 12.5GHz spacing";
           }
           enum "1544.92" {
             description "1544.92 nm/194.0500 THz 12.5/50GHz spacing";
           }
           enum "1544.82" {
             description "1544.82 nm/194.0625 THz 12.5GHz spacing";
           }
           enum "1544.72" {
             description "1544.72 nm/194.0750 THz 12.5GHz spacing";
           }
           enum "1544.63" {
             description "1544.63 nm/194.0875 THz 12.5GHz spacing";
           }
           enum "1544.53" {
             description "1544.53 nm/194.1000 THz 12.5/50/100GHz spacing";
           }
           enum "1544.43" {
             description "1544.43 nm/194.1125 THz 12.5GHz spacing";
           }
           enum "1544.33" {
             description "1544.33 nm/194.1250 THz 12.5GHz spacing";
           }
           enum "1544.23" {
             description "1544.23 nm/194.1375 THz 12.5GHz spacing";
           }
           enum "1544.13" {
             description "1544.13 nm/194.1500 THz 12.5/50GHz spacing";
           }
           enum "1544.03" {
             description "1544.03 nm/194.1625 THz 12.5GHz spacing";
           }
           enum "1543.93" {
             description "1543.93 nm/194.1750 THz 12.5GHz spacing";
           }
           enum "1543.83" {
             description "1543.83 nm/194.1875 THz 12.5GHz spacing";
           }
           enum "1543.73" {
             description "1543.73 nm/194.2000 THz 12.5/50/100GHz spacing";
           }
           enum "1543.63" {
             description "1543.63 nm/194.2125 THz 12.5GHz spacing";
           }
           enum "1543.53" {
             description "1543.53 nm/194.2250 THz 12.5GHz spacing";
           }
           enum "1543.43" {
             description "1543.43 nm/194.2375 THz 12.5GHz spacing";
           }
           enum "1543.33" {
             description "1543.33 nm/194.2500 THz 12.5/50GHz spacing";
           }
           enum "1543.23" {
             description "1543.23 nm/194.2625 THz 12.5GHz spacing";
           }
           enum "1543.13" {
             description "1543.13 nm/194.2750 THz 12.5GHz spacing";
           }
           enum "1543.04" {
             description "1543.04 nm/194.2875 THz 12.5GHz spacing";
           }
           enum "1542.94" {
             description "1542.94 nm/194.3000 THz 12.5/50/100GHz spacing";
           }
           enum "1542.84" {
             description "1542.84 nm/194.3125 THz 12.5GHz spacing";
           }
           enum "1542.74" {
             description "1542.74 nm/194.3250 THz 12.5GHz spacing";
           }
           enum "1542.64" {
             description "1542.64 nm/194.3375 THz 12.5GHz spacing";
           }
           enum "1542.54" {
             description "1542.54 nm/194.3500 THz 12.5/50GHz spacing";
           }
           enum "1542.44" {
             description "1542.44 nm/194.3625 THz 12.5GHz spacing";
           }
           enum "1542.34" {
             description "1542.34 nm/194.3750 THz 12.5GHz spacing";
           }
           enum "1542.24" {
             description "1542.24 nm/194.3875 THz 12.5GHz spacing";
           }
           enum "1542.14" {
             description "1542.14 nm/194.4000 THz 12.5/50/100GHz spacing";
           }
           enum "1542.04" {
             description "1542.04 nm/194.4125 THz 12.5GHz spacing";
           }
           enum "1541.94" {
             description "1541.94 nm/194.4250 THz 12.5GHz spacing";
           }
           enum "1541.84" {
             description "1541.84 nm/194.4375 THz 12.5GHz spacing";
           }
           enum "1541.75" {
             description "1541.75 nm/194.4500 THz 12.5/50GHz spacing";
           }
           enum "1541.65" {
             description "1541.65 nm/194.4625 THz 12.5GHz spacing";
           }
           enum "1541.55" {
             description "1541.55 nm/194.4750 THz 12.5GHz spacing";
           }
           enum "1541.45" {
             description "1541.45 nm/194.4875 THz 12.5GHz spacing";
           }
           enum "1541.35" {
             description "1541.35 nm/194.5000 THz 12.5/50/100GHz spacing";
           }
           enum "1541.25" {
             description "1541.25 nm/194.5125 THz 12.5GHz spacing";
           }
           enum "1541.15" {
             description "1541.15 nm/194.5250 THz 12.5GHz spacing";
           }
           enum "1541.05" {
             description "1541.05 nm/194.5375 THz 12.5GHz spacing";
           }
           enum "1540.95" {
             description "1540.95 nm/194.5500 THz 12.5/50GHz spacing";
           }
           enum "1540.85" {
             description "1540.85 nm/194.5625 THz 12.5GHz spacing";
           }
           enum "1540.76" {
             description "1540.76 nm/194.5750 THz 12.5GHz spacing";
           }
           enum "1540.66" {
             description "1540.66 nm/194.5875 THz 12.5GHz spacing";
           }
           enum "1540.56" {
             description "1540.56 nm/194.6000 THz 12.5/50/100GHz spacing";
           }
           enum "1540.46" {
             description "1540.46 nm/194.6125 THz 12.5GHz spacing";
           }
           enum "1540.36" {
             description "1540.36 nm/194.6250 THz 12.5GHz spacing";
           }
           enum "1540.26" {
             description "1540.26 nm/194.6375 THz 12.5GHz spacing";
           }
           enum "1540.16" {
             description "1540.16 nm/194.6500 THz 12.5/50GHz spacing";
           }
           enum "1540.06" {
             description "1540.06 nm/194.6625 THz 12.5GHz spacing";
           }
           enum "1539.96" {
             description "1539.96 nm/194.6750 THz 12.5GHz spacing";
           }
           enum "1539.86" {
             description "1539.86 nm/194.6875 THz 12.5GHz spacing";
           }
           enum "1539.77" {
             description "1539.77 nm/194.7000 THz 12.5/50/100GHz spacing";
           }
           enum "1539.67" {
             description "1539.67 nm/194.7125 THz 12.5GHz spacing";
           }
           enum "1539.57" {
             description "1539.57 nm/194.7250 THz 12.5GHz spacing";
           }
           enum "1539.47" {
             description "1539.47 nm/194.7375 THz 12.5GHz spacing";
           }
           enum "1539.37" {
             description "1539.37 nm/194.7500 THz 12.5/50GHz spacing";
           }
           enum "1539.27" {
             description "1539.27 nm/194.7625 THz 12.5GHz spacing";
           }
           enum "1539.17" {
             description "1539.17 nm/194.7750 THz 12.5GHz spacing";
           }
           enum "1539.07" {
             description "1539.07 nm/194.7875 THz 12.5GHz spacing";
           }
           enum "1538.98" {
             description "1538.98 nm/194.8000 THz 12.5/50/100GHz spacing";
           }
           enum "1538.88" {
             description "1538.88 nm/194.8125 THz 12.5GHz spacing";
           }
           enum "1538.78" {
             description "1538.78 nm/194.8250 THz 12.5GHz spacing";
           }
           enum "1538.68" {
             description "1538.68 nm/194.8375 THz 12.5GHz spacing";
           }
           enum "1538.58" {
             description "1538.58 nm/194.8500 THz 12.5/50GHz spacing";
           }
           enum "1538.48" {
             description "1538.48 nm/194.8625 THz 12.5GHz spacing";
           }
           enum "1538.38" {
             description "1538.38 nm/194.8750 THz 12.5GHz spacing";
           }
           enum "1538.28" {
             description "1538.28 nm/194.8875 THz 12.5GHz spacing";
           }
           enum "1538.19" {
             description "1538.19 nm/194.9000 THz 12.5/50/100GHz spacing";
           }
           enum "1538.09" {
             description "1538.09 nm/194.9125 THz 12.5GHz spacing";
           }
           enum "1537.99" {
             description "1537.99 nm/194.9250 THz 12.5GHz spacing";
           }
           enum "1537.89" {
             description "1537.89 nm/194.9375 THz 12.5GHz spacing";
           }
           enum "1537.79" {
             description "1537.79 nm/194.9500 THz 12.5/50GHz spacing";
           }
           enum "1537.69" {
             description "1537.69 nm/194.9625 THz 12.5GHz spacing";
           }
           enum "1537.59" {
             description "1537.59 nm/194.9750 THz 12.5GHz spacing";
           }
           enum "1537.50" {
             description "1537.50 nm/194.9875 THz 12.5GHz spacing";
           }
           enum "1537.40" {
             description "1537.40 nm/195.0000 THz 12.5/50/100GHz spacing";
           }
           enum "1537.30" {
             description "1537.30 nm/195.0125 THz 12.5GHz spacing";
           }
           enum "1537.20" {
             description "1537.20 nm/195.0250 THz 12.5GHz spacing";
           }
           enum "1537.10" {
             description "1537.10 nm/195.0375 THz 12.5GHz spacing";
           }
           enum "1537.00" {
             description "1537.00 nm/195.0500 THz 12.5/50GHz spacing";
           }
           enum "1536.90" {
             description "1536.90 nm/195.0625 THz 12.5GHz spacing";
           }
           enum "1536.81" {
             description "1536.81 nm/195.0750 THz 12.5GHz spacing";
           }
           enum "1536.71" {
             description "1536.71 nm/195.0875 THz 12.5GHz spacing";
           }
           enum "1536.61" {
             description "1536.61 nm/195.1000 THz 12.5/50/100GHz spacing";
           }
           enum "1536.51" {
             description "1536.51 nm/195.1125 THz 12.5GHz spacing";
           }
           enum "1536.41" {
             description "1536.41 nm/195.1250 THz 12.5GHz spacing";
           }
           enum "1536.31" {
             description "1536.31 nm/195.1375 THz 12.5GHz spacing";
           }
           enum "1536.22" {
             description "1536.22 nm/195.1500 THz 12.5/50GHz spacing";
           }
           enum "1536.12" {
             description "1536.12 nm/195.1625 THz 12.5GHz spacing";
           }
           enum "1536.02" {
             description "1536.02 nm/195.1750 THz 12.5GHz spacing";
           }
           enum "1535.92" {
             description "1535.92 nm/195.1875 THz 12.5GHz spacing";
           }
           enum "1535.82" {
             description "1535.82 nm/195.2000 THz 12.5/50/100GHz spacing";
           }
           enum "1535.72" {
             description "1535.72 nm/195.2125 THz 12.5GHz spacing";
           }
           enum "1535.63" {
             description "1535.63 nm/195.2250 THz 12.5GHz spacing";
           }
           enum "1535.53" {
             description "1535.53 nm/195.2375 THz 12.5GHz spacing";
           }
           enum "1535.43" {
             description "1535.43 nm/195.2500 THz 12.5/50GHz spacing";
           }
           enum "1535.33" {
             description "1535.33 nm/195.2625 THz 12.5GHz spacing";
           }
           enum "1535.23" {
             description "1535.23 nm/195.2750 THz 12.5GHz spacing";
           }
           enum "1535.13" {
             description "1535.13 nm/195.2875 THz 12.5GHz spacing";
           }
           enum "1535.04" {
             description "1535.04 nm/195.3000 THz 12.5/50/100GHz spacing";
           }
           enum "1534.94" {
             description "1534.94 nm/195.3125 THz 12.5GHz spacing";
           }
           enum "1534.84" {
             description "1534.84 nm/195.3250 THz 12.5GHz spacing";
           }
           enum "1534.74" {
             description "1534.74 nm/195.3375 THz 12.5GHz spacing";
           }
           enum "1534.64" {
             description "1534.64 nm/195.3500 THz 12.5/50GHz spacing";
           }
           enum "1534.54" {
             description "1534.54 nm/195.3625 THz 12.5GHz spacing";
           }
           enum "1534.45" {
             description "1534.45 nm/195.3750 THz 12.5GHz spacing";
           }
           enum "1534.35" {
             description "1534.35 nm/195.3875 THz 12.5GHz spacing";
           }
           enum "1534.25" {
             description "1534.25 nm/195.4000 THz 12.5/50/100GHz spacing";
           }
           enum "1534.15" {
             description "1534.15 nm/195.4125 THz 12.5GHz spacing";
           }
           enum "1534.05" {
             description "1534.05 nm/195.4250 THz 12.5GHz spacing";
           }
           enum "1533.96" {
             description "1533.96 nm/195.4375 THz 12.5GHz spacing";
           }
           enum "1533.86" {
             description "1533.86 nm/195.4500 THz 12.5/50GHz spacing";
           }
           enum "1533.76" {
             description "1533.76 nm/195.4625 THz 12.5GHz spacing";
           }
           enum "1533.66" {
             description "1533.66 nm/195.4750 THz 12.5GHz spacing";
           }
           enum "1533.56" {
             description "1533.56 nm/195.4875 THz 12.5GHz spacing";
           }
           enum "1533.47" {
             description "1533.47 nm/195.5000 THz 12.5/50/100GHz spacing";
           }
           enum "1533.37" {
             description "1533.37 nm/195.5125 THz 12.5GHz spacing";
           }
           enum "1533.27" {
             description "1533.27 nm/195.5250 THz 12.5GHz spacing";
           }
           enum "1533.17" {
             description "1533.17 nm/195.5375 THz 12.5GHz spacing";
           }
           enum "1533.07" {
             description "1533.07 nm/195.5500 THz 12.5/50GHz spacing";
           }
           enum "1532.98" {
             description "1532.98 nm/195.5625 THz 12.5GHz spacing";
           }
           enum "1532.88" {
             description "1532.88 nm/195.5750 THz 12.5GHz spacing";
           }
           enum "1532.78" {
             description "1532.78 nm/195.5875 THz 12.5GHz spacing";
           }
           enum "1532.68" {
             description "1532.68 nm/195.6000 THz 12.5/50/100GHz spacing";
           }
           enum "1532.58" {
             description "1532.58 nm/195.6125 THz 12.5GHz spacing";
           }
           enum "1532.49" {
             description "1532.49 nm/195.6250 THz 12.5GHz spacing";
           }
           enum "1532.39" {
             description "1532.39 nm/195.6375 THz 12.5GHz spacing";
           }
           enum "1532.29" {
             description "1532.29 nm/195.6500 THz 12.5/50GHz spacing";
           }
           enum "1532.19" {
             description "1532.19 nm/195.6625 THz 12.5GHz spacing";
           }
           enum "1532.09" {
             description "1532.09 nm/195.6750 THz 12.5GHz spacing";
           }
           enum "1532.00" {
             description "1532.00 nm/195.6875 THz 12.5GHz spacing";
           }
           enum "1531.90" {
             description "1531.90 nm/195.7000 THz 12.5/50/100GHz spacing";
           }
           enum "1531.80" {
             description "1531.80 nm/195.7125 THz 12.5GHz spacing";
           }
           enum "1531.70" {
             description "1531.70 nm/195.7250 THz 12.5GHz spacing";
           }
           enum "1531.60" {
             description "1531.60 nm/195.7375 THz 12.5GHz spacing";
           }
           enum "1531.51" {
             description "1531.51 nm/195.7500 THz 12.5/50GHz spacing";
           }
           enum "1531.41" {
             description "1531.41 nm/195.7625 THz 12.5GHz spacing";
           }
           enum "1531.31" {
             description "1531.31 nm/195.7750 THz 12.5GHz spacing";
           }
           enum "1531.21" {
             description "1531.21 nm/195.7875 THz 12.5GHz spacing";
           }
           enum "1531.12" {
             description "1531.12 nm/195.8000 THz 12.5/50/100GHz spacing";
           }
           enum "1531.02" {
             description "1531.02 nm/195.8125 THz 12.5GHz spacing";
           }
           enum "1530.92" {
             description "1530.92 nm/195.8250 THz 12.5GHz spacing";
           }
           enum "1530.82" {
             description "1530.82 nm/195.8375 THz 12.5GHz spacing";
           }
           enum "1530.72" {
             description "1530.72 nm/195.8500 THz 12.5/50GHz spacing";
           }
           enum "1530.63" {
             description "1530.63 nm/195.8625 THz 12.5GHz spacing";
           }
           enum "1530.53" {
             description "1530.53 nm/195.8750 THz 12.5GHz spacing";
           }
           enum "1530.43" {
             description "1530.43 nm/195.8875 THz 12.5GHz spacing";
           }
           enum "1530.33" {
             description "1530.33 nm/195.9000 THz 12.5/50/100GHz spacing";
           }
           enum "1530.24" {
             description "1530.24 nm/195.9125 THz 12.5GHz spacing";
           }
           enum "1530.14" {
             description "1530.14 nm/195.9250 THz 12.5GHz spacing";
           }
           enum "1530.04" {
             description "1530.04 nm/195.9375 THz 12.5GHz spacing";
           }
           enum "1529.94" {
             description "1529.94 nm/195.9500 THz 12.5/50GHz spacing";
           }
           enum "1529.85" {
             description "1529.85 nm/195.9625 THz 12.5GHz spacing";
           }
           enum "1529.75" {
             description "1529.75 nm/195.9750 THz 12.5GHz spacing";
           }
           enum "1529.65" {
             description "1529.65 nm/195.9875 THz 12.5GHz spacing";
           }
           enum "1529.55" {
             description "1529.55 nm/196.0000 THz 12.5/50/100GHz spacing";
           }
           enum "1529.46" {
             description "1529.46 nm/196.0125 THz 12.5GHz spacing";
           }
           enum "1529.36" {
             description "1529.36 nm/196.0250 THz 12.5GHz spacing";
           }
           enum "1529.26" {
             description "1529.26 nm/196.0375 THz 12.5GHz spacing";
           }
           enum "1529.16" {
             description "1529.16 nm/196.0500 THz 12.5/50GHz spacing";
           }
           enum "1529.07" {
             description "1529.07 nm/196.0625 THz 12.5GHz spacing";
           }
           enum "1528.97" {
             description "1528.97 nm/196.0750 THz 12.5GHz spacing";
           }
           enum "1528.87" {
             description "1528.87 nm/196.0875 THz 12.5GHz spacing";
           }
           enum "1528.77" {
             description "1528.77 nm/196.1000 THz 12.5/50/100GHz spacing";
           }
           enum "1528.38" {
             description "1528.38 nm/196.1504 THz 50Ghz spacing";
           }
         }
       }
       leaf tx-power {
         description "Transmit laser output power";
         units "dBm";
         type string;
       }
       leaf loopback {
         description "Put the optics in loopback mode";
         type empty;
       }
       leaf los-warning-threshold {
         description "LOS warning threshold";
         units "dBm";
         type string;
       }
       leaf los-alarm-threshold {
         description "LOS alarm threshold";
         units "dBm";
         type string;
       }
       leaf modulation-format {
         description "Type of Modulation Format";
         type enumeration {
           enum "16qam" {
             description "16-QAM Modulation Format";
           }
           enum "8qam" {
             description "8-QAM MOdulation Format";
           }
           enum "qpsk" {
             description "QPSK Modulation Format";
           }
         }
       }
       choice laser-enable-choice {
         leaf laser-enable {
           description "Enable Laser";
           type empty;
         }
         leaf no-laser-enable {
           description "Don't enable Laser";
           type empty;
         }
       }
       choice is-ma-choice {
         leaf is-ma {
           description "Link is enabled with alarms masked";
           type empty;
         }
         leaf no-is-ma {
           description "Don't link is enabled with alarms masked";
           type empty;
         }
       }
       leaf encoding {
         description "Line encoding";
         type enumeration {
           enum "differential" {
             description "Differential phase line encoding";
           }
           enum "non-differential" {
             description "Non-differential phase line encoding";
           }
         }
       }
       leaf fec {
         description "Forward Error Correction mode";
         type enumeration {
           enum "sdfec" {
             description "SDFEC-Sky-Compatible Soft Decision Forward Error Correction";
           }
           enum "sdfec25" {
             description "SDFEC-Denali Soft Decision Forward Error Correction with 25 percent overhead";
           }
         }
       }
       list alarm {
         key name;
         ordered-by user;
         description "Set optic alarms";
         leaf name {
           type enumeration {
             enum "low-light-alarm" {
               description "Enable low light alarm";
             }
           }
         }
         uses apply-advanced;
         choice actiontype {
           case case_1 {
             leaf syslog {
               type empty;
             }
           }
           case case_2 {
             leaf link-down {
               type empty;
             }
           }
         }
       }
       container tca {
         description "Set tca for optic alarms";
         uses apply-advanced;
         container tx-power-high-tca {
           description "Tx power high TCA";
           uses apply-advanced;
           choice enable-tca-choice {
             leaf enable-tca {
               description "Enable tca";
               type empty;
             }
             leaf no-enable-tca {
               description "Don't enable tca";
               type empty;
             }
           }
           leaf threshold {
             description "Threshold for 15 minute tx power high TCA in dBm";
             type string;
           }
           leaf threshold-24hrs {
             description "Threshold for 24 hour tx power high TCA in dBm";
             type string;
           }
         }
         container tx-power-low-tca {
           description "Tx power low TCA";
           uses apply-advanced;
           choice enable-tca-choice {
             leaf enable-tca {
               description "Enable tca";
               type empty;
             }
             leaf no-enable-tca {
               description "Don't enable tca";
               type empty;
             }
           }
           leaf threshold {
             description "Threshold for 15 minute tx power low TCA in dBm";
             type string;
           }
           leaf threshold-24hrs {
             description "Threshold for 24 hour tx power low TCA in dBm";
             type string;
           }
         }
         container rx-power-high-tca {
           description "Rx power high TCA";
           uses apply-advanced;
           choice enable-tca-choice {
             leaf enable-tca {
               description "Enable tca";
               type empty;
             }
             leaf no-enable-tca {
               description "Don't enable tca";
               type empty;
             }
           }
           leaf threshold {
             description "Threshold for 15 minute rx power high TCA in dBm";
             type string;
           }
           leaf threshold-24hrs {
             description "Threshold for 24 hour rx power high TCA in dBm";
             type string;
           }
         }
         container rx-power-low-tca {
           description "Rx power low TCA";
           uses apply-advanced;
           choice enable-tca-choice {
             leaf enable-tca {
               description "Enable tca";
               type empty;
             }
             leaf no-enable-tca {
               description "Don't enable tca";
               type empty;
             }
           }
           leaf threshold {
             description "Threshold for 15 minute rx power low TCA in dBm";
             type string;
           }
           leaf threshold-24hrs {
             description "Threshold for 24 hour rx power low TCA in dBm";
             type string;
           }
         }
         container temperature-high-tca {
           description "Temperature high TCA";
           uses apply-advanced;
           choice enable-tca-choice {
             leaf enable-tca {
               description "Enable tca";
               type empty;
             }
             leaf no-enable-tca {
               description "Don't enable tca";
               type empty;
             }
           }
           leaf threshold {
             description "Threshold for 15 minute high temperature TCA in celsius";
             type string;
           }
           leaf threshold-24hrs {
             description "Threshold for 24 hour high temperature TCA in celsius";
             type string;
           }
         }
         container temperature-low-tca {
           description "Temperature low TCA";
           uses apply-advanced;
           choice enable-tca-choice {
             leaf enable-tca {
               description "Enable tca";
               type empty;
             }
             leaf no-enable-tca {
               description "Don't enable tca";
               type empty;
             }
           }
           leaf threshold {
             description "Threshold for 15 minute low temperature TCA in celsius";
             type string;
           }
           leaf threshold-24hrs {
             description "Threshold for 24 hour low temperature TCA in celsius";
             type string;
           }
         }
         container carrier-frequency-offset-high-tca {
           description "Carrier frequency offset high TCA";
           uses apply-advanced;
           choice enable-tca-choice {
             leaf enable-tca {
               description "Enable tca";
               type empty;
             }
             leaf no-enable-tca {
               description "Don't enable tca";
               type empty;
             }
           }
           leaf threshold {
             description "Threshold for 15 minute frequency offset high TCA in MHz";
             type string;
           }
           leaf threshold-24hrs {
             description "Threshold for 24 hour frequency offset high TCA in MHz";
             type string;
           }
         }
         container carrier-frequency-offset-low-tca {
           description "Carrier frequency offset low TCA";
           uses apply-advanced;
           choice enable-tca-choice {
             leaf enable-tca {
               description "Enable tca";
               type empty;
             }
             leaf no-enable-tca {
               description "Don't enable tca";
               type empty;
             }
           }
           leaf threshold {
             description "Threshold for 15 minute frequency offset low TCA in MHz";
             type string;
           }
           leaf threshold-24hrs {
             description "Threshold for 24 hour frequency offset low TCA in MHz";
             type string;
           }
         }
         container fec-ber {
           description "Optics Errored Seconds Threshold crossing defect trigger";
           choice enable-tca-choice {
             leaf enable-tca {
               description "Enable the Optics errored seconds threshold crossing alert";
               type empty;
             }
             leaf no-enable-tca {
               description "Don't enable the Optics errored seconds threshold crossing alert";
               type empty;
             }
           }
           leaf threshold {
             description "TCA threshold for BER value in format: xe-n, x is an integer or decimal number, n = 0..9";
             default "10e-3";
             type string {
             }
           }
           leaf threshold-24hrs {
             description "TCA threshold for BER value in format: xe-n, x is an integer or decimal number, n = 0..9";
             default "10e-3";
             type string {
             }
           }
         }
         container tec-current-high-tca {
           description "TEC Current high TCA";
           uses apply-advanced;
           choice enable-tca-choice {
             leaf enable-tca {
               description "Enable tca";
               type empty;
             }
             leaf no-enable-tca {
               description "Don't enable tca";
               type empty;
             }
           }
           leaf threshold {
             description "Threshold for 15 minute TEC Current high TCA in mA";
             type string;
           }
           leaf threshold-24hrs {
             description "Threshold for 24 hour TEC Current high TCA in mA";
             type string;
           }
         }
         container tec-current-low-tca {
           description "TEC Current low TCA";
           uses apply-advanced;
           choice enable-tca-choice {
             leaf enable-tca {
               description "Enable tca";
               type empty;
             }
             leaf no-enable-tca {
               description "Don't enable tca";
               type empty;
             }
           }
           leaf threshold {
             description "Threshold for 15 minute TEC Current low TCA in mA";
             type string;
           }
           leaf threshold-24hrs {
             description "Threshold for 24 hour TEC Current low TCA in mA";
             type string;
           }
         }
         container residual-isi-high-tca {
           description "Residual ISI high TCA";
           uses apply-advanced;
           choice enable-tca-choice {
             leaf enable-tca {
               description "Enable tca";
               type empty;
             }
             leaf no-enable-tca {
               description "Don't enable tca";
               type empty;
             }
           }
           leaf threshold {
             description "Threshold for 15 minute Residual ISI high TCA in ps/nm";
             type string;
           }
           leaf threshold-24hrs {
             description "Threshold for 24 hour Residual ISI high TCA in ps/nm";
             type string;
           }
         }
         container residual-isi-low-tca {
           description "Residual ISI low TCA";
           uses apply-advanced;
           choice enable-tca-choice {
             leaf enable-tca {
               description "Enable tca";
               type empty;
             }
             leaf no-enable-tca {
               description "Don't enable tca";
               type empty;
             }
           }
           leaf threshold {
             description "Threshold for 15 minute Residual ISI low TCA in ps/nm";
             type string;
           }
           leaf threshold-24hrs {
             description "Threshold for 24 hour Residual ISI low TCA in ps/nm";
             type string;
           }
         }
         container pam-histogram-high-tca {
           description "PAM Histogram high TCA";
           uses apply-advanced;
           choice enable-tca-choice {
             leaf enable-tca {
               description "Enable tca";
               type empty;
             }
             leaf no-enable-tca {
               description "Don't enable tca";
               type empty;
             }
           }
           leaf threshold {
             description "Threshold for 15 minute PAM Histogram high TCA";
             type string;
           }
           leaf threshold-24hrs {
             description "Threshold for 24 hour PAM Histogram high TCA";
             type string;
           }
         }
         container snr-low-tca {
           description "SNR low TCA";
           uses apply-advanced;
           choice enable-tca-choice {
             leaf enable-tca {
               description "Enable tca";
               type empty;
             }
             leaf no-enable-tca {
               description "Don't enable tca";
               type empty;
             }
           }
           leaf threshold {
             description "Threshold for 15 minute SNR low TCA in dBm ";
             type string;
           }
           leaf threshold-24hrs {
             description "Threshold for 24 hour SNR low TCA in dBm";
             type string;
           }
         }
         container fec-corrected-errors-high-tca {
           description "FEC Corrected Error High Threshold crossing defect trigger";
           uses apply-advanced;
           choice enable-tca-choice {
             leaf enable-tca {
               description "Enable the FEC Corrected Errors threshold crossing alert";
               type empty;
             }
             leaf no-enable-tca {
               description "Don't enable the FEC Corrected Errors threshold crossing alert";
               type empty;
             }
           }
           leaf threshold {
             description "FEC Corrected-Errs value in format: xe-n, x is an integer or decimal number, n = 0..9";
             default "10e-3";
             type string {
             }
           }
           leaf threshold-24hrs {
             description "FEC Corrected-Errs value in format: xe-n, x is an integer or decimal number, n = 0..9";
             default "10e-3";
             type string {
             }
           }
         }
         container fec-ucorrected-words-high-tca {
           description "FEC UCorrected Words High Threshold crossing defect trigger";
           uses apply-advanced;
           choice enable-tca-choice {
             leaf enable-tca {
               description "Enable the FEC UCorrected Words threshold crossing alert";
               type empty;
             }
             leaf no-enable-tca {
               description "Don't enable the FEC UCorrected Words threshold crossing alert";
               type empty;
             }
           }
           leaf threshold {
             description "FEC UCorrected-Words value in format: xe-n, x is an integer or decimal number, n = 0..9";
             default "10e-3";
             type string {
             }
           }
           leaf threshold-24hrs {
             description "FEC UCorrected-Words value in format: xe-n, x is an integer or decimal number, n = 0..9";
             default "10e-3";
             type string {
             }
           }
         }
         container laser-frequency-error-high-tca {
           description "Laser frequency error high TCA";
           uses apply-advanced;
           choice enable-tca-choice {
             leaf enable-tca {
               description "Enable tca";
               type empty;
             }
             leaf no-enable-tca {
               description "Don't enable tca";
               type empty;
             }
           }
           leaf threshold {
             description "Threshold for 15 minute frequency error high TCA in MHz";
             type string;
           }
           leaf threshold-24hrs {
             description "Threshold for 24 hour frequency error high TCA in MHz";
             type string;
           }
         }
         container laser-frequency-error-low-tca {
           description "Laser frequency error low TCA";
           uses apply-advanced;
           choice enable-tca-choice {
             leaf enable-tca {
               description "Enable tca";
               type empty;
             }
             leaf no-enable-tca {
               description "Don't enable tca";
               type empty;
             }
           }
           leaf threshold {
             description "Threshold for 15 minute frequency error low TCA in MHz";
             type string;
           }
           leaf threshold-24hrs {
             description "Threshold for 24 hour frequency error low TCA in MHz";
             type string;
           }
         }
       }
       list warning {
         key name;
         ordered-by user;
         description "Set optic warnings";
         leaf name {
           type enumeration {
             enum "low-light-warning" {
               description "Enable low light warning";
             }
           }
         }
         uses apply-advanced;
         choice actiontype {
           case case_1 {
             leaf syslog {
               description "Set action as syslog";
               type empty;
             }
           }
           case case_2 {
             leaf link-down {
               description "Set action as link-down";
               type empty;
             }
           }
         }
       }
     }
     container otn-options {
       description "Optical Transmission Network interface-specific options";
       uses otn_options_type;
     }
     container fastether-options {
       description "Fast Ethernet interface-specific options";
       uses apply-advanced;
       choice loopback-choice {
         leaf loopback {
           description "Enable loopback";
           type empty;
         }
         leaf no-loopback {
           description "Don't enable loopback";
           type empty;
         }
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       leaf ingress-rate-limit {
         description "Ingress rate at port";
         units "megabits per second";
         type union {
           type string {
             pattern "<.*>|$.*";
           }
           type uint32 {
             range "1 .. 100";
           }
         }
       }
       list source-address-filter {
         key name;
         ordered-by user;
         description "Source address filters";
         leaf name {
           description "Remote MAC address";
           type jt:mac-addr;
         }
       }
       container ieee-802.3ad {
         description "IEEE 802.3ad";
         uses apply-advanced;
         container lacp {
           description "Link Aggregation Control Protocol configuration";
           uses apply-advanced;
           leaf port-priority {
             description "Priority of the port (0 ... 65535)";
             type union {
               type uint16;
               type string {
                 pattern "<.*>|$.*";
               }
             }
           }
         }
         leaf bundle {
           description "Join an aggregated Ethernet interface";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
       }
       container mpls {
         description "MPLS options";
         uses mpls_ifd_options;
       }
       leaf ignore-l3-incompletes {
         description "Ignore L3 incomplete errors";
         type empty;
       }
     }
     container aggregated-ether-options {
       description "Aggregated Ethernet interface-specific options";
       uses apply-advanced;
       choice loopback-choice {
         leaf loopback {
           description "Enable loopback";
           type empty;
         }
         leaf no-loopback {
           description "Don't enable loopback";
           type empty;
         }
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       leaf autostate-exclude {
         description "Interface will not contribute to IRB state";
         type empty;
       }
       container link-protection {
         presence "enable link-protection";
         description "Enable link protection mode";
         uses apply-advanced;
         leaf revertive {
           description "Revert back from active backup link to primary, if primary is UP";
           type empty;
         }
         leaf non-revertive {
           description "Do not revert back (default mode) from active backup link to primary, if primary is UP";
           type empty;
         }
         leaf backup-state {
           description "Link protection backup link state";
           default "accept-data";
           type enumeration {
             enum "accept-data" {
               description "Accept data on receive channel of backup link";
             }
             enum "discard-data" {
               description "Discard data on receive channel of backup link";
             }
             enum "down" {
               description "Backup link is marked down";
             }
           }
         }
         container rtg-config {
           presence "enable rtg-config";
           description "RTG enable on AE";
           uses apply-advanced;
           leaf preempt-cutover-timer {
             description "RTG preempt-cutover-timer in seconds";
             default "1";
             type union {
               type string {
                 pattern "<.*>|$.*";
               }
               type uint32 {
                 range "0 .. 255";
               }
             }
           }
         }
       }
       choice fcoe-lag-choice {
         leaf fcoe-lag {
           description "Enable FIP/FCoE LAG";
           type empty;
         }
         leaf no-fcoe-lag {
           description "Don't enable FIP/FCoE LAG";
           type empty;
         }
       }
       list source-address-filter {
         key name;
         ordered-by user;
         description "Source address filters";
         leaf name {
           description "Remote MAC address";
           type jt:mac-addr;
         }
       }
       container configured-flow-control {
         presence "enable configured-flow-control";
         description "Enable flow control";
         uses apply-advanced;
         leaf rx-buffers {
           description "Enable/Disable Rx buffers";
           type enumeration {
             enum "on" {
               description "Enable Rx buffers";
             }
             enum "off" {
               description "Disable Rx buffers";
             }
           }
         }
         leaf tx-buffers {
           description "Enable/Disable Tx buffers";
           type enumeration {
             enum "on" {
               description "Enable Tx buffers";
             }
             enum "off" {
               description "Disable Tx buffers";
             }
           }
         }
       }
       container load-balance {
         uses aggregate-load-balance;
       }
       container bfd-liveness-detection {
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
         leaf neighbor {
           description "BFD neighbor address";
           type jt:ipaddr;
         }
         leaf local-address {
           description "BFD local address";
           type jt:ipaddr;
         }
         leaf holddown-interval {
           description "Time to hold the session-UP notification to the client";
           units "milliseconds";
           type union {
             type string {
               pattern "<.*>|$.*";
             }
             type uint32 {
               range "0 .. 255000";
             }
           }
         }
       }
       leaf minimum-links {
         description "Minimum number of aggregated links";
         type union {
           type string {
             pattern "<.*>|$.*";
           }
           type uint16;
         }
       }
       container minimum-bandwidth {
         presence "enable minimum-bandwidth";
         description "Minimum bandwidth configured for aggregated bundle";
         uses apply-advanced;
         leaf bw-value {
           description "Bandwidth value";
           default "1";
           type union {
             type uint64;
             type string {
               pattern "<.*>|$.*";
             }
           }
         }
         leaf bw-unit {
           description "Bandwidth unit";
           type enumeration {
             enum "bps" {
               description "Links are in bytes per sec";
             }
             enum "kbps" {
               description "Links are in kilo bytes per sec";
             }
             enum "mbps" {
               description "Links are in mega bytes per sec";
             }
             enum "gbps" {
               description "Links are in giga bytes per sec ";
             }
           }
         }
       }
       choice redundancy_choice {
         case case_1 {
         }
         case case_2 {
         }
       }
       container rebalance-periodic {
         uses apply-advanced;
       }
       leaf link-speed {
         description "Link speed of individual interface that joins the AE";
         type enumeration {
           enum "10m" {
             description "Links are 10M";
           }
           enum "100m" {
             description "Links are 100M";
           }
           enum "1g" {
             description "Links are 1G";
           }
           enum "2.5g" {
             description "Links are 2.5G";
           }
           enum "5g" {
             description "Links are 5G";
           }
           enum "8g" {
             description "Links are 8G";
           }
           enum "10g" {
             description "Links are 10G";
           }
           enum "25g" {
             description "Links are 25G";
           }
           enum "40g" {
             description "Links are 40G";
           }
           enum "50g" {
             description "Links are 50G";
           }
           enum "80g" {
             description "Links are 80G";
           }
           enum "100g" {
             description "Links are 100G";
           }
           enum "oc192" {
             description "Links are OC-192";
           }
           enum "mixed" {
             description "Links are various speeds";
           }
         }
       }
       container local-bias {
         presence "enable local-bias";
         description "Turn on local bias functionality";
         uses apply-advanced;
         leaf disable {
           description "Disable local-bias";
           type empty;
         }
       }
       leaf local-minimum-links-threshold {
         description "Specify threshold for minimum links per VC/VCF member";
         type union {
           type string {
             pattern "<.*>|$.*";
           }
           type uint16 {
             range "1 .. 100";
           }
         }
       }
       leaf resilient-hash {
         description "Turn on resilient-hash";
         type empty;
       }
       container lacp {
         description "Link Aggregation Control Protocol configuration";
         uses apply-advanced;
         choice mode {
           case case_1 {
             leaf active {
               description "Initiate transmission of LACP packets";
               type empty;
             }
           }
           case case_2 {
             leaf passive {
               description "Respond to LACP packets";
               type empty;
             }
           }
         }
         leaf periodic {
           description "Timer interval for periodic transmission of LACP packets";
           type enumeration {
             enum "fast" {
               description "Receive packets every second";
             }
             enum "slow" {
               description "Receive packets every 30 seconds";
             }
           }
         }
         container link-protection {
           presence "enable link-protection";
           uses apply-advanced;
           leaf disable {
             description "To turn off LACP link-protection";
             type empty;
           }
           choice mode {
             case case_1 {
               leaf revertive {
                 description "Switch links when better priority link comes up";
                 type empty;
               }
             }
             case case_2 {
               leaf non-revertive {
                 description "Do not switch links when better priority link comes up";
                 type empty;
               }
             }
           }
           container rtg-config {
             presence "enable rtg-config";
             description "RTG Feature enable on AE";
             uses apply-advanced;
             leaf preempt-cutover-timer {
               description "RTG preempt-cutover-timer in seconds";
               default "1";
               type union {
                 type string {
                   pattern "<.*>|$.*";
                 }
                 type uint32 {
                   range "0 .. 255";
                 }
               }
             }
           }
         }
         leaf system-priority {
           description "Priority of the system (0 ... 65535)";
           type string;
         }
         leaf system-id {
           description "Node's System ID, encoded as a MAC address";
           type jt:mac-addr;
         }
         leaf admin-key {
           description "Node's administrative key";
           type union {
             type uint16;
             type string {
               pattern "<.*>|$.*";
             }
           }
         }
         container hold-time {
           description "Hold time for link up and link down for AE link members";
           leaf up {
             description "Link up hold time for the AE link members";
             units "seconds";
             type union {
               type string {
                 pattern "<.*>|$.*";
               }
               type uint16 {
                 range "1 .. 6000";
               }
             }
           }
         }
         leaf force-up {
           description "Forceup AE interface with LACP";
           type empty;
         }
       }
       list link-protection-sub-group {
         key name;
         ordered-by user;
         description "Link Protection subgroup configuration";
         leaf name {
           description "Name of the subgroup";
           type string {
             length "2 .. 64";
           }
         }
         uses apply-advanced;
         choice type {
           case case_1 {
             leaf primary {
               description "Primary subgroup for N:N link-protection mode";
               type empty;
             }
           }
           case case_2 {
             leaf backup {
               description "Backup subgroup for N:N link-protection mode";
               type empty;
             }
           }
         }
       }
       container ethernet-switch-profile {
         description "Ethernet virtual LAN/media access control-level options";
         uses apply-advanced;
         leaf-list tag-protocol-id {
           description "IEEE 802.1q Tag Protocol Identifier values for VLAN-tagged frames";
           type string;
         }
         leaf mac-learn-enable {
           description "Learn MAC addresses dynamically";
           type empty;
         }
       }
       container mc-ae {
         description "Multi-chassis aggregation (MC-AE) network device configuration";
         uses apply-advanced;
         leaf mc-ae-id {
           description "MC-AE group id";
           type union {
             type string {
               pattern "<.*>|$.*";
             }
             type uint16 {
               range "1 .. 65535";
             }
           }
         }
         leaf redundancy-group {
           description "Redundancy group id";
           default "1";
           type union {
             type string {
               pattern "<.*>|$.*";
             }
             type uint32 {
               range "1 .. 4294967294";
             }
           }
         }
         leaf chassis-id {
           description "Chassis id of MC-AE network device";
           type union {
             type string {
               pattern "<.*>|$.*";
             }
             type uint16 {
               range "0 .. 1";
             }
           }
         }
         leaf mode {
           description "Mode of the MC-AE";
           type enumeration {
             enum "active-active" {
               description "MC-AE in active-active mode";
             }
           }
         }
         leaf status-control {
           description "Status of the MC-AE chassis";
           type enumeration {
             enum "active" {
               description "Chassis is Active";
             }
             enum "standby" {
               description "Chassis is Standby";
             }
           }
         }
         leaf switchover-mode {
           description "Switchover mode";
           type enumeration {
             enum "revertive" {
               description "Switch mcae node when preferred link comes up";
             }
             enum "non-revertive" {
               description "Do not switch mcae node when preferred link comes up";
             }
           }
         }
         leaf revert-time {
           description "Wait interval before performing switchover";
           default "3";
           units "minute";
           type union {
             type string {
               pattern "<.*>|$.*";
             }
             type uint32 {
               range "1 .. 10";
             }
           }
         }
         leaf init-delay-time {
           description "Init delay timer for mcae sm for min traffic loss";
           units "seconds";
           type union {
             type string {
               pattern "<.*>|$.*";
             }
             type uint16 {
               range "1 .. 6000";
             }
           }
         }
         leaf recovery-delay-time {
           description "Delay timer for bringing up ICL, ICCP";
           units "seconds";
           type union {
             type string {
               pattern "<.*>|$.*";
             }
             type uint16 {
               range "1 .. 6000";
             }
           }
         }
         leaf enhanced-convergence {
           description "Optimized convergence time for mcae";
           type empty;
         }
         container events {
           presence "enable events";
           description "MCAE related events";
           uses apply-advanced;
           container iccp-peer-down {
             presence "enable iccp-peer-down";
             description "Define behavior in the event of ICCP peer down";
             uses apply-advanced;
             leaf force-icl-down {
               description "Bring down ICL logical interface";
               type empty;
             }
             leaf prefer-status-control-active {
               description "Keep this node up (recommended only on status-control active)";
               type empty;
             }
           }
         }
       }
     }
     container es-options {
       description "ES PIC interface-specific options";
       uses apply-advanced;
       leaf backup-interface {
         description "Name of backup interface";
         type union {
           type jt:interface-device;
           type string {
             pattern "<.*>|$.*";
           }
         }
       }
     }
     container vdsl-options {
       description "VDSL interface-specific options";
       uses apply-advanced;
       leaf vdsl-profile {
         description "VDSL profile";
         type enumeration {
           enum "auto" {
             description "Auto";
           }
           enum "8a" {
             description "Profile 8a";
           }
           enum "8b" {
             description "Profile 8b";
           }
           enum "8c" {
             description "Profile 8c";
           }
           enum "8d" {
             description "Profile 8d";
           }
           enum "12a" {
             description "Profile 12a";
           }
           enum "12b" {
             description "Profile 12b";
           }
           enum "17a" {
             description "Profile 17a";
           }
         }
       }
       leaf sra {
         description "DSL SRA";
         default "disable";
         type enumeration {
           enum "enable" {
             description "Enable SRA";
           }
           enum "disable" {
             description "Disable SRA";
           }
         }
       }
       leaf v43 {
         description "DSL V43 tones";
         default "enable";
         type enumeration {
           enum "enable" {
             description "Enable V43";
           }
           enum "disable" {
             description "Disable V43";
           }
         }
       }
     }
     container shdsl-options {
       description "SHDSL interface-specific options";
       uses apply-advanced;
       leaf annex {
         description "Type of SHDSL annex";
         default "annex-b";
         type enumeration {
           enum "annex-a" {
             description "Annex-a PIC";
           }
           enum "annex-b" {
             description "Annex-b PIC";
           }
           enum "annex-f" {
             description "Annex-f PIC";
           }
           enum "annex-g" {
             description "Annex-g PIC";
           }
           enum "annex-auto" {
             description "Annex-auto PIC";
           }
         }
       }
       leaf line-rate {
         description "SHDSL line rate";
         type string;
       }
       leaf loopback {
         description "Loopback mode";
         type enumeration {
           enum "local" {
             description "Local loopback";
           }
           enum "remote" {
             description "Remote loopback";
           }
         }
       }
       container snr-margin {
         presence "enable snr-margin";
         description "Signal to noise ratio margin";
         uses apply-advanced;
         leaf current {
           description "Current signal to noise ratio margin";
           units "dB";
           type string;
         }
         leaf snext {
           description "SNEXT signal to noise ratio margin";
           units "dB";
           type string;
         }
       }
     }
     container container-options {
       description "Container interface specific options";
       uses apply-advanced;
       container container-type {
         presence "enable container-type";
         description "Protocol type of the container interface";
         uses apply-advanced;
         choice container-type-choice {
           case case_1 {
             container aps {
               description "APS options on the container";
               uses aps_type;
             }
           }
         }
       }
       container member-interface-type {
         description "Link type of members of container";
         uses apply-advanced;
         choice member_interface_type_choice {
           case case_1 {
             container sonet {
               uses apply-advanced;
               leaf member-interface-speed {
                 description "Link speed of members of container";
                 type enumeration {
                   enum "oc3" {
                     description "Links are OC-3";
                   }
                   enum "oc12" {
                     description "Links are OC-12";
                   }
                   enum "oc48" {
                     description "Links are OC-48";
                   }
                   enum "oc192" {
                     description "Links are OC-192";
                   }
                   enum "oc768" {
                     description "Links are OC-768";
                   }
                   enum "mixed" {
                     description "Links are of different speeds";
                   }
                 }
               }
             }
           }
           case case_2 {
             container atm {
               uses apply-advanced;
               leaf member-interface-speed {
                 description "Link speed of members of container";
                 type enumeration {
                   enum "oc3" {
                     description "Links are OC-3";
                   }
                   enum "oc12" {
                     description "Links are OC-12";
                   }
                   enum "oc48" {
                     description "Links are OC-48";
                   }
                 }
               }
             }
           }
           case case_3 {
             container channelized-sonet {
               uses apply-advanced;
               leaf member-interface-speed {
                 description "Link speed of members of container";
                 type enumeration {
                   enum "coc3" {
                     description "Links are COC-3";
                   }
                   enum "coc12" {
                     description "Links are COC-12";
                   }
                   enum "coc48" {
                     description "Links are COC-48";
                   }
                   enum "coc192" {
                     description "Links are COC-192";
                   }
                   enum "coc768" {
                     description "Links are COC-768";
                   }
                 }
               }
             }
           }
           case case_4 {
             container channelized-sdh {
               uses apply-advanced;
               leaf member-interface-speed {
                 description "Link speed of members of container";
                 type enumeration {
                   enum "cstm1" {
                     description "Links are cstm-1";
                   }
                   enum "cstm4" {
                     description "Links are cstm-4";
                   }
                   enum "cstm16" {
                     description "Links are cstm-16";
                   }
                   enum "coc64" {
                     description "Links are cstm-64";
                   }
                   enum "cstm256" {
                     description "Links are cstm256";
                   }
                 }
               }
             }
           }
         }
       }
       container redundancy {
         description "Container interface redundancy options";
         uses apply-advanced;
         container hold-time {
           description "Hold time for link up and link down";
           leaf up {
             description "Link up hold time";
             units "milliseconds";
             type union {
               type string {
                 pattern "<.*>|$.*";
               }
               type uint32 {
                 range "0 .. 65534";
               }
             }
           }
           leaf down {
             description "Link down hold time";
             units "milliseconds";
             type union {
               type string {
                 pattern "<.*>|$.*";
               }
               type uint32 {
                 range "0 .. 65534";
               }
             }
           }
         }
       }
       leaf-list container-list {
         description "List of container interfaces this member link is associated to";
         type union {
           type jt:interface-device;
           type string {
             pattern "<.*>|$.*";
           }
         }
       }
       choice redundancy-type {
         case case_1 {
           choice aps-redundancy {
             case case_1 {
               leaf primary {
                 description "This member link is primary interface of the container";
                 type empty;
               }
             }
             case case_2 {
               leaf standby {
                 description "This member link is standby interface of the container";
                 type empty;
               }
             }
           }
         }
       }
       leaf fast-aps {
         description "Fast APS switch";
         type empty;
       }
       leaf allow-configuration-override {
         description "Allow physical configuration of member link to override container configuration";
         type empty;
       }
     }
     list unit {
       key name;
       description "Logical interface";
       leaf name {
         type string;
       }
       uses apply-advanced;
       leaf alias {
         description "Interface alias";
         type string;
       }
       leaf enhanced-convergence {
         description "Optimize convergence time for L3";
         type empty;
       }
       leaf proxy-macip-advertisement {
         description "Proxy advertisement of type 2 MAC+IP route for EVPN";
         type empty;
       }
       leaf virtual-gateway-accept-data {
         description "Accept packets destined for virtual gateway address";
         type empty;
       }
       container peer-psd {
         presence "enable peer-psd";
         description "Peer psd";
         leaf psd-name {
           description "Peer psd name";
           type string;
         }
       }
       container peer-interface {
         presence "enable peer-interface";
         description "Peer interface";
         uses apply-advanced;
         leaf interface-name {
           description "Peer interface name";
           type union {
             type jt:interface-unit;
             type string {
               pattern "<.*>|$.*";
             }
           }
         }
       }
       container interface-shared-with {
         presence "enable interface-shared-with";
         description "Specify which PSD owns this logical interface";
         uses apply-advanced;
         leaf psd-name {
           description "Name of protected system domain (psd[1-31], ex. psd2)";
           type string {
           }
         }
       }
       choice enable-disable {
         case case_1 {
           leaf disable {
             description "Disable this logical interface";
             type empty;
           }
         }
       }
       leaf passive-monitor-mode {
         description "Use interface to tap packets from another router";
         type empty;
       }
       leaf clear-dont-fragment-bit {
         description "Clear DF bit in packet (AS PIC and J-series only as well as MIF)";
         type empty;
       }
       leaf description {
         description "Text description of interface";
         type string;
       }
       leaf metadata {
         description "Text metadata attached to interface";
         type string;
       }
       leaf encapsulation {
         description "Logical link-layer encapsulation";
         type enumeration {
           enum "atm-nlpid" {
             description "ATM NLPID encapsulation";
           }
           enum "atm-cisco-nlpid" {
             description "Cisco-compatible ATM NLPID encapsulation";
           }
           enum "atm-snap" {
             description "ATM LLC/SNAP encapsulation";
           }
           enum "atm-vc-mux" {
             description "ATM VC multiplexing";
           }
           enum "atm-ccc-vc-mux" {
             description "ATM VC for CCC";
           }
           enum "atm-tcc-vc-mux" {
             description "ATM VC for translational cross-connect";
           }
           enum "atm-tcc-snap" {
             description "ATM LLC/SNAP for translational cross-connect";
           }
           enum "atm-ccc-cell-relay" {
             description "ATM cell relay for CCC";
           }
           enum "vlan-vci-ccc" {
             description "CCC for VLAN Q-in-Q and ATM VPI/VCI interworking";
           }
           enum "ether-over-atm-llc" {
             description "Ethernet over ATM (LLC/SNAP) encapsulation";
           }
           enum "ether-vpls-over-atm-llc" {
             description "Ethernet VPLS over ATM (bridging) encapsulation";
           }
           enum "ppp-over-ether-over-atm-llc" {
             description "PPPoE over ATM (LLC/SNAP) encapsulation";
           }
           enum "ppp-over-ether" {
             description "PPPoE encapsulation";
           }
           enum "atm-ppp-vc-mux" {
             description "ATM PPP over raw AAL5";
           }
           enum "atm-ppp-llc" {
             description "ATM PPP over AAL5/LLC";
           }
           enum "atm-mlppp-llc" {
             description "ATM MLPPP over AAL5/LLC";
           }
           enum "frame-relay-ppp" {
             description "PPP over Frame Relay";
           }
           enum "frame-relay-ccc" {
             description "Frame Relay DLCI for CCC";
           }
           enum "frame-relay" {
             description "Frame Relay DLCI";
           }
           enum "frame-relay-tcc" {
             description "Frame Relay DLCI for translational cross-connect";
           }
           enum "frame-relay-ether-type" {
             description "Cisco-compatible Frame Relay Encapsulation DLCI";
           }
           enum "frame-relay-ether-type-tcc" {
             description "Cisco-compatible Frame Relay Encapsulation DLCI for TCC";
           }
           enum "ether-vpls-fr" {
             description "Ethernet VPLS over Frame Relay (bridging) encapsulation";
           }
           enum "vlan-ccc" {
             description "802.1q tagging for a cross-connect";
           }
           enum "ethernet-ccc" {
             description "Ethernet for a cross-connect";
           }
           enum "vlan-vpls" {
             description "VLAN virtual private LAN service";
           }
           enum "vlan-bridge" {
             description "VLAN layer-2 bridging";
           }
           enum "dix" {
             description "Ethernet DIXv2 (RFC 894)";
           }
           enum "ethernet" {
             description "Ethernet II (RFC 894)";
           }
           enum "ethernet-vpls" {
             description "Ethernet II virtual private LAN service";
           }
           enum "ethernet-bridge" {
             description "Ethernet II bridging";
           }
           enum "vlan" {
             description "802.1q-tagged Ethernet";
           }
           enum "vlan-tcc" {
             description "802.1q tagging for a translational cross-connect";
           }
           enum "multilink-ppp" {
             description "Multilink PPP";
           }
           enum "multilink-frame-relay-end-to-end" {
             description "Multilink Frame Relay end-to-end (FRF.15)";
           }
           enum "ppp-ccc" {
             description "Serial PPP device for a cross-connect";
           }
         }
       }
       leaf mtu {
         description "Maximum transmission unit packet size";
         type union {
           type string {
             pattern "<.*>|$.*";
           }
           type uint32;
         }
       }
       choice pointedness {
         case case_1 {
           leaf point-to-point {
             description "Point-to-point connection";
             type empty;
           }
         }
         case case_2 {
           leaf multipoint {
             description "Multipoint connection";
             type empty;
           }
         }
       }
       leaf bandwidth {
         description "Logical unit bandwidth (informational only)";
         type string;
       }
       leaf global-layer2-domainid {
         description "Global Layer-2 Identifier for this interface";
         type union {
           type string {
             pattern "<.*>|$.*";
           }
           type uint32 {
             range "5 .. 4094";
           }
         }
       }
       choice traps-choice {
         leaf traps {
           description "Enable SNMP notifications on state changes";
           type empty;
         }
         leaf no-traps {
           description "Don't enable SNMP notifications on state changes";
           type empty;
         }
       }
       choice routing-services-choice {
         leaf routing-services {
           description "Enable routing services";
           type empty;
         }
         leaf no-routing-services {
           description "Don't enable routing services";
           type empty;
         }
       }
       container arp-resp {
         presence "enable arp-resp";
         description "Knob to control ARP response on the interface, default is restricted";
         choice arp-response-options {
           case case_1 {
             leaf unrestricted {
               description "Enable unrestricted ARP respone on the interface";
               type empty;
             }
           }
           case case_2 {
             leaf restricted {
               description "Enable restricted proxy ARP response on the interface";
               type empty;
             }
           }
         }
       }
       container proxy-arp {
         presence "enable proxy-arp";
         description "Enable proxy ARP on the interface, default is unrestricted";
         choice proxyarp-options {
           case case_1 {
             leaf unrestricted {
               description "Enable unrestricted proxy ARP on the interface";
               type empty;
             }
           }
           case case_2 {
             leaf restricted {
               description "Enable restricted proxy ARP on the interface";
               type empty;
             }
           }
         }
       }
       choice vlan_choice {
         case case_1 {
           leaf vlan-id {
             description "Virtual LAN identifier value for 802.1q VLAN tags";
             type string;
           }
         }
         case case_2 {
           leaf vlan-id-range {
             description "Virtual LAN identifier range of form vid1-vid2";
             type string {
             }
           }
         }
         case case_3 {
           leaf-list inner-vlan-id-swap-ranges {
             description "Inner vlan-id swap range(s) of form vid1-vid2 for dynamic L2 VLANs";
             type jt:vlan-range;
           }
         }
         case case_4 {
           leaf-list vlan-id-list {
             description "List of VLAN identifiers";
             type jt:vlan-range;
           }
         }
         case case_5 {
           leaf-list vlan-tag {
             description "IEEE 802.1q tag list for VLAN tagged frames";
             status deprecated;
             type string;
           }
         }
         case case_6 {
           container vlan-tags {
             presence "enable vlan-tags";
             description "IEEE 802.1q tags";
             leaf outer {
               description "[tpid.]vlan-id, tpid format is 0xNNNN and is optional";
               type string;
             }
             choice inner_choice {
               case case_1 {
                 leaf inner {
                   description "[tpid.]vlan-id, tpid format is 0xNNNN and is optional";
                   type string;
                 }
               }
               case case_2 {
                 leaf inner-range {
                   description "[tpid.]vid1-vid2, tpid format is 0xNNNN and is optional";
                   type string {
                   }
                 }
               }
               case case_3 {
                 leaf-list inner-list {
                   description "List of VLAN identifiers";
                   type jt:vlan-range;
                 }
               }
             }
           }
         }
       }
       leaf native-inner-vlan-id {
         description "Native virtual LAN identifier for singly tagged frames";
         type union {
           type string {
             pattern "<.*>|$.*";
           }
           type uint32 {
             range "0 .. 4094";
           }
         }
       }
       container accept-source-mac {
         description "Remote media access control address to/from which to accept traffic";
         uses apply-advanced;
         list mac-address {
           key name;
           description "Remote MAC address";
           uses mac_list;
         }
       }
       container input-vlan-map {
         description "VLAN map operation on input";
         uses vlan_map;
       }
       container output-vlan-map {
         description "VLAN map operation on output";
         uses vlan_map;
       }
       leaf swap-by-poppush {
         description "Pop original vlan tag and then push a new vlan tag";
         type empty;
       }
       leaf receive-lsp {
         description "Name of incoming label-switched path";
         type string;
       }
       leaf transmit-lsp {
         description "Name of outgoing label-switched path";
         type string;
       }
       leaf dlci {
         description "Frame Relay data-link control identifier";
         type union {
           type string {
             pattern "<.*>|$.*";
           }
           type uint32 {
             range "1 .. 1022";
           }
         }
       }
       leaf multicast-dlci {
         description "Frame Relay data-link control identifier for multicast packets";
         type union {
           type string {
             pattern "<.*>|$.*";
           }
           type uint32 {
             range "1 .. 1022";
           }
         }
       }
       choice vci_type {
         case case_1 {
           leaf vci {
             description "ATM point-to-point virtual circuit identifier ([vpi.]vci)";
             type jt:atm-vci;
           }
         }
         case case_2 {
           leaf allow-any-vci {
             description "Allow all VCIs to open in atm-ccc-cell-relay mode";
             type empty;
           }
         }
         case case_3 {
           leaf vpi {
             description "ATM point-to-point virtual path identifier (vpi)";
             type union {
               type string {
                 pattern "<.*>|$.*";
               }
               type uint32 {
                 range "0 .. 255";
               }
             }
           }
         }
         case case_4 {
           leaf trunk-id {
             description "ATM trunk identifier";
             type union {
               type string {
                 pattern "<.*>|$.*";
               }
               type uint32 {
                 range "0 .. 31";
               }
             }
           }
         }
       }
       choice psn_vci_type {
         case case_1 {
         }
         case case_2 {
         }
       }
       container atm-l2circuit-mode {
         description "Select ATM Layer 2 circuit transport mode";
         choice mode_choice {
           case case_1 {
             leaf cell {
               description "ATM Layer 2 circuit cell mode";
               type empty;
             }
           }
           case case_2 {
             leaf aal5 {
               description "ATM Layer 2 circuit AAL5 mode";
               type empty;
             }
           }
         }
       }
       container vci-range {
         description "ATM VCI range start <start-vci> end <end-vci>";
         leaf start {
           description "ATM VCI range's start value";
           type union {
             type string {
               pattern "<.*>|$.*";
             }
             type uint16 {
               range "32 .. 4094";
             }
           }
         }
         leaf end {
           description "ATM VCI range's end value";
           type union {
             type string {
               pattern "<.*>|$.*";
             }
             type uint16 {
               range "32 .. 4094";
             }
           }
         }
       }
       leaf trunk-bandwidth {
         description "ATM trunk bandwidth";
         units "bits per second";
         type string;
       }
       leaf multicast-vci {
         description "ATM virtual circuit identifier for multicast packets";
         type jt:atm-vci;
       }
       container shaping {
         description "Virtual circuit traffic-shaping options";
         uses dcd_shaping_config;
       }
       container oam-period {
         description "OAM cell period";
         choice oam_period_choices {
           case case_1 {
             leaf oam-period {
               description "OAM cell period";
               units "seconds";
               type union {
                 type string {
                   pattern "<.*>|$.*";
                 }
                 type uint32 {
                   range "1 .. 900";
                 }
               }
             }
           }
           case case_2 {
             container disable {
               presence "enable disable";
               description "Disable F5 OAM loopback";
             }
           }
         }
       }
       container oam-liveness {
         description "OAM virtual circuit liveness parameters";
         uses apply-advanced;
         leaf up-count {
           description "Number of OAM cells to consider VC up";
           type union {
             type string {
               pattern "<.*>|$.*";
             }
             type uint32 {
               range "1 .. 255";
             }
           }
         }
         leaf down-count {
           description "Number of OAM cells to consider VC down";
           type union {
             type string {
               pattern "<.*>|$.*";
             }
             type uint32 {
               range "1 .. 255";
             }
           }
         }
       }
       container ppp-options {
         description "Point-to-Point Protocol interface-specific options";
         uses ppp_options_type;
       }
       choice keepalive_choices {
         case case_1 {
           container keepalives {
             description "Send or demand keepalive messages";
             uses keepalives_type;
           }
         }
         case case_2 {
           leaf no-keepalives {
             description "Do not send or demand keepalive messages";
             type empty;
           }
         }
       }
       leaf inverse-arp {
         description "Enable inverse ARP";
         type empty;
       }
       leaf transmit-weight {
         description "ATM2 transmit weight for VC under VP tunnel";
         type union {
           type string {
             pattern "<.*>|$.*";
           }
           type uint16 {
             range "1 .. 32767";
           }
         }
       }
       container epd-threshold {
         description "Early packet discard threshold for ATM2";
         uses epd_threshold_config;
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf atm-scheduler-map {
         description "Assign ATM2 CoS scheduling map";
         type union {
           type string {
             pattern "default";
           }
           type string;
         }
       }
       leaf mrru {
         description "Maximum received reconstructed unit";
         units "bytes";
         type union {
           type string {
             pattern "<.*>|$.*";
           }
           type uint16 {
             range "1500 .. 4500";
           }
         }
       }
       leaf short-sequence {
         description "Short sequence number header format (MLPPP only)";
         type empty;
       }
       leaf fragment-threshold {
         description "Fragmentation threshold";
         units "bytes";
         type union {
           type string {
             pattern "<.*>|$.*";
           }
           type uint32 {
             range "64 .. 4500";
           }
         }
       }
       leaf drop-timeout {
         description "Drop timeout";
         units "milliseconds";
         type union {
           type string {
             pattern "<.*>|$.*";
           }
           type uint16 {
             range "0 .. 2000";
           }
         }
       }
       leaf disable-mlppp-inner-ppp-pfc {
         description "Disable compression for inner PPP header in MLPPP payload";
         type empty;
       }
       leaf minimum-links {
         description "Minimum number of links to sustain the bundle";
         type union {
           type string {
             pattern "<.*>|$.*";
           }
           type uint16;
         }
       }
       leaf multilink-max-classes {
         description "Number of multilink classes";
         type union {
           type string {
             pattern "<.*>|$.*";
           }
           type uint16;
         }
       }
       leaf interleave-fragments {
         description "Interleave long packets with high priority ones";
         type empty;
       }
       leaf link-layer-overhead {
         description "Link layer bit stuffing overhead (0.0 .. 50.0 percent)";
         type jt:unsigned-float;
       }
       leaf accounting-profile {
         description "Accounting profile name";
         type string;
       }
       leaf peer-unit {
         description "Peer unit number";
         type union {
           type string {
             pattern "<.*>|$.*";
           }
           type uint32 {
             range "0 .. 16385";
           }
         }
       }
       container tunnel {
         description "Tunnel parameters";
         uses apply-advanced;
         leaf source {
           description "Tunnel source";
           type jt:ipaddr;
         }
         leaf destination {
           description "Tunnel destination";
           type jt:ipaddr;
         }
         leaf key {
           description "Tunnel key";
           type union {
             type string {
               pattern "<.*>|$.*";
             }
             type uint32 {
               range "0 .. 4294967295";
             }
           }
         }
         leaf backup-destination {
           description "Backup tunnel destination";
           type jt:ipaddr;
         }
         choice fragmentation {
           case case_1 {
             leaf allow-fragmentation {
               description "Do not set DF bit on packets";
               type empty;
             }
           }
           case case_2 {
             leaf do-not-fragment {
               description "Set DF bit on packets";
               type empty;
             }
           }
         }
         leaf ttl {
           description "Time to live";
           type union {
             type string {
               pattern "<.*>|$.*";
             }
             type uint32 {
               range "1 .. 255";
             }
           }
         }
         leaf traffic-class {
           description "TOS/Traffic class field of IP-header";
           type union {
             type string {
               pattern "<.*>|$.*";
             }
             type uint32 {
               range "0 .. 255";
             }
           }
         }
         leaf flow-label {
           description "Flow label field of IP6-header";
           type union {
             type string {
               pattern "<.*>|$.*";
             }
             type uint32 {
               range "0 .. 1048575";
             }
           }
         }
         choice path-mtu-discovery-choice {
           leaf path-mtu-discovery {
             description "Enable path MTU discovery for tunnels";
             type empty;
           }
           leaf no-path-mtu-discovery {
             description "Don't enable path MTU discovery for tunnels";
             type empty;
           }
         }
         container routing-instance {
           description "Routing instance to which tunnel ends belong";
           uses apply-advanced;
           leaf destination {
             description "Routing instance of tunnel destination";
             type string;
           }
         }
       }
       leaf compression-device {
         description "Logical interface used for compression";
         type union {
           type jt:interface-unit;
           type string {
             pattern "<.*>|$.*";
           }
         }
       }
       container layer2-policer {
         description "Layer2 policing for logical interface";
         uses apply-advanced;
         choice layer2-input-policer-choice {
           case case_1 {
             leaf input-policer {
               description "Two-color policer for received packets";
               type string;
             }
           }
           case case_2 {
           }
           case case_3 {
             leaf input-three-color {
               description "Color-blind three-color policer for received packets";
               type string;
             }
           }
         }
         choice layer2-output-policer-choice {
           case case_1 {
             leaf output-policer {
               description "Two-color policer for transmitted packets";
               type string;
             }
           }
           case case_2 {
             leaf output-three-color {
               description "Three-color policer for transmitted packets";
               type string;
             }
           }
         }
       }
       container service {
         description "Service operations";
         uses apply-advanced;
         list pcef {
           key name;
           ordered-by user;
           description "PCEF configuration";
           leaf name {
             description "PCEF Profile name";
             type string;
           }
           uses apply-advanced;
           leaf activate-all {
             description "Activate all rules and rulebases in the pcef profile";
             type empty;
           }
           list activate {
             key name;
             ordered-by user;
             description "Name of pcef profile rule or rulebase to activate";
             leaf name {
               description "Name of pcef profile rule or rulebase to activate";
               type string;
             }
             uses apply-advanced;
           }
         }
       }
       container family {
         description "Protocol family";
         container inet {
           presence "enable inet";
           description "IPv4 parameters";
           uses apply-advanced;
           container dhcp {
             presence "enable dhcp";
             description "Configure DHCP Client";
             uses apply-advanced;
             container client-identifier {
               description "DHCP Server identifies a client by client-identifier value ";
               choice client-identifier-choice {
                 case case_1 {
                   leaf ascii {
                     description "Client identifier as an ASCII string";
                     type string;
                   }
                 }
                 case case_2 {
                   leaf hexadecimal {
                     description "Client identifier as a hexadecimal string";
                     type string {
                     }
                   }
                 }
               }
             }
             leaf lease-time {
               description "Default lease time requested in ";
               units "seconds";
               type string;
             }
             leaf retransmission-attempt {
               description "Number of attempts to retransmit the DHCP client protocol packet";
               default "4";
               type union {
                 type string {
                   pattern "<.*>|$.*";
                 }
                 type uint32 {
                   range "0 .. 6";
                 }
               }
             }
             leaf retransmission-interval {
               description "Number of seconds between successive retransmission";
               default "4";
               units "seconds";
               type union {
                 type string {
                   pattern "<.*>|$.*";
                 }
                 type uint32 {
                   range "4 .. 64";
                 }
               }
             }
             leaf server-address {
               description "DHCP Server-address";
               type jt:ipv4addr;
             }
             leaf update-server {
               description "Propagate TCP/IP settings to DHCP server ";
               type empty;
             }
             leaf vendor-id {
               description "Vendor class id for the DHCP Client";
               type string;
             }
           }
           container targeted-broadcast {
             presence "enable targeted-broadcast";
             description "Directed broadcast";
             uses apply-advanced;
             choice targeted-bcast-choice {
               case case_1 {
                 leaf forward-and-send-to-re {
                   description "Allow packets to be forwarded and sent to re";
                   type empty;
                 }
               }
               case case_2 {
                 leaf forward-only {
                   description "Allow packets only to be forwarded";
                   type empty;
                 }
               }
             }
           }
           leaf destination-class-usage {
             description "Enable destination class usage on this interface";
             status deprecated;
             type empty;
           }
           leaf transit-options-packets {
             description "Transit IP options packets (don't send to Routing Engine)";
             status deprecated;
             type empty;
           }
           leaf transit-ttl-exceeded {
             description "Transit IP TTL-exceeded packets (don't send to Routing Engine)";
             status deprecated;
             type empty;
           }
           leaf receive-options-packets {
             description "Receive IP options packets (don't send to Routing Engine)";
             type empty;
           }
           leaf receive-ttl-exceeded {
             description "Receive IP TTL-exceeded packets (don't send to Routing Engine)";
             type empty;
           }
           container accounting {
             description "Configure interface-based accounting options";
             uses apply-advanced;
             container source-class-usage {
               description "Enable source class usage on this interface";
               uses apply-advanced;
               leaf input {
                 description "Specify this interface for source-class-usage input";
                 type empty;
               }
               leaf output {
                 description "Specify this interface for source-class-usage output";
                 type empty;
               }
             }
             leaf destination-class-usage {
               description "Enable destination class usage on this interface";
               type empty;
             }
           }
           container rpf-check {
             presence "enable rpf-check";
             description "Enable reverse-path-forwarding checks on this interface";
             uses apply-advanced;
             leaf fail-filter {
               description "Name of filter applied to packets failing RPF check";
               type string;
             }
             container mode {
               description "Mode for reverse path forwarding";
               leaf loose {
                 description "Reverse-path-forwarding loose mode";
                 type empty;
               }
             }
           }
           leaf mtu {
             description "Protocol family maximum transmission unit";
             type union {
               type uint32;
               type string {
                 pattern "<.*>|$.*";
               }
             }
           }
           leaf arp-max-cache {
             description "Max interface ARP nexthop cache size";
             type union {
               type string {
                 pattern "<.*>|$.*";
               }
               type uint32 {
                 range "1 .. 2000000";
               }
             }
           }
           leaf arp-new-hold-limit {
             description "Max no. of new unresolved nexthops";
             type union {
               type string {
                 pattern "<.*>|$.*";
               }
               type uint32 {
                 range "1 .. 2000000";
               }
             }
           }
           leaf no-redirects {
             description "Do not redirect traffic";
             type empty;
           }
           leaf no-neighbor-learn {
             description "Disable neighbor address learning on interface";
             type empty;
           }
           leaf unconditional-src-learn {
             description "Glean from arp packets even when source cannot be validated";
             type empty;
           }
           leaf multicast-only {
             description "Allow only multicast traffic (tunnels only)";
             type empty;
           }
           leaf primary {
             description "Candidate for primary interface in system";
             type empty;
           }
           leaf ipsec-sa {
             description "Name of security association";
             type string {
               length "1 .. 32";
             }
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   description "List of filter modules applied to received packets ";
                   type string;
                 }
               }
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
           }
           container simple-filter {
             description "Filter for doing multifield classification";
             uses apply-advanced;
             leaf input {
               description "Name of simple filter applied to received packets";
               type string;
             }
           }
           container policer {
             description "Interface policing";
             uses apply-advanced;
             leaf arp {
               description "Name of policer applied to received ARP packets";
               type string;
             }
             leaf input {
               description "Name of policer applied to received packets";
               type string;
             }
             leaf output {
               description "Name of policer applied to transmitted packets";
               type string;
             }
           }
           container sampling {
             description "Interface sampling";
             uses apply-advanced;
             leaf input {
               description "Sample all packets input on this interface";
               type empty;
             }
             leaf output {
               description "Sample all packets output on this interface";
               type empty;
             }
           }
           list next-hop-tunnel {
             key name;
             ordered-by user;
             description "One or more next-hop tunnel tables";
             leaf name {
               description "Next-hop tunnel gateway address";
               type string;
             }
             uses apply-advanced;
             leaf ipsec-vpn {
               description "Name of IPSec VPN";
               type string;
             }
           }
           list address {
             key name;
             ordered-by user;
             description "Interface address/destination prefix";
             leaf name {
               description "Interface address/destination prefix";
               type jt:ipv4prefix;
             }
             uses apply-advanced;
             leaf destination {
               description "Destination address";
               type jt:ipv4addr;
             }
             leaf destination-profile {
               description "Profile to use for destination address";
               type string;
             }
             leaf broadcast {
               description "Broadcast address";
               type jt:ipv4addr;
             }
             leaf primary {
               description "Candidate for primary address in system";
               type empty;
             }
             leaf preferred {
               description "Preferred address on interface";
               type empty;
             }
             leaf master-only {
               description "Master management IP address for router";
               type empty;
             }
             list multipoint-destination {
               key name;
               ordered-by user;
               description "Multipoint NBMA destination";
               leaf name {
                 description "Destination address";
                 type jt:ipv4addr;
               }
               uses apply-advanced;
               choice link-address {
                 case case_1 {
                   leaf dlci {
                     description "Frame Relay data-link control identifier";
                     type union {
                       type string {
                         pattern "<.*>|$.*";
                       }
                       type uint32 {
                         range "1 .. 1022";
                       }
                     }
                   }
                 }
                 case case_2 {
                   leaf vci {
                     description "ATM virtual circuit identifier ([vpi.]vci)";
                     type jt:atm-vci;
                   }
                 }
               }
               container shaping {
                 description "Virtual circuit traffic-shaping options";
                 uses dcd_shaping_config;
               }
               container oam-period {
                 description "OAM cell period";
                 choice oam_period_choices {
                   case case_1 {
                     leaf oam_period {
                       description "OAM cell period";
                       units "seconds";
                       type union {
                         type string {
                           pattern "<.*>|$.*";
                         }
                         type uint32 {
                           range "1 .. 900";
                         }
                       }
                     }
                   }
                   case case_2 {
                     container disable {
                       presence "enable disable";
                       description "Disable OAM loopback";
                     }
                   }
                 }
               }
               container oam-liveness {
                 description "OAM virtual circuit liveness parameters";
                 uses apply-advanced;
                 leaf up-count {
                   description "Number of OAM cells to consider VC up";
                   type union {
                     type string {
                       pattern "<.*>|$.*";
                     }
                     type uint32 {
                       range "1 .. 255";
                     }
                   }
                 }
                 leaf down-count {
                   description "Number of OAM cells to consider VC down";
                   type union {
                     type string {
                       pattern "<.*>|$.*";
                     }
                     type uint32 {
                       range "1 .. 255";
                     }
                   }
                 }
               }
               leaf inverse-arp {
                 description "Enable inverse ARP reply messages";
                 type empty;
               }
               leaf transmit-weight {
                 description "ATM2 transmit weight for VC under VP tunnel";
                 type union {
                   type string {
                     pattern "<.*>|$.*";
                   }
                   type uint16 {
                     range "1 .. 32767";
                   }
                 }
               }
               container epd-threshold {
                 description "Early packet discard threshold for ATM2";
                 uses epd_threshold_config;
               }
             }
             list arp {
               key name;
               ordered-by user;
               description "Static Address Resolution Protocol entries";
               leaf name {
                 description "Destination IP address";
                 type jt:ipv4addr;
               }
               leaf l2-interface {
                 description "Layer 2 interface name for ARP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to ARP requests for this entry";
                 type empty;
               }
             }
             list vrrp-group {
               key name;
               ordered-by user;
               description "VRRP group";
               uses vrrp-group;
             }
             leaf virtual-gateway-address {
               description "Virtual Gateway IP address";
               type jt:ipv4addr;
             }
           }
           container unnumbered-address {
             description "Unnumbered interface address/destination prefix";
             leaf source {
               description "Interface from which to take local address";
               type union {
                 type jt:interface-unit;
                 type string {
                   pattern "<.*>|$.*";
                 }
               }
             }
             leaf preferred-source-address {
               description "Preferred address on the donor interface";
               type string;
             }
             leaf destination {
               description "Destination address";
               type jt:ipv4addr;
             }
             leaf destination-profile {
               description "Profile to use for destination address";
               type string;
             }
           }
           leaf negotiate-address {
             description "Negotiate address with remote";
             type empty;
           }
         }
         container iso {
           presence "enable iso";
           description "OSI ISO protocol parameters";
           uses apply-advanced;
           list address {
             key name;
             ordered-by user;
             description "Interface address";
             leaf name {
               description "Interface address";
               type jt:isoaddr;
             }
             uses apply-advanced;
           }
           leaf mtu {
             description "Protocol family maximum transmission unit";
             type union {
               type uint32;
               type string {
                 pattern "<.*>|$.*";
               }
             }
           }
         }
         container inet6 {
           presence "enable inet6";
           description "IPv6 protocol parameters";
           uses apply-advanced;
           container dhcpv6-client {
             description "Dynamic Host Configuration Protocol DHCPv6 client configuration";
             uses apply-advanced;
             leaf client-type {
               description "DHCPv6 client type";
               type enumeration {
                 enum "stateful" {
                   description "Stateful client type for address assignment.";
                 }
                 enum "autoconfig" {
                   description "Autoconfig  client type for router-advertisement";
                 }
               }
             }
             list client-ia-type {
               key name;
               ordered-by user;
               description "DHCPv6 client identity association type";
               leaf name {
                 type enumeration {
                   enum "ia-na" {
                     description "Identity Association-Non-temporary Address";
                   }
                   enum "ia-pd" {
                     description "Identity Association-Prefix Address";
                   }
                 }
               }
               uses apply-advanced;
             }
             container rapid-commit {
               presence "enable rapid-commit";
               description "Option is used to signal the use of the two message exchange for address assignment";
             }
             container prefix-delegating {
               description "Prefix delegating parameters";
               uses apply-advanced;
               leaf preferred-prefix-length {
                 description "Client preferred prefix length";
                 type union {
                   type string {
                     pattern "<.*>|$.*";
                   }
                   type uint32 {
                     range "0 .. 64";
                   }
                 }
               }
               leaf sub-prefix-length {
                 description "The sub prefix length for LAN interfaces";
                 type union {
                   type string {
                     pattern "<.*>|$.*";
                   }
                   type uint32 {
                     range "1 .. 64";
                   }
                 }
               }
             }
             container client-identifier {
               description "DHCP Server identifies a client by client-identifier value ";
               leaf duid-type {
                 description "DUID identifying a client";
                 type enumeration {
                   enum "duid-llt" {
                     description "Link-layer address plus time";
                   }
                   enum "vendor" {
                     description "Vendor-assigned unique ID based on Enterprise Number";
                   }
                   enum "duid-ll" {
                     description "Link-layer address";
                   }
                 }
               }
             }
             list req-option {
               key name;
               ordered-by user;
               description "DHCPV6 client requested option configuration";
               leaf name {
                 type enumeration {
                   enum "dns-server" {
                     description "Dns-server option";
                   }
                   enum "domain" {
                     description "Dns-server option";
                   }
                   enum "ntp-server" {
                     description "Ntp-server option";
                   }
                   enum "time-zone" {
                     description "Time-zone option";
                   }
                   enum "sip-server" {
                     description "Sip-server option";
                   }
                   enum "sip-domain" {
                     description "Sip-domain option";
                   }
                   enum "nis-server" {
                     description "Nis-server option";
                   }
                   enum "nis-domain" {
                     description "Nis-domain option";
                   }
                   enum "fqdn" {
                     description "Fully-qualified-domain option";
                   }
                   enum "vendor-spec" {
                     description "Vendor-spec option";
                   }
                 }
               }
               uses apply-advanced;
             }
             leaf retransmission-attempt {
               description "Number of attempts to retransmit the DHCPV6 client protocol packet";
               default "9";
               type union {
                 type string {
                   pattern "<.*>|$.*";
                 }
                 type uint32 {
                   range "0 .. 9";
                 }
               }
             }
           }
           container rpf-check {
             presence "enable rpf-check";
             description "Enable reverse-path-forwarding checks on this interface";
             uses apply-advanced;
             leaf fail-filter {
               description "Name of filter applied to packets failing RPF check";
               type string;
             }
             container mode {
               description "Mode for reverse path forwarding";
               leaf loose {
                 description "Reverse-path-forwarding loose mode";
                 type empty;
               }
             }
           }
           container accounting {
             description "Interface-based accounting options";
             uses apply-advanced;
             container source-class-usage {
               uses apply-advanced;
               leaf input {
                 description "Interface for source-class-usage input";
                 type empty;
               }
               leaf output {
                 description "Interface for source-class-usage output";
                 type empty;
               }
             }
             leaf destination-class-usage {
               description "Enable destination class usage on this interface";
               type empty;
             }
           }
           leaf mtu {
             description "Protocol family maximum transmission unit";
             type union {
               type uint32;
               type string {
                 pattern "<.*>|$.*";
               }
             }
           }
           leaf nd6-stale-time {
             description "Stale time to reconfirm reachability with inet6 neighbour";
             units "seconds";
             type union {
               type string {
                 pattern "<.*>|$.*";
               }
               type uint32 {
                 range "1 .. 18000";
               }
             }
           }
           leaf no-neighbor-learn {
             description "Disable neighbor address learning on interface";
             type empty;
           }
           leaf nd6-max-cache {
             description "Max interface ND nexthop cache size";
             type union {
               type string {
                 pattern "<.*>|$.*";
               }
               type uint32 {
                 range "1 .. 2000000";
               }
             }
           }
           leaf nd6-new-hold-limit {
             description "Max no. of new unresolved nexthops";
             type union {
               type string {
                 pattern "<.*>|$.*";
               }
               type uint32 {
                 range "1 .. 2000000";
               }
             }
           }
           leaf no-redirects {
             description "Do not redirect traffic";
             type empty;
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   description "List of filter modules applied to received packets ";
                   type string;
                 }
               }
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
           }
           container policer {
             description "Interface policing";
             uses apply-advanced;
             leaf input {
               description "Name of policer applied to received packets";
               type string;
             }
             leaf output {
               description "Name of policer applied to transmitted packets";
               type string;
             }
           }
           container sampling {
             description "Interface sampling";
             uses apply-advanced;
             leaf input {
               description "Sample all packets input on this interface";
               type empty;
             }
             leaf output {
               description "Sample all packets output on this interface";
               type empty;
             }
           }
           list address {
             key name;
             ordered-by user;
             description "Interface address or destination prefix";
             leaf name {
               description "Interface address or destination prefix";
               type jt:ipv6prefix;
             }
             uses apply-advanced;
             leaf destination {
               description "Destination address";
               type jt:ipv6addr;
             }
             leaf eui-64 {
               description "Generate EUI-64 interface ID";
               type empty;
             }
             leaf primary {
               description "Candidate for primary address in system";
               type empty;
             }
             leaf preferred {
               description "Preferred address on interface";
               type empty;
             }
             leaf master-only {
               description "Master management IP address for router";
               type empty;
             }
             list ndp {
               key name;
               ordered-by user;
               description "Static Neighbor Discovery Protocol  entries";
               leaf name {
                 description "Destination IP address";
                 type jt:ipv6addr;
               }
               leaf l2-interface {
                 description "Layer 2 interface name for NDP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to NDP requests for this entry";
                 type empty;
               }
             }
             list vrrp-inet6-group {
               key name;
               ordered-by user;
               description "VRRP group";
               uses vrrp-group;
             }
             leaf virtual-gateway-address {
               description "Virtual Gateway IP address";
               type jt:ipv6addr;
             }
             leaf subnet-router-anycast {
               description "Create a subnet roter anycast address for this address.";
               type empty;
             }
           }
           choice dad-disable-choice {
             leaf dad-disable {
               description "Disable duplicate-address-detection";
               type empty;
             }
             leaf no-dad-disable {
               description "Don't disable duplicate-address-detection";
               type empty;
             }
           }
         }
         container mpls {
           presence "enable mpls";
           description "MPLS protocol parameters";
           uses apply-advanced;
           leaf mtu {
             description "Protocol family maximum transmission unit";
             type union {
               type uint32;
               type string {
                 pattern "<.*>|$.*";
               }
             }
           }
           leaf maximum-labels {
             description "Protocol family maximum number of labels";
             default "3";
             type union {
               type string {
                 pattern "<.*>|$.*";
               }
               type uint32 {
                 range "3 .. 5";
               }
             }
           }
           container filter {
             description "Packet filtering";
             uses apply-advanced;
             choice input_choice {
               case case_1 {
                 leaf input {
                   description "Name of filter applied to received packets";
                   type string;
                 }
               }
               case case_2 {
                 leaf-list input-list {
                   description "List of filter modules applied to received packets ";
                   type string;
                 }
               }
             }
             choice output_choice {
               case case_1 {
                 leaf output {
                   description "Name of filter applied to transmitted packets";
                   type string;
                 }
               }
               case case_2 {
                 leaf-list output-list {
                   description "List of filter modules applied to transmitted packets ";
                   type string;
                 }
               }
             }
             leaf group {
               description "Interface group to which interface belongs";
               type union {
                 type string {
                   pattern "<.*>|$.*";
                 }
                 type uint32 {
                   range "1 .. 255";
                 }
               }
             }
           }
           container ingress-queuing-filter {
             description "Protocol family ingress-queuing-filter";
             leaf filter-name {
               description "Name of the ingress-queuing-filter";
               type string;
             }
           }
           container policer {
             description "Interface policing";
             uses apply-advanced;
             leaf input {
               description "Name of policer applied to received packets";
               type string;
             }
             leaf output {
               description "Name of policer applied to transmitted packets";
               type string;
             }
           }
         }
         container mlppp {
           description "Multilink PPP protocol parameters";
           uses apply-advanced;
           leaf bundle {
             description "Logical interface name this link will join";
             type string;
           }
           choice anchor-points {
             case case_1 {
             }
             case case_2 {
             }
           }
           leaf dynamic-profile {
             description " dynamic profile for interface to use";
             type string {
               length "1 .. 80";
             }
           }
         }
         container mlfr-end-to-end {
           presence "enable mlfr-end-to-end";
           description "Multilink Frame Relay end-to-end protocol parameters";
           uses apply-advanced;
           leaf bundle {
             description "Logical interface name this link will join";
             type union {
               type jt:interface-unit;
               type string {
                 pattern "<.*>|$.*";
               }
             }
           }
         }
         container mlfr-uni-nni {
           presence "enable mlfr-uni-nni";
           description "Multilink Frame Relay UNI NNI protocol parameters";
           uses apply-advanced;
           leaf bundle {
             description "Logical interface name this link will join";
             type union {
               type jt:interface-unit;
               type string {
                 pattern "<.*>|$.*";
               }
             }
           }
         }
         container ccc {
           presence "enable ccc";
           description "Circuit cross-connect parameters";
           uses apply-advanced;
           container filter {
             description "Packet filtering";
             uses apply-advanced;
             choice input_choice {
               case case_1 {
                 leaf input {
                   description "Name of filter applied to received packets";
                   type string;
                 }
               }
               case case_2 {
                 leaf-list input-list {
                   description "List of filter modules applied to received packets ";
                   type string;
                 }
               }
             }
             choice output_choice {
               case case_1 {
                 leaf output {
                   description "Name of filter applied to transmitted packets";
                   type string;
                 }
               }
               case case_2 {
                 leaf-list output-list {
                   description "List of filter modules applied to transmitted packets ";
                   type string;
                 }
               }
             }
             leaf group {
               description "Interface group to which interface belongs";
               type union {
                 type string {
                   pattern "<.*>|$.*";
                 }
                 type uint32 {
                   range "1 .. 255";
                 }
               }
             }
           }
           container policer {
             description "Interface policing";
             uses apply-advanced;
             leaf input {
               description "Name of policer applied to received packets";
               type string;
             }
             leaf output {
               description "Name of policer applied to transmitted packets";
               type string;
             }
           }
           leaf translate-fecn-and-becn {
             description "Translate FECN and BECN bits";
             type empty;
           }
           choice de-or-plp {
             case case_1 {
               leaf translate-discard-eligible {
                 description "Translate DE bit";
                 type empty;
               }
             }
             case case_2 {
             }
           }
           leaf keep-address-and-control {
             description "Don't strip PPP address and control bytes";
             type empty;
           }
         }
         container tcc {
           presence "enable tcc";
           description "Translational cross-connect parameters";
           uses apply-advanced;
           container policer {
             description "Interface policing";
             uses apply-advanced;
             leaf input {
               description "Name of policer applied to received packets";
               type string;
             }
             leaf output {
               description "Name of policer applied to transmitted packets";
               type string;
             }
           }
           container proxy {
             presence "enable proxy";
             uses apply-advanced;
             leaf inet-address {
               description "Remote host address on non-Ethernet side of Ethernet TCC";
               type jt:ipv4addr;
             }
           }
           container remote {
             presence "enable remote";
             uses apply-advanced;
             leaf inet-address {
               description "Remote host address on Ethernet side of Ethernet TCC";
               type jt:ipv4addr;
             }
             leaf mac-address {
               description "Remote host MAC address on Ethernet side of Ethernet TCC";
               type jt:mac-addr;
             }
           }
         }
         container vpls {
           presence "enable vpls";
           description "Virtual private LAN service parameters";
           uses apply-advanced;
           leaf core-facing {
             description "Interface is core facing";
             type empty;
           }
         }
         container bridge {
           presence "enable bridge";
           description "Layer-2 bridging parameters";
           uses apply-advanced;
           leaf core-facing {
             description "Interface is core facing";
             type empty;
           }
           leaf interface-mode {
             description "Interface mode (access or trunk)";
             type enumeration {
               enum "access" {
                 description "Interface mode is access";
               }
               enum "trunk" {
                 description "Interface mode is trunk";
               }
             }
           }
           leaf vlan-auto-sense {
             description "Enable VLAN auto sense on this interface";
             type empty;
           }
           leaf bridge-domain-type {
             description "Bridge domain type (svlan or bvlan)";
             type enumeration {
               enum "svlan" {
                 description "Bridge domain type svlan";
               }
               enum "bvlan" {
                 description "Bridge domain type bvlan";
               }
             }
           }
           leaf inter-switch-link {
             description "PVLAN inter switch link";
             type empty;
           }
           choice vlan_list {
             case case_1 {
               leaf vlan-id {
                 description "Access mode and trunk mode VLAN membership";
                 type union {
                   type string {
                     pattern "<.*>|$.*";
                   }
                   type uint32 {
                     range "1 .. 4094";
                   }
                 }
               }
             }
             case case_2 {
               leaf-list vlan-id-list {
                 description "Trunk mode VLAN membership for this interface";
                 type string;
               }
             }
             case case_3 {
               leaf-list inner-vlan-id-list {
                 description "Trunk mode VLAN membership for this interface based on inner VLAN tag";
                 type string;
               }
             }
           }
           container vlan-rewrite {
             description "Specify vlan translation";
             uses apply-advanced;
             list translate {
               key name;
               ordered-by user;
               description "Translate incoming VLAN tag";
               leaf name {
                 description "Specify the incoming VLAN tag";
                 type union {
                   type string {
                     pattern "<.*>|$.*";
                   }
                   type uint32 {
                     range "1 .. 4094";
                   }
                 }
               }
               leaf to-vlan-id {
                 description "Specify the bridge-domain VLAN-ID";
                 type union {
                   type string {
                     pattern "<.*>|$.*";
                   }
                   type uint32 {
                     range "1 .. 4094";
                   }
                 }
               }
             }
           }
           choice isid_list {
             case case_1 {
               leaf isid-list {
                 description "Specify the ISID list";
                 type enumeration {
                   enum "all-service-groups" {
                     description "Map all ISIDs specified under the service-groups";
                   }
                   enum "all" {
                     description "Map all ISIDs";
                   }
                 }
               }
             }
           }
           container recovery-timeout {
             description "Recovery timeout for this interface";
             leaf time-in-seconds {
               units "seconds";
               type union {
                 type string {
                   pattern "<.*>|$.*";
                 }
                 type uint32 {
                   range "10 .. 3600";
                 }
               }
             }
           }
         }
         container ethernet-switching {
           description "Ethernet switching parameters";
           uses ethernet-switching-type;
         }
         container fibre-channel {
           description "Fibre channel switching parameters";
           uses fibre-channel-type;
         }
         container any {
           presence "enable any";
           description "Parameters for 'any' family";
           uses apply-advanced;
           container filter {
             description "Layer 2 packet filtering";
             uses apply-advanced;
             leaf input {
               description "Name of filter applied to received packets";
               type string {
               }
             }
             leaf group {
               description "Group to which interface belongs";
               type union {
                 type string {
                   pattern "<.*>|$.*";
                 }
                 type uint32 {
                   range "1 .. 255";
                 }
               }
             }
           }
         }
         uses apply-advanced;
       }
       leaf service-domain {
         description "Service domain to which interface belongs";
         type enumeration {
           enum "inside" {
             description "Inside network";
           }
           enum "outside" {
             description "Outside network";
           }
         }
       }
       leaf copy-tos-to-outer-ip-header {
         description "Copy IP payload header's ToS field to GRE delivery header";
         type empty;
       }
       container load-balancing-options {
         description "AMS subunit load balancing options";
         uses apply-advanced;
         leaf preferred-active {
           description "Preferred active Interface name";
           type union {
             type jt:interface-device;
             type string {
               pattern "<.*>|$.*";
             }
           }
         }
         container hash-keys {
           uses apply-advanced;
           leaf-list ingress-key {
             description "Hash Key for the ingress direction";
             type enumeration {
               enum "source-ip" {
                 description "Source Ip Address";
               }
               enum "destination-ip" {
                 description "Destination Ip Address";
               }
               enum "protocol" {
                 description "Protocol";
               }
               enum "iif" {
                 description "Incoming Interface";
               }
             }
           }
           leaf-list egress-key {
             description "Hash Key for the egress direction";
             status deprecated;
             type enumeration {
               enum "source-ip" {
                 description "Source Ip Address";
                 status deprecated;
               }
               enum "destination-ip" {
                 description "Destination Ip Address";
                 status deprecated;
               }
               enum "protocol" {
                 description "Protocol";
                 status deprecated;
               }
               enum "oif" {
                 description "Outgoing Interface";
                 status deprecated;
               }
             }
           }
         }
       }
       leaf mac {
         description "Configure logical interface MAC address";
         type jt:mac-unicast;
       }
       leaf virtual-gateway-v4-mac {
         description "Configure virtual gateway IPV4 virtual MAC address";
         type jt:mac-unicast;
       }
       leaf virtual-gateway-v6-mac {
         description "Configure virtual gateway IPV6 virtual MAC address";
         type jt:mac-unicast;
       }
       leaf etree-ac-role {
         description "ETREE attachment circuit role";
         type enumeration {
           enum "root" {
             description "ETREE root interface";
           }
           enum "leaf" {
             description "ETREE leaf interface";
           }
         }
       }
     }
     container no-partition {
       description "Use channelizable interface as clear channel";
       leaf interface-type {
         description "Interface type";
         type enumeration {
           enum "e1" {
             description "E1 interface";
           }
           enum "t1" {
             description "T1 interface";
           }
           enum "at" {
             description "ATM interface";
           }
           enum "t3" {
             description "T3 interface";
           }
           enum "e3" {
             description "E3 interface";
           }
           enum "ct3" {
             description "Channelized T3 interface";
           }
           enum "so" {
             description "SONET interface";
           }
           enum "cau4" {
             description "CAU4 interface";
           }
         }
       }
     }
     list partition {
       key name;
       ordered-by user;
       description "Channelized interface partition";
       leaf name {
         description "Sublevel interface partition index (for example, 1, 3-4)";
         type string;
       }
       leaf oc-slice {
         description "Range of SONET/SDH slices (for example, 1, 7-9)";
         type string;
       }
       leaf timeslots {
         description "Timeslots [(1..24) for T1, (1..31) for E1]; for example, 1-3,4,9,22-24 (no spaces)";
         type string;
       }
       leaf interface-type {
         description "Sublevel interface type";
         type enumeration {
           enum "ds" {
             description "DS0 interface";
           }
           enum "e1" {
             description "E1 interface";
           }
           enum "t1" {
             description "T1 interface";
           }
           enum "at" {
             description "ATM interface";
           }
           enum "ct1" {
             description "Channelized T1 interface";
           }
           enum "ce1" {
             description "Channelized E1 interface";
           }
           enum "t3" {
             description "T3 interface";
           }
           enum "ct3" {
             description "Channelized T3 interface";
           }
           enum "e3" {
             description "E3 interface";
           }
           enum "so" {
             description "SONET interface";
           }
           enum "coc1" {
             description "Channelized OC1 interface";
           }
           enum "cau4" {
             description "Channelized AU4 interface";
           }
           enum "dc" {
             description "D channel interface";
           }
           enum "bc" {
             description "B channel interface";
           }
         }
       }
     }
   }
   grouping keepalives_type {
     uses apply-advanced;
     leaf interval {
       description "Keepalive period";
       units "seconds";
       type union {
         type string {
           pattern "<.*>|$.*";
         }
         type uint16 {
           range "1 .. 32767";
         }
       }
     }
     leaf up-count {
       description "Keepalive received to bring link up";
       type union {
         type string {
           pattern "<.*>|$.*";
         }
         type uint16 {
           range "1 .. 255";
         }
       }
     }
     leaf down-count {
       description "Keepalive missed to bring link down";
       type union {
         type string {
           pattern "<.*>|$.*";
         }
         type uint16 {
           range "1 .. 255";
         }
       }
     }
   }
   grouping mac_list {
     description "MAC address";
     leaf name {
       type jt:mac-addr;
     }
     uses apply-advanced;
     container policer {
       description "MAC policing";
       uses apply-advanced;
       leaf input {
         description "Name of policer applied to received packets";
         type string;
       }
       leaf output {
         description "Name of policer applied to transmitted packets";
         type string;
       }
     }
   }
   grouping macro-data-type {
     leaf name {
       description "Keyword part of the keyword-value pair";
       type string;
     }
     leaf value {
       description "Value part of the keyword-value pair";
       type string;
     }
   }
   grouping mpls_ifd_options {
     uses apply-advanced;
     container pop-all-labels {
       presence "enable pop-all-labels";
       description "Pop all MPLS labels off incoming packets";
       uses apply-advanced;
       leaf-list required-depth {
         description "Required label depth of packet to pop all labels";
         type enumeration {
           enum "all" {
             description "Takes effect only in Stoli based FPCs, in all other FPCs equivalent to '[1 2]'";
           }
           enum "1" {
             description "Required label depth of packet to pop labels";
           }
           enum "2" {
             description "Required label depth of packet to pop labels";
           }
         }
       }
     }
   }
   grouping otn_options_type {
     uses apply-advanced;
     choice laser-enable-choice {
       leaf laser-enable {
         description "Enable Laser";
         type empty;
       }
       leaf no-laser-enable {
         description "Don't enable Laser";
         type empty;
       }
     }
     choice is-ma-choice {
       leaf is-ma {
         description "Link is enabled with alarms masked";
         type empty;
       }
       leaf no-is-ma {
         description "Don't link is enabled with alarms masked";
         type empty;
       }
     }
     choice line-loopback-choice {
       leaf line-loopback {
         description "Enable line loopback";
         type empty;
       }
       leaf no-line-loopback {
         description "Don't enable line loopback";
         type empty;
       }
     }
     choice local-loopback-choice {
       leaf local-loopback {
         description "Enable local host loopback";
         type empty;
       }
       leaf no-local-loopback {
         description "Don't enable local host loopback";
         type empty;
       }
     }
     choice prbs-choice {
       leaf prbs {
         description "Enable otn payload prbs";
         type empty;
       }
       leaf no-prbs {
         description "Don't enable otn payload prbs";
         type empty;
       }
     }
     choice odu-ttim-action-enable-choice {
       leaf odu-ttim-action-enable {
         description "Enable consequent action for ODU TTIM";
         type empty;
       }
       leaf no-odu-ttim-action-enable {
         description "Don't enable consequent action for ODU TTIM";
         type empty;
       }
     }
     choice otu-ttim-action-enable-choice {
       leaf otu-ttim-action-enable {
         description "Enable consequent action for OTU TTIM";
         type empty;
       }
       leaf no-otu-ttim-action-enable {
         description "Don't enable consequent action for OTU TTIM";
         type empty;
       }
     }
     choice transport-monitoring-choice {
       leaf transport-monitoring {
         description "Enable transport monitoring";
         type empty;
       }
       leaf no-transport-monitoring {
         description "Don't enable transport monitoring";
         type empty;
       }
     }
     container odu-delay-management {
       description "Set odu delay management";
       uses apply-advanced;
       choice monitor-end-point-choice {
         leaf monitor-end-point {
           description "Originate connection monitor end point";
           type empty;
         }
         leaf no-monitor-end-point {
           description "Don't originate connection monitor end point";
           type empty;
         }
       }
       choice start-measurement-choice {
         leaf start-measurement {
           description "Enable to start a dm measurement";
           type empty;
         }
         leaf no-start-measurement {
           description "Don't enable to start a dm measurement";
           type empty;
         }
       }
       choice bypass-choice {
         leaf bypass {
           description "Act as tandem passing dm value through node";
           type empty;
         }
         leaf no-bypass {
           description "Don't act as tandem passing dm value through node";
           type empty;
         }
       }
       leaf number-of-frames {
         description "Number of consequent frames to declare dm done";
         type union {
           type string {
             pattern "<.*>|$.*";
           }
           type uint32 {
             range "0 .. 255";
           }
         }
       }
       choice remote-loop-enable-choice {
         leaf remote-loop-enable {
           description "Enable remote DM loop on remote end";
           type empty;
         }
         leaf no-remote-loop-enable {
           description "Don't enable remote DM loop on remote end";
           type empty;
         }
       }
     }
     container signal-degrade {
       description "Signal degrade thresholds";
       uses apply-advanced;
       leaf interval {
         description "Time interval";
         default "10";
         units "milliseconds";
         type union {
           type string {
             pattern "<.*>|$.*";
           }
           type uint32 {
             range "1 .. 1000";
           }
         }
       }
       leaf ber-threshold-clear {
         description "Ber threshold for signal degrade clear (format: xe-n, example: 4.5e-3)";
         type string {
         }
       }
       leaf ber-threshold-signal-degrade {
         description "Ber threshold for signal-degrade (format: xe-n, example: 4.5e-3)";
         type string {
         }
       }
       leaf q-threshold-signal-degrade-clear {
         description "Q threshold for signal-degrade clear (e.g. 14.26)";
         units "dB";
         type string;
       }
       leaf q-threshold-signal-degrade {
         description "Q threshold for signal-degrade (e.g. 9.26)";
         units "dB";
         type string;
       }
     }
     container odu-signal-degrade {
       description "Signal degrade thresholds for ODU";
       uses apply-advanced;
       leaf interval {
         description "Time interval";
         default "10";
         units "milliseconds";
         type union {
           type string {
             pattern "<.*>|$.*";
           }
           type uint32 {
             range "1 .. 1000";
           }
         }
       }
       leaf ber-threshold-clear {
         description "Ber th for sd clear (format: xe-n, example: 4.5e-3)";
         default "1.0e-9";
         type string {
         }
       }
       leaf ber-threshold-signal-degrade {
         description "Ber th for sd (format: xe-n, example: 4.5e-3)";
         default "1.0e-6";
         type string {
         }
       }
     }
     container preemptive-fast-reroute {
       description "Preemptive fast reroute";
       uses apply-advanced;
       choice odu-signal-degrade-monitor-enable-choice {
         leaf odu-signal-degrade-monitor-enable {
           description "Enable ODU signal degrade monitoring";
           type empty;
         }
         leaf no-odu-signal-degrade-monitor-enable {
           description "Don't enable ODU signal degrade monitoring";
           type empty;
         }
       }
       choice odu-backward-frr-enable-choice {
         leaf odu-backward-frr-enable {
           description "Enable ODU backward frr insertion";
           type empty;
         }
         leaf no-odu-backward-frr-enable {
           description "Don't enable ODU backward frr insertion";
           type empty;
         }
       }
       choice signal-degrade-monitor-enable-choice {
         leaf signal-degrade-monitor-enable {
           description "Enable signal degrade monitoring";
           type empty;
         }
         leaf no-signal-degrade-monitor-enable {
           description "Don't enable signal degrade monitoring";
           type empty;
         }
       }
       choice backward-frr-enable-choice {
         leaf backward-frr-enable {
           description "Enable backward frr insertion";
           type empty;
         }
         leaf no-backward-frr-enable {
           description "Don't enable backward frr insertion";
           type empty;
         }
       }
     }
     leaf fec {
       description "Forward Error Correction mode";
       type enumeration {
         enum "none" {
           description "GFEC all 0's";
         }
         enum "gfec" {
           description "GFEC-Generic Forward Error Correction";
         }
         enum "efec" {
           description "EFEC-Enhanced Forward Error Correction";
         }
         enum "gfec-sdfec" {
           description "Both gfec and sdfec";
         }
         enum "ufec" {
           description "UFEC-Ultra Forward Error Correction";
         }
         enum "sdfec" {
           description "SDFEC-Soft Decision Forward Error Correction";
         }
         enum "hgfec" {
           description "HGFEC-High Gain Forward Error Correction";
         }
       }
     }
     choice insert-odu-oci-choice {
       leaf insert-odu-oci {
         description "Force odu open connection indication";
         type empty;
       }
       leaf no-insert-odu-oci {
         description "Don't force odu open connection indication";
         type empty;
       }
     }
     choice insert-odu-lck-choice {
       leaf insert-odu-lck {
         description "Force odu locked maintenance signal";
         type empty;
       }
       leaf no-insert-odu-lck {
         description "Don't force odu locked maintenance signal";
         type empty;
       }
     }
     leaf rate {
       description "Optical Transmission Network mode";
       type enumeration {
         enum "pass-thru" {
           description "Pass through mode - No OTN framing";
         }
         enum "fixed-stuff-bytes" {
           description "Fixed Stuff Bytes 11.0957Gbps";
         }
         enum "no-fixed-stuff-bytes" {
           description "No Fixed Stuff Bytes 11.0491Gbps";
         }
         enum "oc192" {
           description "OTU2 for OC192 10.7Gbps";
         }
         enum "otu3" {
           description "OTU3 for 40Gbps";
         }
         enum "otu4" {
           description "OTU4/OTU4v for 100Gbps-127Gbps";
         }
       }
     }
     container bytes {
       description "Set OTN header bytes";
       uses apply-advanced;
       leaf transmit-payload-type {
         description "Transmit payload type";
         type union {
           type string {
             pattern "<.*>|$.*";
           }
           type uint32 {
             range "0 .. 255";
           }
         }
       }
     }
     container tti {
       description "Trace Identifier";
       uses apply-advanced;
       leaf otu-dapi {
         description "OTU Destination Access Point Identifier";
         type string;
       }
       leaf otu-sapi {
         description "OTU Source Access Point Identifier";
         type string;
       }
       leaf otu-expected-receive-dapi {
         description "OTU Expected Receive Destination Access Point Identifier";
         type string;
       }
       leaf otu-expected-receive-sapi {
         description "OTU Expected Receive Source Access Point Identifier";
         type string;
       }
       leaf odu-dapi {
         description "ODU Destination Access Point Identifier";
         type string;
       }
       leaf odu-sapi {
         description "ODU Source Access Point Identifier";
         type string;
       }
       leaf odu-expected-receive-dapi {
         description "ODU Expected Receive Destination Access Point Identifier";
         type string;
       }
       leaf odu-expected-receive-sapi {
         description "ODU Expected Receive Source Access Point Identifier";
         type string;
       }
       choice otu-dapi-first-byte-nul-choice {
         leaf otu-dapi-first-byte-nul {
           description "Insert all-0s to first byte";
           type empty;
         }
         leaf no-otu-dapi-first-byte-nul {
           description "Don't insert all-0s to first byte";
           type empty;
         }
       }
       choice otu-sapi-first-byte-nul-choice {
         leaf otu-sapi-first-byte-nul {
           description "Insert all-0s to first byte";
           type empty;
         }
         leaf no-otu-sapi-first-byte-nul {
           description "Don't insert all-0s to first byte";
           type empty;
         }
       }
       choice otu-expected-receive-dapi-first-byte-nul-choice {
         leaf otu-expected-receive-dapi-first-byte-nul {
           description "Insert all-0s to first byte";
           type empty;
         }
         leaf no-otu-expected-receive-dapi-first-byte-nul {
           description "Don't insert all-0s to first byte";
           type empty;
         }
       }
       choice otu-expected-receive-sapi-first-byte-nul-choice {
         leaf otu-expected-receive-sapi-first-byte-nul {
           description "Insert all-0s to first byte";
           type empty;
         }
         leaf no-otu-expected-receive-sapi-first-byte-nul {
           description "Don't insert all-0s to first byte";
           type empty;
         }
       }
       choice odu-dapi-first-byte-nul-choice {
         leaf odu-dapi-first-byte-nul {
           description "Insert all-0s to first byte";
           type empty;
         }
         leaf no-odu-dapi-first-byte-nul {
           description "Don't insert all-0s to first byte";
           type empty;
         }
       }
       choice odu-sapi-first-byte-nul-choice {
         leaf odu-sapi-first-byte-nul {
           description "Insert all-0s to first byte";
           type empty;
         }
         leaf no-odu-sapi-first-byte-nul {
           description "Don't insert all-0s to first byte";
           type empty;
         }
       }
       choice odu-expected-receive-dapi-first-byte-nul-choice {
         leaf odu-expected-receive-dapi-first-byte-nul {
           description "Insert all-0s to first byte";
           type empty;
         }
         leaf no-odu-expected-receive-dapi-first-byte-nul {
           description "Don't insert all-0s to first byte";
           type empty;
         }
       }
       choice odu-expected-receive-sapi-first-byte-nul-choice {
         leaf odu-expected-receive-sapi-first-byte-nul {
           description "Insert all-0s to first byte";
           type empty;
         }
         leaf no-odu-expected-receive-sapi-first-byte-nul {
           description "Don't insert all-0s to first byte";
           type empty;
         }
       }
     }
     container trigger {
       description "Defect triggers";
       uses apply-advanced;
       container oc-los {
         description "OC Loss Of Signal defect trigger";
         choice oc_los_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-lof {
         description "OC Loss Of Frame defect trigger";
         choice oc_lof_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-lom {
         description "OC Loss Of Multiframe defect trigger";
         choice oc_lom_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-wavelength-lock {
         description "OC Wavelength Lock defect trigger";
         choice oc_wavelength_lock_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-tsf {
         description "Oc tsf defect trigger";
         choice oc-tsf-choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-ais {
         description "OTU Alarm Indication Signal defect trigger";
         choice otu_ais_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-bdi {
         description "OTU Backward Defect Indication defect trigger";
         choice otu_bdi_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-iae {
         description "OTU Incoming Alignment defect trigger";
         choice otu_iae_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-ttim {
         description "OTU Trail Trace Identifier Mismatch defect trigger";
         choice otu_ttim_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-sd {
         description "OTU Signal Degrade defect trigger";
         choice otu_sd_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-fec-deg {
         description "OTU FEC Degrade defect trigger";
         choice otu_fec_deg_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-fec-exe {
         description "OTU FEC Excessive Error defect trigger";
         choice otu_fec_exe_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-ais {
         description "ODU Alarm Indication Signal defect trigger";
         choice odu_ais_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-bdi {
         description "ODU Backward Defect Indication defect trigger";
         choice odu_bdi_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-iae {
         description "Odu iae defect trigger";
         choice odu-iae-choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-bei {
         description "Odu backward error indication defect trigger";
         choice odu_bei_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-oci {
         description "ODU Open Connection Indication defect trigger";
         choice odu_oci_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-lck {
         description "ODU Locked defect trigger";
         choice odu_lck_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-ttim {
         description "ODU Trail Trace Identifier Mismatch defect trigger";
         choice odu_ttim_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-sd {
         description "ODU Signal Degrade defect trigger";
         choice odu_sd_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container opu-ptim {
         description "Payload Type Mismatch defect trigger";
         choice opu_ptm_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
     }
     container tca {
       description "TCA - threshold crossing alerts";
       uses apply-advanced;
       container otu-tca-es {
         description "OTU Errored Seconds Threshold crossing defect trigger";
         choice enable-tca-choice {
           leaf enable-tca {
             description "Enable the OTU errored seconds threshold crossing alert";
             type empty;
           }
           leaf no-enable-tca {
             description "Don't enable the OTU errored seconds threshold crossing alert";
             type empty;
           }
         }
         leaf threshold {
           description "TCA threshold for OTU errored seconds in 15 minutes";
           default "135";
           type union {
             type string {
               pattern "<.*>|$.*";
             }
             type uint32 {
               range "1 .. 900";
             }
           }
         }
         leaf threshold-24hrs {
           description "TCA threshold for OTU errored seconds in 24 hours";
           default "162";
           type union {
             type string {
               pattern "<.*>|$.*";
             }
             type uint32 {
               range "1 .. 86400";
             }
           }
         }
       }
       container otu-tca-ses {
         description "OTU Severely Errored Seconds Threshold crossing defect trigger";
         choice enable-tca-choice {
           leaf enable-tca {
             description "Enable the OTU severely errored seconds threshold crossing alert";
             type empty;
           }
           leaf no-enable-tca {
             description "Don't enable the OTU severely errored seconds threshold crossing alert";
             type empty;
           }
         }
         leaf threshold {
           description "TCA threshold for OTU severely errored seconds in 15 minutes";
           default "90";
           type union {
             type string {
               pattern "<.*>|$.*";
             }
             type uint32 {
               range "1 .. 900";
             }
           }
         }
         leaf threshold-24hrs {
           description "TCA threshold for OTU severely errored seconds in 24 hours";
           default "108";
           type union {
             type string {
               pattern "<.*>|$.*";
             }
             type uint32 {
               range "1 .. 86400";
             }
           }
         }
       }
       container otu-tca-uas {
         description "OTU Unavailable Seconds Threshold crossing defect trigger";
         choice enable-tca-choice {
           leaf enable-tca {
             description "Enable the OTU unavailable seconds threshold crossing alert";
             type empty;
           }
           leaf no-enable-tca {
             description "Don't enable the OTU unavailable seconds threshold crossing alert";
             type empty;
           }
         }
         leaf threshold {
           description "TCA threshold for OTU unavailable seconds in 15 minutes";
           default "90";
           type union {
             type string {
               pattern "<.*>|$.*";
             }
             type uint32 {
               range "10 .. 900";
             }
           }
         }
         leaf threshold-24hrs {
           description "TCA threshold for OTU unavailable seconds in 24 hours";
           default "108";
           type union {
             type string {
               pattern "<.*>|$.*";
             }
             type uint32 {
               range "10 .. 86400";
             }
           }
         }
       }
       container otu-tca-bbe {
         description "OTU Background Block Error Threshold crossing defect trigger";
         choice enable-tca-choice {
           leaf enable-tca {
             description "Enable the OTU BBE threshold crossing alert";
             type empty;
           }
           leaf no-enable-tca {
             description "Don't enable the OTU BBE threshold crossing alert";
             type empty;
           }
         }
         leaf threshold {
           description "TCA threshold for OTU BBE in 15 minutes";
           default "800";
           type union {
             type string {
               pattern "<.*>|$.*";
             }
             type uint32 {
               range "1 .. 771000000";
             }
           }
         }
         leaf threshold-24hrs {
           description "TCA threshold for OTU BBE in 24 hours";
           default "960";
           type union {
             type string {
               pattern "<.*>|$.*";
             }
             type uint32 {
               range "1 .. 771000000";
             }
           }
         }
       }
       container otu-tca-es-fe {
         description "OTU far-end Errored Seconds Threshold crossing defect trigger";
         choice enable-tca-choice {
           leaf enable-tca {
             description "Enable the OTU far-end errored seconds threshold crossing alert";
             type empty;
           }
           leaf no-enable-tca {
             description "Don't enable the OTU far-end errored seconds threshold crossing alert";
             type empty;
           }
         }
         leaf threshold {
           description "TCA threshold for OTU far-end errored seconds in 15 minutes";
           default "135";
           type union {
             type string {
               pattern "<.*>|$.*";
             }
             type uint32 {
               range "1 .. 900";
             }
           }
         }
         leaf threshold-24hrs {
           description "TCA threshold for OTU far-end errored seconds in 24 hours";
           default "162";
           type union {
             type string {
               pattern "<.*>|$.*";
             }
             type uint32 {
               range "1 .. 86400";
             }
           }
         }
       }
       container otu-tca-ses-fe {
         description "OTU far-end Severely Errored Seconds Threshold crossing defect trigger";
         choice enable-tca-choice {
           leaf enable-tca {
             description "Enable the OTU far-end Unavailable Seconds threshold crossing alert";
             type empty;
           }
           leaf no-enable-tca {
             description "Don't enable the OTU far-end Unavailable Seconds threshold crossing alert";
             type empty;
           }
         }
         leaf threshold {
           description "TCA threshold for OTU far-end severely errored seconds in 15 minutes";
           default "90";
           type union {
             type string {
               pattern "<.*>|$.*";
             }
             type uint32 {
               range "1 .. 900";
             }
           }
         }
         leaf threshold-24hrs {
           description "TCA threshold for OTU far-end severely errored seconds in 24 hours";
           default "108";
           type union {
             type string {
               pattern "<.*>|$.*";
             }
             type uint32 {
               range "1 .. 86400";
             }
           }
         }
       }
       container otu-tca-uas-fe {
         description "OTU far-end Unavailable Seconds Threshold crossing defect trigger";
         choice enable-tca-choice {
           leaf enable-tca {
             description "Enable the OTU far end unavailabe second threshold crossing alert";
             type empty;
           }
           leaf no-enable-tca {
             description "Don't enable the OTU far end unavailabe second threshold crossing alert";
             type empty;
           }
         }
         leaf threshold {
           description "TCA threshold for OTU far-end unavailable seconds in 15 minutes";
           default "90";
           type union {
             type string {
               pattern "<.*>|$.*";
             }
             type uint32 {
               range "10 .. 900";
             }
           }
         }
         leaf threshold-24hrs {
           description "TCA threshold for OTU far-end unavailable seconds in 24 hours";
           default "108";
           type union {
             type string {
               pattern "<.*>|$.*";
             }
             type uint32 {
               range "10 .. 86400";
             }
           }
         }
       }
       container otu-tca-bbe-fe {
         description "OTU far-end Background Block Error (BEI) Threshold crossing defect trigger";
         choice enable-tca-choice {
           leaf enable-tca {
             description "Enable the OTU BBE (BEI) threshold crossing alert";
             type empty;
           }
           leaf no-enable-tca {
             description "Don't enable the OTU BBE (BEI) threshold crossing alert";
             type empty;
           }
         }
         leaf threshold {
           description "TCA threshold for OTU far-end BBE (BEI) in 15 minutes";
           default "800";
           type union {
             type string {
               pattern "<.*>|$.*";
             }
             type uint32 {
               range "1 .. 771000000";
             }
           }
         }
         leaf threshold-24hrs {
           description "TCA threshold for OTU far-end BBE (BEI) in 24 hours";
           default "960";
           type union {
             type string {
               pattern "<.*>|$.*";
             }
             type uint32 {
               range "1 .. 771000000";
             }
           }
         }
       }
       container odu-tca-es {
         description "ODU Errored Seconds Threshold crossing defect trigger";
         choice enable-tca-choice {
           leaf enable-tca {
             description "Enable the ODU errored seconds threshold crossing alert";
             type empty;
           }
           leaf no-enable-tca {
             description "Don't enable the ODU errored seconds threshold crossing alert";
             type empty;
           }
         }
         leaf threshold {
           description "TCA threshold for ODU errored seconds in 15 minutes";
           default "135";
           type union {
             type string {
               pattern "<.*>|$.*";
             }
             type uint32 {
               range "1 .. 900";
             }
           }
         }
         leaf threshold-24hrs {
           description "TCA threshold for ODU errored seconds in 24 hours";
           default "162";
           type union {
             type string {
               pattern "<.*>|$.*";
             }
             type uint32 {
               range "1 .. 86400";
             }
           }
         }
       }
       container odu-tca-ses {
         description "ODU Severely Errored Seconds Threshold crossing defect trigger";
         choice enable-tca-choice {
           leaf enable-tca {
             description "Enable the ODU severely errored seconds threshold crossing alert";
             type empty;
           }
           leaf no-enable-tca {
             description "Don't enable the ODU severely errored seconds threshold crossing alert";
             type empty;
           }
         }
         leaf threshold {
           description "TCA threshold for ODU severely errored seconds in 15 minutes";
           default "90";
           type union {
             type string {
               pattern "<.*>|$.*";
             }
             type uint32 {
               range "1 .. 900";
             }
           }
         }
         leaf threshold-24hrs {
           description "TCA threshold for ODU severely-errored seconds in 24 hours";
           default "108";
           type union {
             type string {
               pattern "<.*>|$.*";
             }
             type uint32 {
               range "1 .. 86400";
             }
           }
         }
       }
       container odu-tca-uas {
         description "ODU Unavailable Seconds Threshold crossing defect trigger";
         choice enable-tca-choice {
           leaf enable-tca {
             description "Enable the ODU unavailable seconds threshold crossing alert";
             type empty;
           }
           leaf no-enable-tca {
             description "Don't enable the ODU unavailable seconds threshold crossing alert";
             type empty;
           }
         }
         leaf threshold {
           description "TCA threshold for ODU unavailable seconds in 15 minutes";
           default "90";
           type union {
             type string {
               pattern "<.*>|$.*";
             }
             type uint32 {
               range "10 .. 900";
             }
           }
         }
         leaf threshold-24hrs {
           description "TCA threshold for ODU unavailable seconds in 24 hours";
           default "108";
           type union {
             type string {
               pattern "<.*>|$.*";
             }
             type uint32 {
               range "10 .. 86400";
             }
           }
         }
       }
       container odu-tca-bbe {
         description "ODU Background Block Error Threshold crossing defect trigger";
         choice enable-tca-choice {
           leaf enable-tca {
             description "Enable the ODU BBE threshold crossing alert";
             type empty;
           }
           leaf no-enable-tca {
             description "Don't enable the ODU BBE threshold crossing alert";
             type empty;
           }
         }
         leaf threshold {
           description "TCA threshold for ODU BBE in 15 minutes";
           default "800";
           type union {
             type string {
               pattern "<.*>|$.*";
             }
             type uint32 {
               range "1 .. 771000000";
             }
           }
         }
         leaf threshold-24hrs {
           description "TCA threshold for ODU backgrand block error in 24 hours";
           default "960";
           type union {
             type string {
               pattern "<.*>|$.*";
             }
             type uint32 {
               range "1 .. 771000000";
             }
           }
         }
       }
       container odu-tca-es-fe {
         description "ODU far-end Errored Seconds Threshold crossing defect trigger";
         choice enable-tca-choice {
           leaf enable-tca {
             description "Enable the ODU far-end errored seconds threshold crossing alert";
             type empty;
           }
           leaf no-enable-tca {
             description "Don't enable the ODU far-end errored seconds threshold crossing alert";
             type empty;
           }
         }
         leaf threshold {
           description "TCA threshold for ODU far-end errored seconds in 15 minutes";
           default "135";
           type union {
             type string {
               pattern "<.*>|$.*";
             }
             type uint32 {
               range "1 .. 900";
             }
           }
         }
         leaf threshold-24hrs {
           description "TCA threshold for ODU far-end errored seconds in 24 hours";
           default "162";
           type union {
             type string {
               pattern "<.*>|$.*";
             }
             type uint32 {
               range "1 .. 86400";
             }
           }
         }
       }
       container odu-tca-ses-fe {
         description "ODU far-end Severely Errored Seconds Threshold crossing defect trigger";
         choice enable-tca-choice {
           leaf enable-tca {
             description "Enable the ODU far-end Unavailable Seconds threshold crossing alert";
             type empty;
           }
           leaf no-enable-tca {
             description "Don't enable the ODU far-end Unavailable Seconds threshold crossing alert";
             type empty;
           }
         }
         leaf threshold {
           description "TCA threshold for ODU far-end severely errored seconds in 15 minutes";
           default "90";
           type union {
             type string {
               pattern "<.*>|$.*";
             }
             type uint32 {
               range "1 .. 900";
             }
           }
         }
         leaf threshold-24hrs {
           description "TCA threshold for ODU severely-errored seconds in 24 hours";
           default "108";
           type union {
             type string {
               pattern "<.*>|$.*";
             }
             type uint32 {
               range "1 .. 86400";
             }
           }
         }
       }
       container odu-tca-uas-fe {
         description "ODU far-end Unavailable Seconds Threshold crossing defect trigger";
         choice enable-tca-choice {
           leaf enable-tca {
             description "Enable the ODU far end unavailabe second threshold crossing alert";
             type empty;
           }
           leaf no-enable-tca {
             description "Don't enable the ODU far end unavailabe second threshold crossing alert";
             type empty;
           }
         }
         leaf threshold {
           description "TCA threshold for ODU far-end unavailable seconds in 15 minutes";
           default "90";
           type union {
             type string {
               pattern "<.*>|$.*";
             }
             type uint32 {
               range "10 .. 900";
             }
           }
         }
         leaf threshold-24hrs {
           description "TCA threshold for ODU far-end unavailable seconds in 24 hours";
           default "108";
           type union {
             type string {
               pattern "<.*>|$.*";
             }
             type uint32 {
               range "10 .. 86400";
             }
           }
         }
       }
       container odu-tca-bbe-fe {
         description "ODU far-end Background Block Error (BEI) Threshold crossing defect trigger";
         choice enable-tca-choice {
           leaf enable-tca {
             description "Enable the ODU BBE (BEI) threshold crossing alert";
             type empty;
           }
           leaf no-enable-tca {
             description "Don't enable the ODU BBE (BEI) threshold crossing alert";
             type empty;
           }
         }
         leaf threshold {
           description "TCA threshold for ODU far-end BBE (BEI) in 15 minutes";
           default "800";
           type union {
             type string {
               pattern "<.*>|$.*";
             }
             type uint32 {
               range "1 .. 771000000";
             }
           }
         }
         leaf threshold-24hrs {
           description "TCA threshold for ODU far-end backgrand block error in 24 hours";
           default "960";
           type union {
             type string {
               pattern "<.*>|$.*";
             }
             type uint32 {
               range "1 .. 771000000";
             }
           }
         }
       }
       container otu-tca-fec-ber {
         description "OTU Errored Seconds Threshold crossing defect trigger";
         choice enable-tca-choice {
           leaf enable-tca {
             description "Enable the OTU errored seconds threshold crossing alert";
             type empty;
           }
           leaf no-enable-tca {
             description "Don't enable the OTU errored seconds threshold crossing alert";
             type empty;
           }
         }
         leaf threshold {
           description "TCA threshold for BER value in format: xe-n, x is an integer or decimal number, n = 0..9";
           default "10e-3";
           type string {
           }
         }
         leaf threshold-24hrs {
           description "TCA threshold for BER value in format: xe-n, x is an integer or decimal number, n = 0..9";
           default "10e-3";
           type string {
           }
         }
       }
     }
   }
   grouping ppp_options_type {
     uses apply-advanced;
     leaf dynamic-profile {
       description "Dynamic profile name";
       type string;
     }
     container chap {
       presence "enable chap";
       description "Challenge Handshake Authentication Protocol options";
       uses apply-advanced;
       choice access-data {
         case case_1 {
           leaf access-profile {
             description "Profile containing client list and access parameters";
             type string {
               length "1 .. 63";
             }
           }
         }
         case case_2 {
           leaf default-chap-secret {
             description "Default CHAP secret to be used when no matching access profile exists";
             type jt:unreadable;
           }
         }
       }
       leaf local-name {
         description "Name sent in CHAP-Challenge and CHAP-Response";
         type string;
       }
       leaf no-rfc2486 {
         description "RFC2486 compliance is not enforced";
         type empty;
       }
       leaf passive {
         description "Handle incoming CHAP requests only";
         type empty;
       }
     }
     container pap {
       presence "enable pap";
       description "Password Authentication Protocol options";
       uses apply-advanced;
       choice access-data {
         case case_1 {
           leaf access-profile {
             description "Profile containing client list and access parameters";
             type string {
               length "1 .. 63";
             }
           }
         }
         case case_2 {
           leaf default-password {
             description "Default PAP password used in the absence of matching profile";
             type jt:unreadable;
           }
         }
       }
       leaf local-name {
         description "Name sent in PAP request packet";
         type string;
       }
       leaf no-rfc2486 {
         description "RFC2486 compliance is not enforced";
         type empty;
       }
       leaf local-password {
         description "Password sent in PAP request packet";
         type jt:unreadable;
       }
       leaf passive {
         description "Do not handle PAP authentication requests";
         type empty;
       }
     }
     container compression {
       description "Set compression options";
       leaf acfc {
         description "Negotiate Address/Control field compression";
         type empty;
       }
       leaf pfc {
         description "Negotiate Protocol field compression";
         type empty;
       }
     }
     leaf lcp-restart-timer {
       description "LCP restart timer";
       units "milliseconds";
       type union {
         type string {
           pattern "<.*>|$.*";
         }
         type uint16 {
           range "20 .. 10000";
         }
       }
     }
     leaf ncp-restart-timer {
       description "NCP restart timer";
       units "milliseconds";
       type union {
         type string {
           pattern "<.*>|$.*";
         }
         type uint16 {
           range "500 .. 10000";
         }
       }
     }
     leaf no-termination-request {
       description "Don't send PPP termination requests";
       type empty;
     }
     leaf loopback-clear-timer {
       description "Loopback clear timer";
       units "seconds";
       type union {
         type string {
           pattern "<.*>|$.*";
         }
         type uint8 {
           range "1 .. 60";
         }
       }
     }
     leaf lcp-max-conf-req {
       description "Maximum LCP Conf-Req to be sent, 0 means infinite";
       type union {
         type string {
           pattern "<.*>|$.*";
         }
         type uint32 {
           range "0 .. 65535";
         }
       }
     }
     leaf ncp-max-conf-req {
       description "Maximum NCP Conf-Req to be sent, 0 means infinite";
       type union {
         type string {
           pattern "<.*>|$.*";
         }
         type uint32 {
           range "0 .. 65535";
         }
       }
     }
     leaf on-demand-ip-address {
       description "Enable On-Demand IPv4 address allocation and de-allocation";
       type empty;
     }
     leaf aaa-options {
       description "Attach AAA options name to dynamic-profile";
       type string {
         length "1 .. 63";
       }
     }
     container initiate-ncp {
       description "Enable server initiated NCP";
       uses apply-advanced;
       leaf ip {
         description "Enable server initiated IPNCP";
         type empty;
       }
       leaf ipv6 {
         description "Enable server initiated IPv6NCP";
         type empty;
       }
       leaf dual-stack-passive {
         description "Disable server initiated IPNCP/IPv6NCP for dual-stack client";
         type empty;
       }
     }
     leaf mtu {
       description "The Maximum Transfer Unit size in bytes";
       type string;
     }
     leaf peer-ip-address-optional {
       description "Set Peer IP Address Optional in IP NCP Negotiations";
       type empty;
     }
     leaf ipcp-suggest-dns-option {
       description "Suggest peer to negotiate with DNS Adresses options";
       type empty;
     }
   }
   grouping service_set_syslog_object {
     uses apply-advanced;
     list host {
       key name;
       ordered-by user;
       max-elements 10;
       leaf name {
         description "Name of host to notify";
         type string {
         }
       }
       uses apply-advanced;
       list contents {
         key name;
         leaf name {
           description "Facility type";
           type enumeration {
             enum "services" {
               description "Adaptive Services PIC";
             }
           }
         }
         choice level {
           case case_1 {
             leaf any {
               description "All levels";
               type empty;
             }
           }
           case case_2 {
             leaf emergency {
               description "Panic conditions";
               type empty;
             }
           }
           case case_3 {
             leaf alert {
               description "Conditions that should be corrected immediately";
               type empty;
             }
           }
           case case_4 {
             leaf critical {
               description "Critical conditions";
               type empty;
             }
           }
           case case_5 {
             leaf error {
               description "Error conditions";
               type empty;
             }
           }
           case case_6 {
             leaf warning {
               description "Warning messages";
               type empty;
             }
           }
           case case_7 {
             leaf notice {
               description "Conditions that should be handled specially";
               type empty;
             }
           }
           case case_8 {
             leaf info {
               description "Informational messages";
               type empty;
             }
           }
           case case_9 {
             leaf none {
               description "No messages";
               type empty;
             }
           }
         }
       }
       leaf facility-override {
         description "Alternate facility for logging to remote host";
         type enumeration {
           enum "authorization" {
             description "Authorization system";
           }
           enum "daemon" {
             description "Various system processes";
           }
           enum "ftp" {
             description "FTP process";
           }
           enum "kernel" {
             description "Kernel";
           }
           enum "user" {
             description "User processes";
           }
           enum "local0" {
             description "Local logging option number 0";
           }
           enum "local1" {
             description "Local logging option number 1";
           }
           enum "local2" {
             description "Local logging option number 2";
           }
           enum "local3" {
             description "Local logging option number 3";
           }
           enum "local4" {
             description "Local logging option number 4";
           }
           enum "local5" {
             description "Local logging option number 5";
           }
           enum "local6" {
             description "Local logging option number 6";
           }
           enum "local7" {
             description "Local logging option number 7";
           }
         }
       }
       leaf log-prefix {
         description "Prefix for all logging to this host";
         type string {
         }
       }
       leaf port {
         description "UDP port for syslogd on the host";
         type union {
           type string {
             pattern "<.*>|$.*";
           }
           type uint16 {
             range "1 .. 65535";
           }
         }
       }
       container class {
         description "Syslog messages classes";
         uses apply-advanced;
         container session-logs {
           presence "enable session-logs";
           description "Allow syslog messages for session events";
           uses apply-advanced;
           container open {
             presence "enable open";
             description "Allow syslog messages for session open events";
           }
           container close {
             presence "enable close";
             description "Allow syslog messages for session close events";
           }
         }
         container packet-logs {
           presence "enable packet-logs";
           description "Allow syslog messages for packet related events";
         }
         container stateful-firewall-logs {
           presence "enable stateful-firewall-logs";
           description "Allow syslog messages for stateful firewall events";
         }
         container alg-logs {
           presence "enable alg-logs";
           description "Allow syslog messages for ALG events";
         }
         container nat-logs {
           presence "enable nat-logs";
           description "Allow syslog messages for NAT events";
           uses apply-advanced;
           container deterministic-nat-configuration-log {
             presence "enable deterministic-nat-configuration-log";
             description "Allow syslog messages for Determinisitic NAT config events";
           }
         }
         container ids-logs {
           presence "enable ids-logs";
           description "Allow syslog messages for IDS events";
         }
         container pcp-logs {
           presence "enable pcp-logs";
           description "PCP logs";
           container map {
             presence "enable map";
             description "Allow syslog messages for PCP";
           }
           container debug {
             presence "enable debug";
             description "Allow PCP debug syslogs";
           }
         }
         container ha-logs {
           description "Stateful high availability logs";
           uses apply-advanced;
           container open-synchronized {
             presence "enable open-synchronized";
             description "Allow syslog message for session open events";
           }
           container close-synchronized {
             presence "enable close-synchronized";
             description "Allow syslog message for session close events";
           }
         }
       }
       leaf source-address {
         description "Use specified address as source address";
         type jt:ipv4addr;
       }
     }
     leaf message-rate-limit {
       description "Maximum syslog messages per second allowed from this interface. Applies per member if set at aggregate level";
       units "messages per second";
       type union {
         type string {
           pattern "<.*>|$.*";
         }
         type uint32 {
           range "0 .. 2147483647";
         }
       }
     }
   }
   grouping sonet_options_type {
     uses apply-advanced;
     leaf vtmapping {
       description "VT mapping mode";
       type enumeration {
         enum "klm" {
           description "KLM mode";
         }
         enum "itu-t" {
           description "ITU-T mode";
         }
       }
     }
     leaf fcs {
       description "Frame checksum";
       type enumeration {
         enum "32" {
           description "32-bit mode";
         }
         enum "16" {
           description "16-bit mode";
         }
       }
     }
     leaf path-trace {
       description "Path trace string";
       type string;
     }
     leaf loopback {
       description "Loopback mode";
       type enumeration {
         enum "local" {
           description "Local loopback";
         }
         enum "remote" {
           description "Remote loopback";
         }
       }
     }
     container trigger {
       description "Defect triggers";
       uses apply-advanced;
       container lol {
         description "LOL defect trigger";
         choice lol_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container pll {
         description "PLL defect trigger";
         choice pll_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container lof {
         description "LOF defect trigger";
         choice lof_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container los {
         description "LOS defect trigger";
         choice los_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ais-l {
         description "AIS-L defect trigger";
         choice ais_l_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container rfi-l {
         description "RFI-L defect trigger";
         choice rfi_l_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ber-sd {
         description "BER-SD defect trigger";
         uses apply-advanced;
         choice ber_sd_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ber-sf {
         description "BER-SF defect trigger";
         uses apply-advanced;
         choice ber_sf_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ais-p {
         description "AIS-P defect trigger";
         choice ais_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container lop-p {
         description "LOP-P defect trigger";
         choice lop_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container rfi-p {
         description "RFI-P defect trigger";
         choice rfi_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container uneq-p {
         description "UNEQ-P defect trigger";
         choice uneq_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container plm-p {
         description "PLM-P defect trigger";
         choice plm_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container locd {
         description "LOCD defect trigger (ATM only)";
         choice locd_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container lcdp {
         description "LCD-P defect trigger (Ethernet WAN only)";
         choice lcdp_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
     }
     container aps {
       description "Automatic Protection Switching";
       uses aps_type;
     }
     choice payload_scrambler_choices {
       case case_1 {
         container payload-scrambler {
           presence "enable payload-scrambler";
           description "Enable payload scrambling";
           choice payload-choice {
           }
         }
       }
       case case_2 {
         leaf no-payload-scrambler {
           description "Do not enable payload scrambling";
           type empty;
         }
       }
     }
     choice z0-increment-choice {
       leaf z0-increment {
         description "Increment Z0 in SDH mode";
         type empty;
       }
       leaf no-z0-increment {
         description "Don't increment Z0 in SDH mode";
         type empty;
       }
     }
     choice loop-timing-choice {
       leaf loop-timing {
         description "Set loop timing for STM-1";
         type empty;
       }
       leaf no-loop-timing {
         description "Don't set loop timing for STM-1";
         type empty;
       }
     }
     container bytes {
       description "Set SONET header bytes";
       uses apply-advanced;
       leaf e1-quiet {
         description "E1-quiet value";
         type union {
           type string {
             pattern "<.*>|$.*";
           }
           type uint32 {
             range "0 .. 255";
           }
         }
       }
       leaf f1 {
         description "F1 user value";
         type union {
           type string {
             pattern "<.*>|$.*";
           }
           type uint32 {
             range "0 .. 255";
           }
         }
       }
       leaf f2 {
         description "F2 user value";
         type union {
           type string {
             pattern "<.*>|$.*";
           }
           type uint32 {
             range "0 .. 255";
           }
         }
       }
       leaf s1 {
         description "S1/Z1 value (stratum clock by convention)";
         type union {
           type string {
             pattern "<.*>|$.*";
           }
           type uint32 {
             range "0 .. 255";
           }
         }
       }
       leaf z3 {
         description "Z3 user value";
         type union {
           type string {
             pattern "<.*>|$.*";
           }
           type uint32 {
             range "0 .. 255";
           }
         }
       }
       leaf z4 {
         description "Z4 user value";
         type union {
           type string {
             pattern "<.*>|$.*";
           }
           type uint32 {
             range "0 .. 255";
           }
         }
       }
       leaf c2 {
         description "C2 user value";
         type union {
           type string {
             pattern "<.*>|$.*";
           }
           type uint32 {
             range "0 .. 255";
           }
         }
       }
     }
     leaf rfc-2615 {
       description "RFC 2615 compliance";
       type empty;
     }
     leaf aggregate {
       description "Join a SONET aggregate";
       type union {
         type jt:interface-device;
         type string {
           pattern "<.*>|$.*";
         }
       }
     }
     container mpls {
       description "MPLS options";
       uses mpls_ifd_options;
     }
   }
   grouping vlan_map {
     description "IEEE 802.1q Virtual LAN (VLAN) Tag mapping";
     uses apply-advanced;
     choice operation_choices {
       case case_1 {
         leaf push {
           description "Push a VLAN tag";
           type empty;
         }
       }
       case case_2 {
         leaf swap {
           description "Swap a VLAN tag";
           type empty;
         }
       }
       case case_3 {
         leaf pop {
           description "Pop a VLAN tag";
           type empty;
         }
       }
       case case_4 {
         leaf push-push {
           description "Push two VLAN tags";
           type empty;
         }
       }
       case case_5 {
         leaf swap-push {
           description "Swap VLAN tag and push a new VLAN tag";
           type empty;
         }
       }
       case case_6 {
         leaf swap-swap {
           description "Swap both outer and inner VLAN tags";
           type empty;
         }
       }
       case case_7 {
         leaf pop-swap {
           description "Pop outer VLAN tag and swap inner VLAN tag";
           type empty;
         }
       }
       case case_8 {
         leaf pop-pop {
           description "Pop both outer and inner VLAN tags";
           type empty;
         }
       }
     }
     leaf tag-protocol-id {
       description "IEEE 802.1q Tag Protocol Identifier to rewrite";
       type string {
       }
     }
     leaf inner-tag-protocol-id {
       description "IEEE 802.1q Tag Protocol ID to rewrite for inner tag";
       type string {
       }
     }
     leaf vlan-id {
       description "VLAN ID to rewrite";
       type string;
     }
     leaf inner-vlan-id {
       description "VLAN ID to rewrite for inner tag";
       type string;
     }
   }
   grouping vrrp-group {
     description "Virtual Router Redundancy Protocol group";
     leaf name {
       description "Identifier for VRRP group";
       type union {
         type string {
           pattern "<.*>|$.*";
         }
         type uint32 {
           range "0 .. 255";
         }
       }
     }
     uses apply-advanced;
     choice address {
       case case_1 {
         leaf-list virtual-address {
           description "One or more virtual IPv4 addresses";
           type jt:ipv4addr;
         }
       }
       case case_2 {
         leaf-list virtual-inet6-address {
           description "One or more virtual inet6 addresses";
           type jt:ipv6addr;
         }
       }
     }
     leaf virtual-link-local-address {
       description "Virtual link-local addresses";
       type jt:ipv6addr;
     }
     leaf priority {
       description "Virtual router election priority";
       type union {
         type string {
           pattern "<.*>|$.*";
         }
         type uint32 {
           range "0 .. 255";
         }
       }
     }
     leaf preferred {
       description "Preferred group on subnet";
       type empty;
     }
     choice advertisement_type {
       case case_1 {
         leaf advertise-interval {
           description "Advertisement interval";
           units "seconds";
           type union {
             type string {
               pattern "<.*>|$.*";
             }
             type uint32 {
               range "1 .. 255";
             }
           }
         }
       }
       case case_2 {
         leaf fast-interval {
           description "Fast advertisement interval";
           units "milliseconds";
           type union {
             type string {
               pattern "<.*>|$.*";
             }
             type uint32 {
               range "10 .. 40950";
             }
           }
         }
       }
       case case_3 {
         leaf inet6-advertise-interval {
           description "Inet6 advertisement interval";
           units "milliseconds";
           type union {
             type string {
               pattern "<.*>|$.*";
             }
             type uint32 {
               range "100 .. 40000";
             }
           }
         }
       }
     }
     choice preempt_type {
       case case_1 {
         container preempt {
           presence "enable preempt";
           description "Allow preemption";
           uses apply-advanced;
           leaf hold-time {
             description "Preemption hold time";
             units "seconds";
             type union {
               type string {
                 pattern "<.*>|$.*";
               }
               type uint32 {
                 range "0 .. 3600";
               }
             }
           }
         }
       }
       case case_2 {
         leaf no-preempt {
           description "Don't allow preemption";
           type empty;
         }
       }
     }
     choice accept_type {
       case case_1 {
         leaf accept-data {
           description "Accept packets destined for virtual IP address";
           type empty;
         }
       }
       case case_2 {
         leaf no-accept-data {
           description "Don't accept packets destined for virtual IP address";
           type empty;
         }
       }
     }
     leaf authentication-type {
       description "Authentication type";
       type enumeration {
         enum "md5" {
           description "HMAC-MD5-96";
         }
         enum "simple" {
           description "Simple password";
         }
       }
     }
     leaf authentication-key {
       description "Authentication key";
       type jt:unreadable;
     }
     container track {
       description "Interfaces to track for VRRP group";
       uses apply-advanced;
       leaf priority-hold-time {
         description "Priority hold time";
         units "seconds";
         type union {
           type string {
             pattern "<.*>|$.*";
           }
           type uint32 {
             range "0 .. 3600";
           }
         }
       }
       list interface {
         key name;
         ordered-by user;
         description "Interface to track in VRRP group";
         leaf name {
           description "Name of interface";
           type union {
             type jt:interface-unit;
             type string {
               pattern "<.*>|$.*";
             }
           }
         }
         uses apply-advanced;
         list bandwidth-threshold {
           key name;
           description "Track bandwidth of interface";
           leaf name {
             description "Interface speed below which priority cost is incurred";
             units "bits per second";
             type string;
           }
           leaf priority-cost {
             description "Value subtracted from priority when bandwidth is below threshold";
             type union {
               type string {
                 pattern "<.*>|$.*";
               }
               type uint32 {
                 range "1 .. 254";
               }
             }
           }
         }
         leaf priority-cost {
           description "Value to subtract from priority when interface is down";
           type union {
             type string {
               pattern "<.*>|$.*";
             }
             type uint32 {
               range "1 .. 254";
             }
           }
         }
       }
       list route {
         key "route_address routing-instance";
         ordered-by user;
         description "Route to track in VRRP group";
         leaf route_address {
           description "Route address";
           type jt:ipprefix-mandatory;
         }
         leaf routing-instance {
           description "Routing instance to which route belongs, or 'default'";
           type string {
           }
         }
         leaf priority-cost {
           description "Value to subtract from priority when route is down";
           type union {
             type string {
               pattern "<.*>|$.*";
             }
             type uint32 {
               range "1 .. 254";
             }
           }
         }
       }
     }
     container vrrp-inherit-from {
       description "VRRP group to follow for this VRRP group";
       uses apply-advanced;
       leaf active-interface {
         description "Interface name of VRRP active group";
         type union {
           type jt:interface-unit;
           type string {
             pattern "<.*>|$.*";
           }
         }
       }
       leaf active-group {
         description "Identifier for VRRP active group";
         type union {
           type string {
             pattern "<.*>|$.*";
           }
           type uint32 {
             range "0 .. 255";
           }
         }
       }
     }
     leaf advertisements-threshold {
       description "Number of vrrp advertisements missed before declaring master down";
       type union {
         type string {
           pattern "<.*>|$.*";
         }
         type uint32 {
           range "1 .. 15";
         }
       }
     }
   }
 }
