/*
 * Copyright (c) 2017 Juniper Networks, Inc.
 * All rights reserved.
 */
 module junos-qfx-conf-access {
   namespace "http://yang.juniper.net/junos-qfx/conf/access";

   prefix jc-access;

   import junos-common-ddl-extensions {
     prefix junos;
   }

   import junos-common-types {
     prefix jt;
   }

   import junos-qfx-conf-root {
     prefix jc;
   }

   organization "Juniper Networks, Inc.";

   contact "yang-support@juniper.net";

   description "Junos access configuration module";

   revision 2017-01-01 {
     description "Junos: 17.4R1.16";
   }

   augment /jc:configuration {
     uses access-group;
   }
   augment /jc:configuration/jc:groups {
     uses access-group;
   }
   grouping access-group {
     container access {
       description "Network access configuration";
       uses juniper-access-options;
     }
   }
   grouping juniper-access-options {
     uses apply-advanced;
     list radius-server {
       key name;
       ordered-by user;
       description "RADIUS server configuration";
       uses access-radius-server-object;
     }
     list domain-name-server {
       key name;
       ordered-by user;
       description "Default DNS server's IPv4 address";
       leaf name {
         description "Address";
         type jt:ipv4addr;
       }
       uses apply-advanced;
     }
     list domain-name-server-inet {
       key name;
       ordered-by user;
       description "DNS server's IPv4 address";
       leaf name {
         description "Address";
         type jt:ipv4addr;
       }
       uses apply-advanced;
     }
     list domain-name-server-inet6 {
       key name;
       ordered-by user;
       description "DNS server's IPv6 address";
       leaf name {
         description "Address";
         type jt:ipv6addr;
       }
       uses apply-advanced;
     }
     list wins-server {
       key name;
       ordered-by user;
       description "Default WINS server's IPv4 address";
       leaf name {
         description "Address";
         type jt:ipv4addr;
       }
       uses apply-advanced;
     }
     list address-pool {
       key name;
       ordered-by user;
       description "Address pool";
       uses address-pool-object;
     }
     list group-profile {
       key name;
       ordered-by user;
       description "Group profile to use for this client";
       uses group-profile-object;
     }
     list profile {
       key name;
       ordered-by user;
       description "Set of attributes that define access";
       leaf name {
         description "Profile name";
         type string {
           length "1 .. 63";
         }
       }
       uses apply-advanced;
       leaf-list accounting-order {
         description "Order in which accounting mechanisms are used";
         junos:must "(!(any \".. client <*> l2tp\"))";
         junos:must-message "Not supported in tunnel client profile configuration";
         junos:must "(!(any \".. client <*> ike\"))";
         junos:must-message "Not supported in IKE configuration";
         type enumeration {
           enum "radius" {
             description "Remote Authentication Dial-In User Service";
           }
         }
       }
       leaf-list authentication-order {
         description "Order in which authentication mechanisms are used";
         junos:must "(!(any \".. client <*> ike\"))";
         junos:must-message "Not supported in IKE configuration";
         type enumeration {
           enum "radius" {
             description "Remote Authentication Dial-In User Service";
             junos:must "(!(any \".. .. client <*> l2tp\"))";
             junos:must-message "Authentication-order cannot include RADIUS for tunnel client profile";
           }
           enum "password" {
             description "Locally configured password in access profile";
           }
           enum "none" {
             description "No authentication performed";
           }
           enum "nasreq" {
             description "Diameter based authentication and authorization using NASREQ application protocol";
           }
           enum "ldap" {
             description "Lightweight Directory Access Protocol";
             junos:must "((!(any \".. .. client <*> l2tp\") && !(any \".. .. client <*> ppp\")))";
             junos:must-message "Authentication-order cannot include LDAP for tunnel, ppp client profile";
             junos:must "((!(\".. .. authentication-order $$={radius}\") && !(\".. .. authentication-order $$={securid}\")))";
             junos:must-message "Only one of ldap, radius or securid can be specified";
           }
           enum "securid" {
             description "RSA SecurID Authentication";
             junos:must "((!(any \".. .. client <*> l2tp\") && !(any \".. .. client <*> ppp\")))";
             junos:must-message "Authentication-order cannot include securid for tunnel, ppp client profile";
             junos:must "((!(\".. .. authentication-order $$={radius}\") && !(\".. .. authentication-order $$={ldap}\")))";
             junos:must-message "Only one of ldap, radius or securid can be specified";
           }
         }
       }
       leaf-list authorization-order {
         description "Order in which authorization mechanisms are used";
         type enumeration {
           enum "jsrc" {
             description "Diameter based authorization using Juniper's SRC application protocol";
           }
           enum "nasreq" {
             description "Diameter based authorization using NASREQ application protocol";
           }
           enum "none" {
             description "No authorization performed";
           }
         }
       }
       leaf provisioning-order {
         description "Order in which provisioning mechanisms are used";
         type enumeration {
           enum "jsrc" {
             description "Address authorization via SRC";
           }
           enum "gx-plus" {
             description "Policy/service provisioning via GXPLUS";
           }
           enum "pcrf" {
             description "Policy/service provisioning via PCRF";
           }
         }
       }
       leaf-list preauthentication-order {
         description "Order in which preauthentication mechanisms are used";
         junos:must "(!(\".. radius attributes exclude calling-station-id access-request\"))";
         junos:must-message "calling-station-id is excluded from access request";
         type enumeration {
           enum "radius" {
             description "Remote Authentication Dial-In User Service";
           }
         }
       }
       leaf-list charging-service-list {
         description "List of used 3gpp charging servicess";
         junos:must "(\".. provisioning-order pcrf\")";
         junos:must-message "charging-service-list requires provisioning-order pcrf";
         junos:must "(!(\".. service accounting-order\"))";
         junos:must-message "charging-service-list is mutually exclusive with service accounting";
         type enumeration {
           enum "ocs" {
             description "Online charging service";
           }
         }
       }
       list domain-name-server {
         key name;
         ordered-by user;
         description "Default DNS server's IPv4 address";
         leaf name {
           description "Address";
           type jt:ipv4addr;
         }
         uses apply-advanced;
       }
       list domain-name-server-inet {
         key name;
         ordered-by user;
         description "DNS server's IPv4 address";
         leaf name {
           description "Address";
           type jt:ipv4addr;
         }
         uses apply-advanced;
       }
       list domain-name-server-inet6 {
         key name;
         ordered-by user;
         description "DNS server's IPv6 address";
         leaf name {
           description "Address";
           type jt:ipv6addr;
         }
         uses apply-advanced;
       }
       list wins-server {
         key name;
         ordered-by user;
         description "Default WINS server's IPv4 address";
         leaf name {
           description "Address";
           type jt:ipv4addr;
         }
         uses apply-advanced;
       }
       list client {
         key name;
         description "Entity requesting access";
         junos:must "(((!(any \". <*> l2tp\") || !(any \". <*> ppp\")) && ((!(any \". <*> l2tp\") || !(any \". <*> ike\")) && (!(any \". <*> ike\") || !(any \". <*> ppp\")))))";
         junos:must-message "All clients in one profile must be either PPP or L2TP or IKE";
         uses access-client-object;
       }
       container address-assignment {
         description "Address assignment pool";
         uses apply-advanced;
         leaf pool {
           description "Name of address-assignment pool";
           junos:must "(\"access address-assignment pool $$\")";
           junos:must-message "Address assignment pool must be defined in the [edit access address-assignment pool] hierarchy";
           type string {
             length "1 .. 63";
           }
         }
       }
       container local {
         description "Set configuration for local reporting";
         uses apply-advanced;
         leaf flat-file-profile {
           description "Specifies that the service accounting will be reported as per flat-file profile";
           junos:must "(\"accounting-options flat-file-profile $$\")";
           junos:must-message "referenced flat-file-profile must be defined in accounting-options";
           type string;
         }
       }
       container radius {
         description "Set of RADIUS configurations";
         uses apply-advanced;
         leaf-list authentication-server {
           description "The authentication server list to use in the specified order to send authentication messages";
           type jt:ipaddr;
         }
         leaf-list accounting-server {
           description "The accounting server list to use in the specified order to send accounting messages";
           type jt:ipaddr;
         }
         leaf-list preauthentication-server {
           description "The preauthentication server list to use in the specified order to send preauthentication messages";
           type jt:ipv4addr;
         }
         container options {
           description "Specifies the RADIUS options";
           uses apply-advanced;
           leaf ethernet-port-type-virtual {
             description "Type of physical port to authenticate the user is virtual (RADIUS attribute 61)";
             type empty;
           }
           container interface-description-format {
             description "Interface description in the NAS-port-ID attribute";
             uses apply-advanced;
             leaf exclude-sub-interface {
               description "Exclude sub-interface from interface description";
               type empty;
             }
             leaf exclude-adapter {
               description "Exclude adapter from interface description";
               type empty;
             }
             leaf exclude-channel {
               description "Exclude channel from interface description";
               type empty;
             }
           }
           leaf nas-identifier {
             description "NAS-Identifier to be used for authentication and accounting requests (RADIUS attribute 32)";
             type string {
               length "1 .. 64";
             }
           }
           container nas-port-extended-format {
             description "RADIUS client's use of an extended format for RADIUS attribute 5";
             uses apply-advanced;
             leaf ae-width {
               description "Number of bits for the aggregated ethernet identifier field";
               units "bits";
               type union {
                 type string {
                   pattern "<.*>|$.*";
                 }
                 type uint32 {
                   range "0 .. 32";
                 }
               }
             }
             leaf slot-width {
               description "Number of bits for the slot field";
               units "bits";
               type union {
                 type string {
                   pattern "<.*>|$.*";
                 }
                 type uint32 {
                   range "0 .. 32";
                 }
               }
             }
             leaf adapter-width {
               description "Number of bits for the adapter field";
               units "bits";
               type union {
                 type string {
                   pattern "<.*>|$.*";
                 }
                 type uint32 {
                   range "0 .. 32";
                 }
               }
             }
             leaf port-width {
               description "Number of bits for the port field";
               units "bits";
               type union {
                 type string {
                   pattern "<.*>|$.*";
                 }
                 type uint32 {
                   range "0 .. 32";
                 }
               }
             }
             leaf pw-width {
               description "Number of bits for the pseudo-wire field";
               units "bits";
               type union {
                 type string {
                   pattern "<.*>|$.*";
                 }
                 type uint32 {
                   range "0 .. 32";
                 }
               }
             }
             leaf stacked-vlan-width {
               description "Number of bits for the S-VLAN subinterface field";
               units "bits";
               type union {
                 type string {
                   pattern "<.*>|$.*";
                 }
                 type uint32 {
                   range "0 .. 32";
                 }
               }
             }
             leaf vlan-width {
               description "Number of bits for the VLAN subinterface field";
               units "bits";
               type union {
                 type string {
                   pattern "<.*>|$.*";
                 }
                 type uint32 {
                   range "0 .. 32";
                 }
               }
             }
             container atm {
               description "ATM specific parameters for NAS Port";
               uses apply-advanced;
               leaf slot-width {
                 description "Number of bits for the ATM slot field";
                 units "bits";
                 type union {
                   type string {
                     pattern "<.*>|$.*";
                   }
                   type uint32 {
                     range "0 .. 32";
                   }
                 }
               }
               leaf adapter-width {
                 description "Number of bits for the ATM adapter field";
                 units "bits";
                 type union {
                   type string {
                     pattern "<.*>|$.*";
                   }
                   type uint32 {
                     range "0 .. 32";
                   }
                 }
               }
               leaf port-width {
                 description "Number of bits for the ATM port field";
                 units "bits";
                 type union {
                   type string {
                     pattern "<.*>|$.*";
                   }
                   type uint32 {
                     range "0 .. 32";
                   }
                 }
               }
               leaf vpi-width {
                 description "Number of bits for the ATM VPI field";
                 units "bits";
                 type union {
                   type string {
                     pattern "<.*>|$.*";
                   }
                   type uint32 {
                     range "0 .. 32";
                   }
                 }
               }
               leaf vci-width {
                 description "Number of bits for the ATM VCI field";
                 units "bits";
                 type union {
                   type string {
                     pattern "<.*>|$.*";
                   }
                   type uint32 {
                     range "0 .. 32";
                   }
                 }
               }
             }
           }
           leaf nas-port-id-delimiter {
             description "Single character delimiter character to use in the NAS-Port-Id";
             type string {
               length 1;
             }
           }
           container nas-port-id-format {
             description "Format methods for building the NAS-Port-Id radius attribute";
             uses apply-advanced;
             leaf nas-identifier {
               description "Include the nas-identifier value";
               type empty;
             }
             leaf interface-description {
               description "Include the interface-description value";
               type empty;
             }
             leaf agent-circuit-id {
               description "Include (ACI) agent-circuit-id value";
               type empty;
             }
             leaf agent-remote-id {
               description "Include (ARI) agent-remote-id value";
               type empty;
             }
             leaf postpend-vlan-tags {
               description "Include the vlan tag(s) using :<outer>-<inner>";
               type empty;
             }
             leaf interface-text-description {
               description "Include the interfaces description string";
               type empty;
             }
             leaf-list order {
               description "Order of options for appearance in the NAS-Port-Id string";
               junos:must "((!(\".. nas-identifier\") && (!(\".. interface-description\") && (!(\".. agent-circuit-id\") && (!(\".. agent-remote-id\") && (!(\".. postpend-vlan-tags\") && !(\".. interface-text-description\")))))))";
               junos:must-message "Order is mutually exclusive with other nas-port-id-format options";
               type enumeration {
                 enum "nas-identifier" {
                   description "Include the nas-identifier value";
                 }
                 enum "agent-circuit-id" {
                   description "Include (ACI) agent-circuit-id value";
                 }
                 enum "agent-remote-id" {
                   description "Include (ARI) agent-remote-id value";
                 }
                 enum "interface-description" {
                   description "Include the interface-description value";
                 }
                 enum "interface-text-description" {
                   description "Include the interface's description string";
                 }
                 enum "postpend-vlan-tags" {
                   description "Include the vlan tag(s) using :<outer>-<inner>";
                 }
               }
             }
           }
           container nas-port-type {
             description "Translation mechanism for changing the NAS-Port-Type radius attribute";
             uses apply-advanced;
             leaf ethernet {
               description "Translation mechanism for changing the Ethernet value";
               type string;
             }
           }
           leaf calling-station-id-delimiter {
             description "Single character separator for calling-station-id";
             type string {
               length 1;
             }
           }
           container calling-station-id-format {
             description "Format method for building the calling-station-id";
             uses apply-advanced;
             leaf nas-identifier {
               description "Include the nas-identifier value";
               type empty;
             }
             leaf interface-description {
               description "Include the interface-description value";
               type empty;
             }
             leaf agent-circuit-id {
               description "Include agent-circuit-id value";
               type empty;
             }
             leaf agent-remote-id {
               description "Include agent-remote-id value";
               type empty;
             }
             leaf interface-text-description {
               description "Include the interfaces description string";
               type empty;
             }
             leaf stacked-vlan {
               description "Include the stacked vlan tag value";
               type empty;
             }
             leaf vlan {
               description "Include the vlan tag value";
               type empty;
             }
           }
           leaf accounting-session-id-format {
             description "Decimal format or description format for the accounting session ID";
             type enumeration {
               enum "decimal" {
                 description "Decimal-session-identifier";
               }
               enum "description" {
                 description "Description Format: <jnpr> <interface-type> <interface-specifier>:<session-identifier>";
               }
             }
           }
           leaf revert-interval {
             description "Time after which to revert to primary server";
             units "seconds";
             type union {
               type string {
                 pattern "<.*>|$.*";
               }
               type uint32 {
                 range "0 .. 604800";
               }
             }
           }
           leaf vlan-nas-port-stacked-format {
             description "Include the S-VLAN ID, in addition to the VLAN ID, for subscribers on Ethernet interfaces";
             type empty;
           }
           leaf client-authentication-algorithm {
             description "Algorithm to access the RADIUS servers for authentication";
             type enumeration {
               enum "direct" {
                 description "Contacts the first AAA server on the list for each request, the second AAA server if the first one fails, and so on";
               }
               enum "round-robin" {
                 description "Contacts the first AAA server for the first request, the second AAA server for the second request, and so on";
               }
             }
           }
           leaf client-accounting-algorithm {
             description "Algorithm to access the RADIUS servers for accounting";
             type enumeration {
               enum "direct" {
                 description "Contacts the first AAA server on the list for each request, the second AAA server if the first one fails, and so on";
               }
               enum "round-robin" {
                 description "Contacts the first AAA server for the first request, the second AAA server for the second request, and so on";
               }
             }
           }
           leaf juniper-dsl-attributes {
             description "Include the Juniper (IANA 4874) DSL VSAs in requests to RADIUS servers";
             type empty;
           }
           container ip-address-change-notify {
             presence "enable ip-address-change-notify";
             junos:must "(\".. .. .. accounting address-change-immediate-update\")";
             junos:must-message "address-change-immediate-update must be configured";
             description "Include IPv4-Release-Control VSA (26-164) in requests to RADIUS server";
             leaf message {
               description "Message to be added in IPv4-Release-Control VSA (26-164)";
               type string {
                 length "1 .. 32";
               }
             }
           }
           leaf coa-dynamic-variable-validation {
             description "Enable strict dynamic variable validation (no undefined variable) in CoA processing";
             type empty;
           }
           leaf chap-challenge-in-request-authenticator {
             description "Use 16-byte CHAP challenge as Request Authenticator";
             type empty;
           }
           container service-activation {
             description "Service activation requirement for successful login";
             uses apply-advanced;
             leaf extensible-service {
               description "Service activation of extensible services requirement for successful login";
               default "optional-at-login";
               type enumeration {
                 enum "required-at-login" {
                   description "Service activation must succeed to allow subscriber login";
                 }
                 enum "optional-at-login" {
                   description "Service activation success is not required to allow subscriber login";
                 }
               }
             }
             leaf dynamic-profile {
               description "Service activation of dynamic-profile services requirement for successful login";
               default "required-at-login";
               type enumeration {
                 enum "required-at-login" {
                   description "Service activation must succeed to allow subscriber login";
                 }
                 enum "optional-at-login" {
                   description "Service activation success is not required to allow subscriber login";
                 }
               }
             }
           }
           leaf accounting-username-original {
             description "Use orignal (un-modified) username in accounting messages";
             type empty;
           }
         }
         container attributes {
           description "Specifies how RADIUS attributes should be handled";
           uses apply-advanced;
           container ignore {
             description "Ignores the specified attribute in RADIUS Access-Accept messages";
             uses apply-advanced;
             leaf output-filter {
               description "Output-filter/egress-Policy-Name (VSA 26-11)";
               type empty;
             }
             leaf input-filter {
               description "Input-filter/ingress-Policy-Name (VSA 26-10)";
               type empty;
             }
             leaf framed-ip-netmask {
               description "Framed-ip-netmask/framed-Ip-Netmask (attribute 9)";
               type empty;
             }
             leaf logical-system-routing-instance {
               description "Logical-system-routing-instance/virtual-Router (VSA 26-1)";
               type empty;
             }
             leaf dynamic-iflset-name {
               description "Interface-set/Dynamic-Iflset-name (VSA 26-130)";
               type empty;
             }
           }
           container exclude {
             description "Configures the exclusion of RADIUS attributes in RADIUS messages";
             uses apply-advanced;
             leaf-list accounting-authentic {
               description "Excludes RADIUS attribute 45, Acct-Authentic";
               type enumeration {
                 enum "accounting-on" {
                   description "RADIUS Accounting-On Message";
                 }
                 enum "accounting-off" {
                   description "RADIUS Accounting-Off message";
                 }
                 enum "accounting-start" {
                   description "RADIUS Accounting-Start message";
                 }
                 enum "accounting-stop" {
                   description "RADIUS Accounting-Stop message";
                 }
               }
             }
             leaf-list accounting-delay-time {
               description "Excludes RADIUS attribute 41, Acct-Delay-Time";
               type enumeration {
                 enum "accounting-on" {
                   description "RADIUS Accounting-On Message";
                 }
                 enum "accounting-off" {
                   description "RADIUS Accounting-Off message";
                 }
                 enum "accounting-start" {
                   description "RADIUS Accounting-Start message";
                 }
                 enum "accounting-stop" {
                   description "RADIUS Accounting-Stop message";
                 }
               }
             }
             leaf-list accounting-session-id {
               description "Excludes RADIUS attribute 44, Acct-Session-ID";
               type enumeration {
                 enum "access-request" {
                   description "RADIUS Access-Request message";
                 }
               }
             }
             leaf-list accounting-terminate-cause {
               description "Excludes RADIUS attribute 49, Acct-Terminate-Cause";
               type enumeration {
                 enum "accounting-off" {
                   description "RADIUS Accounting-Off message";
                 }
               }
             }
             leaf-list called-station-id {
               description "Excludes RADIUS attribute 30, Called-Station-ID";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list calling-station-id {
               description "Excludes RADIUS attribute 31, Calling-Station-ID";
               type enumeration {
                 enum "access-request" {
                   description "RADIUS Access-Request message";
                   junos:must "(!(\".. .. .. .. .. preauthentication-order\"))";
                   junos:must-message "Preauthentication-order and exclude calling-station-id in access-request are mutually exclusive";
                 }
                 enum "accounting-start" {
                   description "RADIUS Accounting-Start message";
                 }
                 enum "accounting-stop" {
                   description "RADIUS Accounting-Stop message";
                 }
               }
             }
             leaf-list class {
               description "Excludes RADIUS attribute 25, Class";
               type enumeration {
                 enum "accounting-start" {
                   description "RADIUS Accounting-Start message";
                 }
                 enum "accounting-stop" {
                   description "RADIUS Accounting-Stop message";
                 }
               }
             }
             leaf-list delegated-ipv6-prefix {
               description "Excludes RADIUS attribute 123, Delegated-IPv6-Prefix";
               type enumeration {
                 enum "accounting-start" {
                   description "RADIUS Accounting-Start message";
                 }
                 enum "accounting-stop" {
                   description "RADIUS Accounting-Stop message";
                 }
               }
             }
             leaf-list dhcp-options {
               description "Excludes RADIUS attribute 26-55, DHCP-Options";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list dhcp-gi-address {
               description "Excludes RADIUS attribute 26-57, DHCP-GI-Address";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list dhcp-mac-address {
               description "Excludes RADIUS attribute 26-56, DHCP-MAC-Address";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list output-filter {
               description "Excludes RADIUS attribute 26-11, Egress-Policy-Name";
               type enumeration {
                 enum "accounting-start" {
                   description "RADIUS Accounting-Start message";
                 }
                 enum "accounting-stop" {
                   description "RADIUS Accounting-Stop message";
                 }
               }
             }
             leaf-list event-time-stamp {
               description "Excludes RADIUS attribute 55, Event-Timestamp";
               type enumeration {
                 enum "accounting-on" {
                   description "RADIUS Accounting-On Message";
                 }
                 enum "accounting-off" {
                   description "RADIUS Accounting-Off message";
                 }
                 enum "accounting-start" {
                   description "RADIUS Accounting-Start message";
                 }
                 enum "accounting-stop" {
                   description "RADIUS Accounting-Stop message";
                 }
               }
             }
             leaf-list filter-id {
               description "Excludes RADIUS attribute 11, Filter-Id";
               type enumeration {
                 enum "accounting-start" {
                   description "RADIUS Accounting-Start message";
                 }
                 enum "accounting-stop" {
                   description "RADIUS Accounting-Stop message";
                 }
               }
             }
             leaf-list framed-ip-address {
               description "Excludes RADIUS attribute 8, Framed-IP-Address";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list framed-ip-netmask {
               description "Excludes RADIUS attribute 9, Framed-IP-Netmask";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list framed-ip-route {
               description "Excludes RADIUS attribute 22, Framed-Route";
               type enumeration {
                 enum "accounting-start" {
                   description "RADIUS Accounting-Start message";
                 }
                 enum "accounting-stop" {
                   description "RADIUS Accounting-Stop message";
                 }
               }
             }
             leaf-list framed-ipv6-address {
               description "Excludes RADIUS attribute 168, Framed-IPV6-Address";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list framed-ipv6-pool {
               description "Excludes RADIUS attribute 100, Framed-IPv6-Pool";
               type enumeration {
                 enum "accounting-start" {
                   description "RADIUS Accounting-Start message";
                 }
                 enum "accounting-stop" {
                   description "RADIUS Accounting-Stop message";
                 }
               }
             }
             leaf-list framed-ipv6-prefix {
               description "Excludes RADIUS attribute 97, Framed-IPv6-Prefix";
               type enumeration {
                 enum "accounting-start" {
                   description "RADIUS Accounting-Start message";
                 }
                 enum "accounting-stop" {
                   description "RADIUS Accounting-Stop message";
                 }
               }
             }
             leaf-list framed-ipv6-route {
               description "Excludes RADIUS attribute 99, Framed-IPv6-Route";
               type enumeration {
                 enum "accounting-start" {
                   description "RADIUS Accounting-Start message";
                 }
                 enum "accounting-stop" {
                   description "RADIUS Accounting-Stop message";
                 }
               }
             }
             leaf-list framed-pool {
               description "Excludes RADIUS attribute 88, Framed-Pool";
               type enumeration {
                 enum "accounting-start" {
                   description "RADIUS Accounting-Start message";
                 }
                 enum "accounting-stop" {
                   description "RADIUS Accounting-Stop message";
                 }
               }
             }
             leaf-list input-filter {
               description "Excludes RADIUS attribute 26-10, Ingress-Policy-Name";
               type enumeration {
                 enum "accounting-start" {
                   description "RADIUS Accounting-Start message";
                 }
                 enum "accounting-stop" {
                   description "RADIUS Accounting-Stop message";
                 }
               }
             }
             leaf-list input-gigapackets {
               description "Excludes Juniper (IANA 4874) VSA  26-42, Acct-Input-Gigapackets";
               type enumeration {
                 enum "accounting-stop" {
                   description "RADIUS Accounting-Stop message";
                 }
               }
             }
             leaf-list input-gigawords {
               description "Excludes RADIUS attribute 52, Acct-Input-Gigawords";
               type enumeration {
                 enum "accounting-stop" {
                   description "RADIUS Accounting-Stop message";
                 }
               }
             }
             leaf-list input-ipv6-packets {
               description "Excludes Juniper (IANA 4874) VSA  26-153, Acct-Input-IPv6-Packets";
               type enumeration {
                 enum "accounting-stop" {
                   description "RADIUS Accounting-Stop message";
                 }
               }
             }
             leaf-list input-ipv6-gigawords {
               description "Excludes Juniper (IANA 4874) VSA  26-155, Acct-Input-IPv6-Gigawords";
               type enumeration {
                 enum "accounting-stop" {
                   description "RADIUS Accounting-Stop message";
                 }
               }
             }
             leaf-list input-ipv6-octets {
               description "Excludes Juniper (IANA 4874) VSA  26-151, Acct-Input-IPv6-Octets";
               type enumeration {
                 enum "accounting-stop" {
                   description "RADIUS Accounting-Stop message";
                 }
               }
             }
             leaf-list interface-description {
               description "Excludes RADIUS attribute 26-63, Interface-Desc";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list nas-identifier {
               description "Excludes RADIUS attribute 32, NAS-identifier";
               type enumeration {
                 enum "access-request" {
                   description "RADIUS Access-Request message";
                 }
                 enum "accounting-on" {
                   description "RADIUS Accounting-On Message";
                 }
                 enum "accounting-off" {
                   description "RADIUS Accounting-Off message";
                 }
                 enum "accounting-start" {
                   description "RADIUS Accounting-Start message";
                 }
                 enum "accounting-stop" {
                   description "RADIUS Accounting-Stop message";
                 }
               }
             }
             leaf-list nas-port {
               description "Excludes RADIUS attribute 5, NAS-Port";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list nas-port-id {
               description "Excludes RADIUS attribute 87, NAS-Port-ID";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list nas-port-type {
               description "Excludes RADIUS attribute 61, NAS-Port-Type";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list output-gigapackets {
               description "Excludes Juniper (IANA 4874) VSA  26-43, Acct-Output-Gigapackets";
               type enumeration {
                 enum "accounting-stop" {
                   description "RADIUS Accounting-Stop message";
                 }
               }
             }
             leaf-list output-gigawords {
               description "Excludes RADIUS attribute 53, Acct-Output-Gigawords";
               type enumeration {
                 enum "accounting-stop" {
                   description "RADIUS Accounting-Stop message";
                 }
               }
             }
             leaf-list output-ipv6-packets {
               description "Excludes Juniper (IANA 4874) VSA  26-154, Acct-Output-IPv6-Packets";
               type enumeration {
                 enum "accounting-stop" {
                   description "RADIUS Accounting-Stop message";
                 }
               }
             }
             leaf-list output-ipv6-gigawords {
               description "Excludes Juniper (IANA 4874) VSA  26-156, Acct-Output-IPv6-Gigawords";
               type enumeration {
                 enum "accounting-stop" {
                   description "RADIUS Accounting-Stop message";
                 }
               }
             }
             leaf-list output-ipv6-octets {
               description "Excludes Juniper (IANA 4874) VSA  26-152, Acct-Output-IPv6-Octets";
               type enumeration {
                 enum "accounting-stop" {
                   description "RADIUS Accounting-Stop message";
                 }
               }
             }
             leaf-list dynamic-iflset-name {
               description "Excludes RADIUS attribute 26-130, Dynamic-Iflset-Name";
               type enumeration {
                 enum "accounting-start" {
                   description "RADIUS Accounting-Start message";
                 }
                 enum "accounting-stop" {
                   description "RADIUS Accounting-Stop message";
                 }
               }
             }
             leaf-list dsl-forum-attributes {
               description "Excludes DSL Forum RADIUS attributes (RFC 4679)";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list l2c-upstream-data {
               description "Excludes Juniper (IANA 4874) DSL VSA 26-92, L2C-Upstream-Data";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list l2c-downstream-data {
               description "Excludes Juniper (IANA 4874) DSL VSA 26-93, L2C-Downstream-Data";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list acc-loop-cir-id {
               description "Excludes Juniper (IANA 4874) DSL VSA 26-110, Acc-Loop-Cir-Id";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list acc-aggr-cir-id-bin {
               description "Excludes Juniper (IANA 4874) DSL VSA 26-111, Acc-Aggr-Cir-Id-Bin";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list acc-aggr-cir-id-asc {
               description "Excludes Juniper (IANA 4874) DSL VSA 26-112, Acc-Aggr-Cir-Id-Asc";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list act-data-rate-up {
               description "Excludes Juniper (IANA 4874) DSL VSA 26-113, Act-Data-Rate-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list act-data-rate-dn {
               description "Excludes Juniper (IANA 4874) DSL VSA 26-114, Act-Data-Rate-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list min-data-rate-up {
               description "Excludes Juniper (IANA 4874) DSL VSA 26-115, Min-Data-Rate-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list min-data-rate-dn {
               description "Excludes Juniper (IANA 4874) DSL VSA 26-116, Min-Data-Rate-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list att-data-rate-up {
               description "Excludes Juniper (IANA 4874) DSL VSA 26-117, Att-Data-Rate-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list att-data-rate-dn {
               description "Excludes Juniper (IANA 4874) DSL VSA 26-118, Att-Data-Rate-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list max-data-rate-up {
               description "Excludes Juniper (IANA 4874) DSL VSA 26-119, Max-Data-Rate-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list max-data-rate-dn {
               description "Excludes Juniper (IANA 4874) DSL VSA 26-120, Max-Data-Rate-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list min-lp-data-rate-up {
               description "Excludes Juniper (IANA 4874) DSL VSA 26-121, Min-Lp-Data-Rate-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list min-lp-data-rate-dn {
               description "Excludes Juniper (IANA 4874) DSL VSA 26-122, Min-Lp-Data-Rate-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list max-interlv-delay-up {
               description "Excludes Juniper (IANA 4874) DSL VSA 26-123, Max-Interlv-Delay-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list act-interlv-delay-up {
               description "Excludes Juniper (IANA 4874) DSL VSA 26-124, Act-Interlv-Delay-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list max-interlv-delay-dn {
               description "Excludes Juniper (IANA 4874) DSL VSA 26-125, Max-Interlv-Delay-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list act-interlv-delay-dn {
               description "Excludes Juniper (IANA 4874) DSL VSA 26-126, Act-Interlv-Delay-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list dsl-line-state {
               description "Excludes Juniper (IANA 4874) DSL VSA 26-127, DSL-Line-State";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list dsl-type {
               description "Excludes Juniper (IANA 4874) DSL VSA 26-128, DSL-Type";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list downstream-calculated-qos-rate {
               description "Excludes Juniper (IANA 4874) DSL VSA 26-141, Downstream-Calculated-QoS-Rate";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list upstream-calculated-qos-rate {
               description "Excludes Juniper (IANA 4874) DSL VSA 26-142, Upstream-Calculated-QoS-Rate";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list cos-shaping-rate {
               description "Excludes Juniper (IANA 4874) VSA 26-177, Cos-Shaping-Rate";
               type enumeration {
                 enum "accounting-start" {
                   description "RADIUS Accounting-Start message";
                 }
                 enum "accounting-stop" {
                   description "RADIUS Accounting-Stop message";
                 }
               }
             }
             leaf-list framed-interface-id {
               description "Excludes RADIUS attribute 96, Framed-Interface-Id";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list chargeable-user-identity {
               description "Excludes RADIUS attribute 89, Chargeable-User-Identity";
               type enumeration {
                 enum "access-request" {
                   description "RADIUS Access-Request message";
                 }
               }
             }
             leaf-list l2tp-tx-connect-speed {
               description "Excludes Juniper (IANA 4874) VSA 26-162, , L2TP-Tx-Connect-Speed";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list l2tp-rx-connect-speed {
               description "Excludes Juniper (IANA 4874) VSA 26-163, , L2TP-Rx-Connect-Speed";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-type {
               description "Excludes RADIUS attribute 64, Tunnel-Type";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-medium-type {
               description "Excludes RADIUS attribute 65, Tunnel-Medium-Type";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-client-endpoint {
               description "Excludes RADIUS attribute 66, Tunnel-Client-Endpoint";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-server-endpoint {
               description "Excludes RADIUS attribute 67, Tunnel-Server-Endpoint";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-assignment-id {
               description "Excludes RADIUS attribute 82, Tunnel-Assignment-Id";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-client-auth-id {
               description "Excludes RADIUS attribute 90, Tunnel-Client-Auth-Id";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-server-auth-id {
               description "Excludes RADIUS attribute 91, Tunnel-Server-Auth-Id";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list acct-tunnel-connection {
               description "Excludes RADIUS attribute 68, Acct-Tunnel-Connection";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list acc-loop-remote-id {
               description "Excludes Juniper (IANA 4874) VSA 26-XXX, ERX-Acc-Loop-Remote-Id";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list acc-loop-encap {
               description "Excludes Juniper (IANA 4874) VSA 26-182, ERX-Acc-Loop-Encap";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list pppoe-description {
               description "Excludes RADIUS attribute 26-24, PPPOE-Description";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list virtual-router {
               description "Excludes Juniper (IANA 4874) VSA 26-1, Virtual-Router";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list first-relay-ipv4-address {
               description "Excludes RADIUS attribute 26-189, DHCP-First-Relay-IPv4-Address";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list first-relay-ipv6-address {
               description "Excludes RADIUS attribute 26-190, DHCP-First-Relay-IPv6-Address";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list dhcpv6-options {
               description "Excludes RADIUS attribute 26-207, DHCPv6-Options";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list dhcp-header {
               description "Excludes RADIUS attribute 26-208, DHCP-Header";
               type enumeration {
                 enum "access-request" {
                   description "RADIUS Access-Request message";
                 }
               }
             }
             leaf-list dhcpv6-header {
               description "Excludes RADIUS attribute 26-209, DHCPv6-Header";
               type enumeration {
                 enum "access-request" {
                   description "RADIUS Access-Request message";
                 }
               }
             }
             leaf-list acct-request-reason {
               description "Excludes RADIUS attribute 26-210, Acct-Request-Reason";
               type enumeration {
                 enum "accounting-start" {
                   description "RADIUS Accounting-Start message";
                 }
                 enum "accounting-stop" {
                   description "RADIUS Accounting-Stop message";
                 }
               }
             }
           }
         }
       }
       container session-options {
         description "Options for an authenticated client's session";
         uses apply-advanced;
         leaf-list client-group {
           description "One or more groups to which client belongs";
           type string;
         }
         leaf client-idle-timeout {
           description "Time in minutes of idleness after which access is denied";
           units "minutes";
           type union {
             type string {
               pattern "<.*>|$.*";
             }
             type uint32 {
               range "10 .. 1440";
             }
           }
         }
         leaf client-idle-timeout-ingress-only {
           description "Idle timeout applies to ingress traffic only";
           type empty;
         }
         leaf client-session-timeout {
           description "Time in minutes since initial access after which access is denied";
           units "minutes";
           type union {
             type string {
               pattern "<.*>|$.*";
             }
             type uint32 {
               range "1 .. 527040";
             }
           }
         }
         container strip-user-name {
           description "Options for stripping user name string";
           uses apply-advanced;
           container delimiter {
             description "Allowable delimiter characters for strip user name separation";
             leaf characters {
               description "Sequence of characters without spaces and commas";
               type string {
                 length "1 .. 8";
               }
             }
           }
           container parse-direction {
             description "Strip user name parsing direction";
             choice direction {
               case case_1 {
                 leaf right-to-left {
                   description "Parse the username from right to left";
                   type empty;
                 }
               }
               case case_2 {
                 leaf left-to-right {
                   description "Parse the username field from left to right";
                   type empty;
                 }
               }
             }
           }
         }
       }
       container client-name-filter {
         description "Restrictions on client names";
         uses access-client-name-filter-object;
       }
       container ldap-options {
         description "Lightweight Directory Access Protocol options";
         junos:must "((!(any \".. client <*> l2tp\") && (!(any \".. client <*> ike\") && !(any \".. client <*> ppp\"))))";
         junos:must-message "'ldap-options' statement is not supported in L2TP, IKE, or PPP configuration";
         uses access-ldap-options;
         junos:must "((!(any \".. client <*> l2tp\") && (!(any \".. client <*> ike\") && !(any \".. client <*> ppp\"))))";
         junos:must-message "'ldap-options' statement is not supported in L2TP, IKE, or PPP configuration";
       }
       list ldap-server {
         key name;
         ordered-by user;
         description "Lightweight Directory Access Protocol server";
         junos:must "(\".. ldap-options\")";
         junos:must-message "ldap-options must be configured when ldap-server is configured";
         junos:must "((!(any \".. client <*> l2tp\") && (!(any \".. client <*> ike\") && !(any \".. client <*> ppp\"))))";
         junos:must-message "'ldap-server' statement is not supported in L2TP, IKE, or PPP configuration";
         uses ldap-server-object;
       }
       list radius-server {
         key name;
         ordered-by user;
         description "RADIUS server configuration";
         junos:must "(!(any \".. client <*> l2tp\"))";
         junos:must-message "Not supported in L2TP configuration";
         junos:must "((!(any \".. client <*> l2tp\") && !(any \".. client <*> ike\")))";
         junos:must-message "Not supported in L2TP or IKE configuration";
         uses profile-radius-server-object;
       }
       container accounting {
         description "Specifies the accounting options";
         uses apply-advanced;
         leaf-list order {
           description "Order in which accounting mechanisms are used";
           type enumeration {
             enum "radius" {
               description "Remote authentication dial-in user service";
             }
           }
         }
         leaf accounting-stop-on-failure {
           description "Send an Acct-Stop message if a user fails authentication, but AAA-server grants access";
           type empty;
         }
         leaf accounting-stop-on-access-deny {
           description "Send an Acct-Stop message if AAA-server denies access";
           type empty;
         }
         leaf immediate-update {
           description "Send an Acct-Update message on receipt of a Acct-response for the Acct-Start message";
           type empty;
         }
         leaf coa-immediate-update {
           description "Send an Acct-Update message on completion of processing a change of authorization";
           type empty;
         }
         leaf address-change-immediate-update {
           description "Send an Acct-Update message to notify address change";
           type empty;
         }
         leaf update-interval {
           description "The interval in min btw accounting updates(Interim-stats off,if unspecified)";
           units "minutes";
           type union {
             type string {
               pattern "<.*>|$.*";
             }
             type uint32 {
               range "10 .. 1440";
             }
           }
         }
         leaf statistics {
           description "Reports set of statistics attributes based on reporting type";
           type enumeration {
             enum "volume-time" {
               description "Configures the option to report both volume and uptime";
             }
             enum "time" {
               description "Configures the option to report only uptime";
             }
           }
         }
         leaf wait-for-acct-on-ack {
           description "Wait for ACCT-ON-ACK";
           type empty;
         }
         leaf send-acct-status-on-config-change {
           description "Send ACCT-ON/OFF on config change";
           type empty;
         }
         leaf duplication {
           description "Send duplicated accounting reports if applied";
           type empty;
         }
         leaf-list duplication-filter {
           description "Configure duplication filters";
           type enumeration {
             enum "interim-original" {
               description "Do not send original accounting interims";
             }
             enum "interim-duplicated" {
               description "Do not send duplicated accounting interims";
             }
             enum "exclude-attributes" {
               description "Use duplication access profile exclude attributes";
             }
           }
         }
         container duplication-vrf {
           description "Duplication vrf configurations";
           uses apply-advanced;
           leaf vrf-name {
             description "VRF name";
             type string {
               length "1 .. 257";
             }
           }
           leaf-list access-profile-name {
             description "Access profile name";
             type string {
               length "1 .. 63";
             }
             max-elements 5;
           }
         }
         leaf-list duplication-attribute-format {
           description "Use attribute format defined under duplication accouting access-profile";
           type enumeration {
             enum "username" {
               description "Username";
             }
           }
         }
         leaf ancp-speed-change-immediate-update {
           description "Send an Acct-Update message when ANCP speed change is detected";
           type empty;
         }
         leaf family-state-change-immediate-update {
           description "Send an Acct-Update message to notify address family activation state change";
           type empty;
         }
       }
       container service {
         description "Subscriber service configurations";
         uses apply-advanced;
         leaf accounting-order {
           description "Order in which accounting mechanism service is used";
           type enumeration {
             enum "activation-protocol" {
               description "Send service accounting reports via service activation protocol";
             }
             enum "radius" {
               description "Send service accounting reports via radius protocol";
             }
             enum "local" {
               description "Send service accounting for local reporting";
               junos:must "(\".. .. local flat-file-profile\")";
               junos:must-message "local flat-file-profile must be configured under access profile for accounting-order local";
             }
           }
         }
         container accounting {
           description "Specifies the service accounting options";
           uses apply-advanced;
           leaf update-interval {
             description "The interval in minutes between accounting updates(Interim-stats off, if not specified)";
             units "minutes";
             type union {
               type string {
                 pattern "<.*>|$.*";
               }
               type uint32 {
                 range "10 .. 1440";
               }
             }
           }
           leaf statistics {
             description "Reports set of statistics attributes based on reporting type";
             junos:must "(!(\".. .. accounting-order $$={local}\"))";
             junos:must-message "Statistics configuration is no-op when accounting-order is set to local for flat-file based accounting";
             type enumeration {
               enum "time" {
                 description "Configures the option to report only uptime";
               }
               enum "volume-time" {
                 description "Configures the option to report both volume and uptime";
               }
             }
           }
         }
       }
       container jsrc {
         description "Set of JSRC configurations";
         uses apply-advanced;
         container attributes {
           description "Specifies how JSRC attributes should be handled";
           uses apply-advanced;
           container exclude {
             description "Configures the exclusion of JSRC attributes in DIAMETER messages";
             uses apply-advanced;
             leaf-list user-name {
               description "Excludes Diameter attribute 1, User-Name";
               type enumeration {
                 enum "authorization-request" {
                   description "Authorization AA-Request message";
                 }
                 enum "provisioning-request" {
                   description "Provisioning AA-Request message";
                 }
               }
             }
           }
         }
       }
     }
     container address-assignment {
       description "Address assignment configuration";
       uses address-assignment-type;
     }
     leaf address-protection {
       description "Initiate Duplicate Address Protection";
       type empty;
     }
     container address-preservation {
       description "Enable address preservation";
       uses apply-advanced;
       leaf address-types {
         type enumeration {
           enum "delegated-prefix" {
             description "Address preservation delegated prefix";
           }
         }
       }
       leaf aging-time {
         description "Time to hold address reservation";
         default "86400";
         units "seconds";
         type union {
           type string {
             pattern "<.*>|$.*";
           }
           type uint32 {
             range "3600 .. 604800";
           }
         }
       }
     }
     container domain {
       description "Domain map configuration";
       uses domain-map-type;
     }
     container ppp-options {
       presence "enable ppp-options";
       description "Point-to-Point Protocol (PPP) specific options";
       uses apply-advanced;
       container compliance {
         description "Standards compliance definition";
         uses apply-advanced;
         leaf-list rfc {
           description "Enforce compliance with RFC standards";
           type enumeration {
             enum "2486" {
               description "RFC 2486 compliant";
             }
           }
         }
       }
     }
     container gx-plus {
       description "GX-PLUS configuration";
       junos:must "(!(\".. pcrf\"))";
       junos:must-message "pcrf is mutually exclusive with gx-plus";
       uses gx-plus-definition;
       junos:must "(!(\".. pcrf\"))";
       junos:must-message "pcrf is mutually exclusive with gx-plus";
     }
     container pcrf {
       description "PCRF configuration";
       uses pcrf-definition;
     }
     container ocs {
       description "OCS configuration";
       uses ocs-definition;
     }
     leaf report-interface-descriptions {
       description "Support reporting of interface descriptions";
       type empty;
     }
     container nasreq {
       description "Nasreq configuration";
       uses nasreq-definition;
     }
     list protocol-attributes {
       key name;
       ordered-by user;
       description "Protocol specific attribute configuration";
       uses protocol-attribute-type;
     }
     list aaa-options {
       key name;
       ordered-by user;
       description "AAA option configurations";
       leaf name {
         description "AAA options name";
         junos:must "((\".. access-profile\" || (\".. aaa-context\" || \".. subscriber-context\")))";
         junos:must-message "at least one of attritues is configured";
         type string {
           length "1 .. 63";
         }
       }
       uses apply-advanced;
       leaf access-profile {
         description "Access profile name";
         junos:must "(\"access profile $$\")";
         junos:must-message "referenced access profile must be defined";
         type string {
           length "1 .. 63";
         }
       }
       leaf aaa-context {
         description "AAA context";
         type string;
       }
       leaf subscriber-context {
         description "Subscriber context";
         type string;
       }
     }
     container radius-options {
       description "RADIUS options";
       uses access-radius-options;
     }
     container ldap-options {
       description "Lightweight Directory Access Protocol options";
       uses access-ldap-options;
     }
     list ldap-server {
       key name;
       ordered-by user;
       description "Lightweight Directory Access Protocol server options";
       junos:must "(\".. ldap-options\")";
       junos:must-message "ldap-options must be configured when ldap-server is configured";
       uses ldap-server-object;
     }
     list securid-server {
       key name;
       ordered-by user;
       description "SecurID server configuration";
       max-elements 1;
       uses securid-server-object;
     }
     container accounting-backup-options {
       description "Pending accounting backup-options ";
       uses apply-advanced;
       leaf max-pending-accounting-stops {
         description "Max pending accouting stops";
         junos:must "(!(any \"access profile <*> provisioning-order $$={pcrf}\"))";
         junos:must-message "backup accounting is not supported with pcrf provisioning";
         type union {
           type string {
             pattern "<.*>|$.*";
           }
           type uint32 {
             range "1 .. 168000";
           }
         }
       }
       leaf max-withhold-time {
         description "Maximum time in mins to hold the pending accounting stops";
         units "minutes";
         junos:must "(!(any \"access profile <*> provisioning-order $$={pcrf}\"))";
         junos:must-message "backup accounting is not supported with pcrf provisioning";
         type union {
           type string {
             pattern "<.*>|$.*";
           }
           type uint32 {
             range "60 .. 1440";
           }
         }
       }
     }
     container terminate-code {
       description "Terminate code mapping configuration";
       uses apply-advanced;
       container aaa {
         description "AAA terminate-code mapping configuration";
         uses apply-advanced;
         container deny {
           description "Terminate-code specification";
           uses apply-advanced;
           container authentication-denied {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-resources {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container server-request-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container service-shutdown {
           description "Terminate-code specification";
           uses apply-advanced;
           container network-logout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container remote-reset {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container subscriber-logout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container time-limit {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container volume-limit {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container shutdown {
           description "Terminate-code specification";
           uses apply-advanced;
           container administrative-reset {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container idle-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container remote-reset {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container session-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
       }
       container dhcp {
         description "DHCP terminate-code mapping configuration";
         uses apply-advanced;
         container client-request {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container lost-carrier {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container nak {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container nas-logout {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container no-offers {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
       }
       container vlan {
         description "VLAN terminate-code mapping configuration";
         uses apply-advanced;
         container admin-logout {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container admin-reconnect {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container other {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container out-of-band {
           description "Terminate-code specification";
           uses apply-advanced;
           container access-interface-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container admin-access-interface-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container admin-core-interface-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container ancp {
             description "Terminate-code specification";
             uses apply-advanced;
             container port-down {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container port-vlan-id-change {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container core-interface-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container l2-wholesale {
             description "Terminate-code specification";
             uses apply-advanced;
             container no-free-vlans {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
         }
         container profile-request-error {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container sdb-error {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container subscriber-activate-error {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
       }
     }
   }
   grouping access-client-name-filter-object {
     description "Restrictions on client names authenticated on this server";
     uses apply-advanced;
     leaf domain-name {
       description "Domain name to match (must be part of username)";
       type string;
     }
     leaf separator {
       description "Separator character in domain name";
       type string {
         length 1;
       }
     }
     leaf count {
       description "Number of separator instances";
       default "0";
       type union {
         type string {
           pattern "<.*>|$.*";
         }
         type uint8 {
           range "0 .. 255";
         }
       }
     }
   }
   grouping access-client-object {
     leaf name {
       description "Name of entity requesting access";
       type string;
     }
     uses apply-advanced;
     leaf no-rfc2486 {
       description "RFC2486 compliance is not enforced";
       type empty;
     }
     leaf chap-secret {
       description "CHAP secret";
       type jt:unreadable;
     }
     leaf pap-password {
       description "PAP password";
       type jt:unreadable;
     }
     choice client_type {
       case case_1 {
       }
       case case_2 {
       }
       case case_3 {
         container ike {
           presence "enable ike";
           description "Configuration for dynamic IKE peers";
           uses apply-advanced;
           leaf initiate-dead-peer-detection {
             description "Initiate dead peer detection";
             type empty;
           }
           container dead-peer-detection {
             presence "enable dead-peer-detection";
             junos:must "(\".. initiate-dead-peer-detection\")";
             junos:must-message "[ edit access profile <*> client * ike initiate-dead-peer-detection ] must be set";
             description "Dead peer detection options";
             uses apply-advanced;
             leaf interval {
               description "Interval at which the DPD messages should be sent";
               default "2";
               units "seconds";
               type union {
                 type string {
                   pattern "<.*>|$.*";
                 }
                 type uint32 {
                   range "1 .. 180";
                 }
               }
             }
             leaf threshold {
               description "Maximum number of DPD messages";
               default "3";
               type union {
                 type string {
                   pattern "<.*>|$.*";
                 }
                 type uint32 {
                   range "1 .. 10";
                 }
               }
             }
           }
           container respond-bad-spi {
             presence "enable respond-bad-spi";
             description "Respond to IPsec packets with bad security parameter index (SPI) values";
             leaf max-responses {
               description "Maximum number of times to respond";
               default "5";
               type union {
                 type string {
                   pattern "<.*>|$.*";
                 }
                 type uint32 {
                   range "1 .. 30";
                 }
               }
             }
           }
           choice name {
             case case_1 {
             }
             case case_2 {
             }
           }
           container reverse-route {
             presence "enable reverse-route";
             description "Reverse route parameters";
             uses apply-advanced;
             container preference {
               description "Preference value";
               leaf metric-value {
                 description "Metric value";
                 type union {
                   type uint32;
                   type string {
                     pattern "<.*>|$.*";
                   }
                 }
               }
             }
           }
         }
       }
     }
     leaf-list client-group {
       description "One or more groups to which the client belongs";
       type string;
     }
     container firewall-user {
       description "Client is configured as a firewall user";
       uses apply-advanced;
       leaf password {
         description "Password for user";
         type string {
           length "1 .. 128";
         }
       }
     }
   }
   grouping access-ldap-options {
     uses apply-advanced;
     leaf revert-interval {
       description "Time after which to revert to primary server";
       default "600";
       units "seconds";
       type union {
         type string {
           pattern "<.*>|$.*";
         }
         type uint32 {
           range "60 .. 4294967295";
         }
       }
     }
     leaf base-distinguished-name {
       description "Suffix when assembling user distinguished name (DN) or base DN under which to search for user DN";
       type string;
     }
     choice search_type {
       case case_1 {
         container assemble {
           presence "enable assemble";
           description "Derive user distinguished name from 'common-name' and 'base-distinguished-name'";
           uses apply-advanced;
           leaf common-name {
             description "Prefix in user distinguished name (for example, 'cn' or 'uid')";
             default "cn";
             type string;
           }
         }
       }
       case case_2 {
         container search {
           presence "enable search";
           description "Search for user's distinguished name";
           uses apply-advanced;
           leaf search-filter {
             description "Filter to use in search (examples: 'cn=' or 'givenName=')";
             type string;
           }
           container admin-search {
             presence "enable admin-search";
             description "Perform an administrator search to find user's distinguished name";
             uses apply-advanced;
             leaf distinguished-name {
               description "Administrator's distinguished name";
               type string;
             }
             leaf password {
               description "Administrator password";
               type jt:unreadable;
             }
           }
         }
       }
     }
   }
   grouping access-radius-options {
     uses apply-advanced;
     leaf revert-interval {
       description "Time after which to revert to primary server";
       default "60";
       units "seconds";
       type union {
         type string {
           pattern "<.*>|$.*";
         }
         type uint32 {
           range "0 .. 604800";
         }
       }
     }
     leaf timeout-grace {
       description "The period after a RADIUS server times out before marking the server as dead";
       default "10";
       units "seconds";
       type union {
         type string {
           pattern "<.*>|$.*";
         }
         type uint32 {
           range "0 .. 30";
         }
       }
     }
     leaf request-rate {
       description "Maximum number of RADIUS requests sent per second";
       default "500";
       type union {
         type string {
           pattern "<.*>|$.*";
         }
         type uint32 {
           range "100 .. 4000";
         }
       }
     }
     leaf interim-rate {
       description "Maximum number of RADIUS requests sent per second";
       default "500";
       type union {
         type string {
           pattern "<.*>|$.*";
         }
         type uint32 {
           range "50 .. 4000";
         }
       }
     }
     leaf interim-update-tolerance {
       description "Maximum tolerance for Interim Updates to RADIUS";
       default "60";
       units "seconds";
       type union {
         type string {
           pattern "<.*>|$.*";
         }
         type uint32 {
           range "1 .. 600";
         }
       }
     }
     container unique-nas-port {
       presence "enable unique-nas-port";
       junos:must "(!(any \"access profile <*> radius options vlan-nas-port-stacked-format\"))";
       junos:must-message "unique-nas-port is not supported with vlan-nas-port-stacked-format";
       junos:must "(!(any \"access profile <*> radius options nas-port-extended-format\"))";
       junos:must-message "unique-nas-port is not supported with nas-port-extended-format";
       description "Use unique value for NAS-Port radius attribute";
       uses apply-advanced;
       leaf chassis-id {
         description "Configure chassis identifier field of NAS-Port";
         junos:must "(\".. chassis-id-width\")";
         junos:must-message "chassis-id-width must be configured";
         type union {
           type string {
             pattern "<.*>|$.*";
           }
           type uint32 {
             range "0 .. 127";
           }
         }
       }
       leaf chassis-id-width {
         description "Number of bits for the chassis identifier field of NAS-Port";
         units "bits";
         junos:must "(\".. chassis-id\")";
         junos:must-message "chassis-id must be configured";
         type union {
           type string {
             pattern "<.*>|$.*";
           }
           type uint32 {
             range "1 .. 7";
           }
         }
       }
     }
   }
   grouping access-radius-server-object {
     leaf name {
       description "RADIUS server address";
       type jt:ipaddr;
     }
     uses apply-advanced;
     leaf port {
       description "RADIUS server authentication port number";
       default "1812";
       type union {
         type string {
           pattern "<.*>|$.*";
         }
         type uint16 {
           range "1 .. 65535";
         }
       }
     }
     leaf preauthentication-port {
       description "RADIUS server preauthentication port number";
       type union {
         type string {
           pattern "<.*>|$.*";
         }
         type uint16 {
           range "1 .. 65535";
         }
       }
     }
     leaf accounting-port {
       description "Port number to send RADIUS accounting messages";
       default "1813";
       type union {
         type string {
           pattern "<.*>|$.*";
         }
         type uint16 {
           range "1 .. 65535";
         }
       }
     }
     leaf dynamic-request-port {
       description "RADIUS client dynamic request port number";
       default "3799";
       type union {
         type string {
           pattern "<.*>|$.*";
         }
         type uint16 {
           range "1 .. 65535";
         }
       }
     }
     leaf secret {
       description "Shared secret with the RADIUS server";
       type jt:unreadable;
     }
     leaf preauthentication-secret {
       description "Shared secret with the RADIUS server";
       type jt:unreadable;
     }
     leaf timeout {
       description "Request timeout period";
       default "3";
       units "seconds";
       type union {
         type string {
           pattern "<.*>|$.*";
         }
         type uint32 {
           range "1 .. 1000";
         }
       }
     }
     leaf retry {
       description "Retry attempts";
       default "3";
       type union {
         type string {
           pattern "<.*>|$.*";
         }
         type uint32 {
           range "1 .. 100";
         }
       }
     }
     leaf accounting-timeout {
       description "Accounting request timeout period";
       default "0";
       units "seconds";
       type union {
         type string {
           pattern "<.*>|$.*";
         }
         type uint32 {
           range "0 .. 1000";
         }
       }
     }
     leaf accounting-retry {
       description "Accounting retry attempts";
       default "0";
       type union {
         type string {
           pattern "<.*>|$.*";
         }
         type uint32 {
           range "0 .. 100";
         }
       }
     }
     leaf max-outstanding-requests {
       description "Maximum requests in flight to server";
       default "1000";
       type union {
         type string {
           pattern "<.*>|$.*";
         }
         type uint32 {
           range "0 .. 2000";
         }
       }
     }
     leaf source-address {
       description "Use specified address as source address";
       type jt:ipaddr;
     }
     leaf routing-instance {
       description "Use specified routing instance";
       junos:must "(\"routing-instances $$\")";
       junos:must-message "referenced routing-instance must be defined";
       type string;
     }
   }
   grouping address-assignment-type {
     description "Address assignment configuration";
     uses apply-advanced;
     container neighbor-discovery-router-advertisement {
       description "Designated NDRA pool for this instance";
       leaf ndra-name {
         description "Designated NDRA pool name";
         junos:must "(\".. .. pool $$  family inet6\")";
         junos:must-message "designated NDRA pool must be configured and family inet6 must be set";
         type string {
           length "1 .. 63";
           junos:posix-pattern "^[A-Za-z0-9][_0-9A-Za-z-]{0,62}$";
           junos:pattern-message "Must be a string beginning with a number or letter and consisting of no more than 63 total letters, numbers, dashes and underscores.";
         }
       }
     }
     leaf high-utilization {
       description "Generate an SNMP trap when address pool use surpasses this percentage";
       type union {
         type string {
           pattern "<.*>|$.*";
         }
         type uint16 {
           range "2 .. 99";
         }
       }
     }
     leaf abated-utilization {
       description "Generate an SNMP clear trap when address pool use falls below this percentage";
       type union {
         type string {
           pattern "<.*>|$.*";
         }
         type uint16 {
           range "1 .. 98";
         }
       }
     }
     leaf high-utilization-v6 {
       description "Generate an SNMP trap when address pool use surpasses this percentage";
       type union {
         type string {
           pattern "<.*>|$.*";
         }
         type uint16 {
           range "2 .. 99";
         }
       }
     }
     leaf abated-utilization-v6 {
       description "Generate an SNMP clear trap when address pool use falls below this percentage";
       type union {
         type string {
           pattern "<.*>|$.*";
         }
         type uint16 {
           range "1 .. 98";
         }
       }
     }
     list pool {
       key name;
       ordered-by user;
       description "Address pool";
       leaf name {
         description "Address pool name";
         junos:must "(!(\".. link $$\"))";
         junos:must-message "Link cannot be self referential";
         type string {
           length "1 .. 63";
           junos:posix-pattern "^[A-Za-z0-9][_0-9A-Za-z-]{0,62}$";
           junos:pattern-message "Must be a string beginning with a number or letter and consisting of no more than 63 total letters, numbers, dashes and underscores.";
         }
       }
       uses apply-advanced;
       leaf active-drain {
         description "Notify client of pool active drain mode";
         type empty;
       }
       leaf hold-down {
         description "Place pool in passive drain mode";
         type empty;
       }
       leaf link {
         description "Address pool link name";
         junos:must "(\".. .. pool $$\")";
         junos:must-message "Link must be to a valid pool name";
         type string {
           length "1 .. 63";
           junos:posix-pattern "^[A-Za-z0-9][_0-9A-Za-z-]{0,62}$";
           junos:pattern-message "Must be a string beginning with a number or letter and consisting of no more than 63 total letters, numbers, dashes and underscores.";
         }
       }
       container family {
         presence "enable family";
         description "Address family";
         choice family_type {
           case case_1 {
             container inet {
               presence "enable inet";
               description "IPv4";
               uses apply-advanced;
               leaf network {
                 description "Network address";
                 type jt:ipv4prefix;
               }
               list range {
                 key name;
                 ordered-by user;
                 description "Address range";
                 leaf name {
                   description "Range name";
                   type string {
                     length "1 .. 63";
                     junos:posix-pattern "^[A-Za-z0-9][_0-9A-Za-z-]{0,62}$";
                     junos:pattern-message "Must be a string beginning with a number or letter and consisting of no more than 63 total letters, numbers, dashes and underscores.";
                   }
                 }
                 uses apply-advanced;
                 leaf low {
                   description "Lower limit of address range";
                   type jt:ipv4addr;
                 }
                 leaf high {
                   description "Upper limit of address range";
                   type jt:ipv4addr;
                 }
               }
               container dhcp-attributes {
                 description "DHCP options and match criteria";
                 uses dhcp-attribute-type;
               }
               container xauth-attributes {
                 description "Configure xauth attributes";
                 uses apply-advanced;
                 leaf primary-dns {
                   description "Specify the primary-dns IP address";
                   type jt:ipv4prefix;
                 }
                 leaf secondary-dns {
                   description "Specify the secondary-dns IP address";
                   type jt:ipv4prefix;
                 }
                 leaf primary-wins {
                   description "Specify the primary-wins IP address";
                   type jt:ipv4prefix;
                 }
                 leaf secondary-wins {
                   description "Specify the secondary-wins IP address";
                   type jt:ipv4prefix;
                 }
               }
               list host {
                 key name;
                 ordered-by user;
                 description "Hostname for static reservations";
                 leaf name {
                   description "Hostname";
                   type string {
                     length "1 .. 63";
                     junos:posix-pattern "^[A-Za-z0-9][_0-9A-Za-z-]{0,62}$";
                     junos:pattern-message "Must be a string beginning with a number or letter and consisting of no more than 63 total letters, numbers, dashes and underscores.";
                   }
                 }
                 uses apply-advanced;
                 leaf hardware-address {
                   description "Hardware address";
                   type jt:mac-addr;
                 }
                 leaf ip-address {
                   description "Reserved address";
                   type jt:ipv4addr;
                 }
               }
               list excluded-address {
                 key name;
                 ordered-by user;
                 description "Excluded Addresses";
                 max-elements 20;
                 leaf name {
                   description "Excluded address";
                   type jt:ipv4addr;
                 }
                 uses apply-advanced;
               }
               list excluded-range {
                 key name;
                 ordered-by user;
                 description "Excluded address range";
                 max-elements 20;
                 leaf name {
                   description "Range name";
                   type string {
                     length "1 .. 63";
                     junos:posix-pattern "^[A-Za-z0-9][_0-9A-Za-z-]{0,62}$";
                     junos:pattern-message "Must be a string beginning with a number or letter and consisting of no more than 63 total letters, numbers, dashes and underscores.";
                   }
                 }
                 uses apply-advanced;
                 leaf low {
                   description "Lower limit of excluded address range";
                   type jt:ipv4addr;
                 }
                 leaf high {
                   description "Upper limit of excluded address range";
                   type jt:ipv4addr;
                 }
               }
             }
           }
           case case_2 {
             container inet6 {
               presence "enable inet6";
               description "IPv6";
               uses apply-advanced;
               leaf prefix {
                 description "IPv6 network prefix";
                 type jt:ipv6prefix-mandatory;
               }
               list range {
                 key name;
                 ordered-by user;
                 description "IPv6 address range";
                 leaf name {
                   description "Range name";
                   type string {
                     length "1 .. 63";
                     junos:posix-pattern "^[A-Za-z0-9][_0-9A-Za-z-]{0,62}$";
                     junos:pattern-message "Must be a string beginning with a number or letter and consisting of no more than 63 total letters, numbers, dashes and underscores.";
                   }
                 }
                 uses apply-advanced;
                 leaf low {
                   description "Lower limit of ipv6 address range";
                   junos:must "(\".. high\")";
                   junos:must-message "range upper bound must be defined";
                   type jt:ipv6prefix-mandatory;
                 }
                 leaf high {
                   description "Upper limit of ipv6 address range";
                   junos:must "(\".. low\")";
                   junos:must-message "range lower bound must be defined";
                   type jt:ipv6prefix-mandatory;
                 }
                 leaf prefix-length {
                   description "IPv6 delegated prefix length";
                   junos:must "(!(\".. low\"))";
                   junos:must-message "range lower bound may not be defined";
                   type union {
                     type string {
                       pattern "<.*>|$.*";
                     }
                     type uint32 {
                       range "1 .. 128";
                     }
                   }
                 }
               }
               container dhcp-attributes {
                 description "DHCP options and match criteria";
                 uses dhcp-attribute-type;
               }
               list excluded-address {
                 key name;
                 ordered-by user;
                 description "Excluded Addresses";
                 max-elements 20;
                 leaf name {
                   description "Excluded address";
                   type jt:ipv6addr;
                 }
                 uses apply-advanced;
               }
               list excluded-range {
                 key name;
                 ordered-by user;
                 description "Excluded address range";
                 max-elements 20;
                 leaf name {
                   description "Range name";
                   type string {
                     length "1 .. 63";
                     junos:posix-pattern "^[A-Za-z0-9][_0-9A-Za-z-]{0,62}$";
                     junos:pattern-message "Must be a string beginning with a number or letter and consisting of no more than 63 total letters, numbers, dashes and underscores.";
                   }
                 }
                 uses apply-advanced;
                 leaf low {
                   description "Lower limit of excluded address range";
                   type jt:ipv6addr;
                 }
                 leaf high {
                   description "Upper limit of excluded address range";
                   type jt:ipv6addr;
                 }
               }
             }
           }
         }
       }
     }
   }
   grouping address-pool-object {
     leaf name {
       description "Address pool name";
       type string {
         length "1 .. 63";
         junos:posix-pattern "^[A-Za-z0-9][_0-9A-Za-z-]{0,62}$";
         junos:pattern-message "Must be a string beginning with a number or letter and consisting of no more than 63 total letters, numbers, dashes and underscores.";
       }
     }
     uses apply-advanced;
     choice address_choice {
       case case_1 {
         leaf address {
           description "Address or address prefix";
           type jt:ipv4prefix;
         }
       }
       case case_2 {
         container address-range {
           presence "enable address-range";
           description "Range of addresses for pool";
           leaf low {
             description "Lower limit of address range";
             type jt:ipv4addr;
           }
           leaf high {
             description "Upper limit of address range";
             type jt:ipv4addr;
           }
         }
       }
     }
   }
   grouping apply-advanced {
     description "Apply advanced configuration logic";
     leaf-list apply-groups {
       description "Groups from which to inherit configuration data";
       type string;
     }
     leaf-list apply-groups-except {
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping dhcp-attribute-type {
     uses apply-advanced;
     container option-match {
       description "Match";
       uses apply-advanced;
       container option-82 {
         uses apply-advanced;
         list circuit-id {
           key name;
           ordered-by user;
           description "Circuit ID portion of the option 82";
           leaf name {
             type string;
           }
           leaf range {
             description "Range name";
             type string;
           }
         }
         list remote-id {
           key name;
           ordered-by user;
           description "Remote ID portion of the option 82";
           leaf name {
             type string;
           }
           leaf range {
             description "Range name";
             type string;
           }
         }
       }
     }
     leaf maximum-lease-time {
       description "Maximum lease time advertised to clients";
       units "seconds";
       type string;
     }
     leaf server-identifier {
       description "Server Identifier - IP address value";
       type jt:ipv4addr;
     }
     leaf grace-period {
       description "Grace period for leases";
       units "seconds";
       type union {
         type uint32;
         type string {
           pattern "<.*>|$.*";
         }
       }
     }
     leaf domain-name {
       description "Domain name advertised to clients";
       type string {
         junos:posix-pattern "^[[:alnum:]._-]+$";
         junos:pattern-message "Must be a string of letters, numbers, dashes or underscores";
       }
     }
     list name-server {
       key name;
       ordered-by user;
       description "Domain name servers available to the client";
       leaf name {
         description "DNS server's IPv4 address";
         type jt:ipv4addr;
       }
       uses apply-advanced;
     }
     list wins-server {
       key name;
       ordered-by user;
       description "WINS name servers";
       leaf name {
         description "WINS server's IPv4 address";
         type jt:ipv4addr;
       }
       uses apply-advanced;
     }
     list router {
       key name;
       ordered-by user;
       description "Routers advertised to clients";
       leaf name {
         description "Router's IPv4 address";
         type jt:ipv4addr;
       }
       uses apply-advanced;
     }
     leaf boot-file {
       description "Boot filename advertised to clients";
       type string;
     }
     leaf boot-server {
       description "Boot server advertised to clients";
       type string {
         junos:posix-pattern "^[[:alnum:]._-]+$";
         junos:pattern-message "Must be a string of letters, numbers, dashes or underscores";
       }
     }
     leaf tftp-server {
       description "TFTP server IP address advertised to clients";
       type jt:ipv4addr;
     }
     leaf netbios-node-type {
       description "Type of NETBIOS node advertised to clients";
       type enumeration {
         enum "b-node" {
           description "Broadcast node";
         }
         enum "p-node" {
           description "Peer-to-peer node";
         }
         enum "m-node" {
           description "Mixed Node";
         }
         enum "h-node" {
           description "Hybrid node";
         }
       }
     }
     leaf sip-server-domain-name {
       description "SIP server domain name available to clients";
       type string {
         junos:posix-pattern "^[[:alnum:]._-]+$";
         junos:pattern-message "Must be a string of letters, numbers, dashes or underscores";
       }
     }
     list sip-server-address {
       key name;
       ordered-by user;
       description "SIP Servers list of IPv6 addresses available to the client";
       leaf name {
         description "SIP Server's IPv6 address";
         type jt:ipv6addr;
       }
       uses apply-advanced;
     }
     list dns-server {
       key name;
       ordered-by user;
       description "Domain name servers available to the client";
       leaf name {
         description "DNS server's IPv6 address";
         type jt:ipv6addr;
       }
       uses apply-advanced;
     }
     list option {
       key name;
       ordered-by user;
       description "DHCP option";
       leaf name {
         description "DHCP option identifier code";
         type union {
           type uint32;
           type string {
             pattern "<.*>|$.*";
           }
         }
       }
       choice option-type-choice {
         case case_1 {
           leaf flag {
             description "Boolean flag value";
             type enumeration {
               enum "true" {
                 description "True value";
               }
               enum "false" {
                 description "False value";
               }
               enum "on" {
                 description "On value";
               }
               enum "off" {
                 description "Off value";
               }
             }
           }
         }
         case case_2 {
           leaf byte {
             description "Unsigned 8-bit value";
             type union {
               type uint8;
               type string {
                 pattern "<.*>|$.*";
               }
             }
           }
         }
         case case_3 {
           leaf short {
             description "Signed 16-bit numeric value";
             type union {
               type int16;
               type string {
                 pattern "<.*>|$.*";
               }
             }
           }
         }
         case case_4 {
           leaf unsigned-short {
             description "Unsigned 16-bit numeric value";
             type union {
               type uint16;
               type string {
                 pattern "<.*>|$.*";
               }
             }
           }
         }
         case case_5 {
           leaf integer {
             description "Signed 32-bit numeric value";
             type union {
               type int32;
               type string {
                 pattern "<.*>|$.*";
               }
             }
           }
         }
         case case_6 {
           leaf unsigned-integer {
             description "Unsigned 32-bit numeric value";
             type union {
               type uint32;
               type string {
                 pattern "<.*>|$.*";
               }
             }
           }
         }
         case case_7 {
           leaf hex-string {
             description "Hexadecimal string";
             type string {
               length "1 .. 510";
               junos:posix-pattern "^[[:xdigit:]]+$";
               junos:pattern-message "Must be hexadecimal digits (0-9, a-f, A-F)";
             }
           }
         }
         case case_8 {
           leaf string {
             description "Character string value";
             type string {
               length "1 .. 254";
             }
           }
         }
         case case_9 {
           leaf ip-address {
             description "IP address value";
             type jt:ipv4addr;
           }
         }
         case case_10 {
           leaf ipv6-address {
             description "IPV6 address value";
             type jt:ipv6addr;
           }
         }
         case case_11 {
           container array {
             presence "enable array";
             description "Array of values";
             uses apply-advanced;
             choice option-type-array-choice {
               case case_1 {
                 leaf-list flag {
                   description "Array of boolean flag values";
                   type enumeration {
                     enum "true" {
                       description "True value";
                     }
                     enum "false" {
                       description "False value";
                     }
                     enum "on" {
                       description "On value";
                     }
                     enum "off" {
                       description "Off value";
                     }
                   }
                 }
               }
               case case_2 {
                 leaf-list byte {
                   description "Array of unsigned 8-bit values";
                   type union {
                     type uint8;
                     type string {
                       pattern "<.*>|$.*";
                     }
                   }
                 }
               }
               case case_3 {
                 leaf-list short {
                   description "Array of signed 16-bit numeric values";
                   type union {
                     type int16;
                     type string {
                       pattern "<.*>|$.*";
                     }
                   }
                 }
               }
               case case_4 {
                 leaf-list unsigned-short {
                   description "Array of 16-bit numeric values";
                   type union {
                     type uint16;
                     type string {
                       pattern "<.*>|$.*";
                     }
                   }
                 }
               }
               case case_5 {
                 leaf-list integer {
                   description "Array of signed 32-bit numeric values";
                   type union {
                     type int32;
                     type string {
                       pattern "<.*>|$.*";
                     }
                   }
                 }
               }
               case case_6 {
                 leaf-list unsigned-integer {
                   description "Array of unsigned 32-bit numeric values";
                   type union {
                     type uint32;
                     type string {
                       pattern "<.*>|$.*";
                     }
                   }
                 }
               }
               case case_7 {
                 leaf-list hex-string {
                   description "Hexadecimal string";
                   type string {
                     length "1 .. 510";
                   }
                 }
               }
               case case_8 {
                 leaf-list string {
                   description "Array of character string values";
                   type string {
                     length "1 .. 254";
                   }
                 }
               }
               case case_9 {
                 leaf-list ip-address {
                   description "Array of IP address values";
                   type jt:ipv4addr;
                 }
               }
               case case_10 {
                 leaf-list ipv6-address {
                   description "Array of IPv6 address values";
                   type jt:ipv6addr;
                 }
               }
             }
           }
         }
       }
     }
     leaf valid-lifetime {
       description "Valid lifetime advertised to clients";
       units "seconds";
       junos:must "(!(\".. maximum-lease-time\"))";
       junos:must-message "'valid-lifetime' statement cannot be included along with 'maximum-lease-time'";
       type string;
     }
     leaf preferred-lifetime {
       description "Preferred lifetime advertised to clients";
       units "seconds";
       junos:must "(!(\".. maximum-lease-time\"))";
       junos:must-message "'preferred-lifetime' statement cannot be included along with 'maximum-lease-time'";
       type string;
     }
     leaf t1-percentage {
       description "T1 time as percentage of preferred lifetime or max lease";
       units "percent";
       junos:must "(!(\".. t2-rebinding-time\"))";
       junos:must-message "T1 must be configured in seconds to match T2";
       junos:must "(!(\".. t1-renewal-time\"))";
       junos:must-message "T1 time in seconds already configured";
       type union {
         type string {
           pattern "<.*>|$.*";
         }
         type uint32 {
           range "0 .. 100";
         }
       }
     }
     leaf t2-percentage {
       description "T2 time as percentage of preferred lifetime or max lease";
       units "percent";
       junos:must "(!(\".. t1-renewal-time\"))";
       junos:must-message "T2 must be configured in seconds to match T1";
       junos:must "(!(\".. t2-rebinding-time\"))";
       junos:must-message "T2 time in seconds already configured";
       type union {
         type string {
           pattern "<.*>|$.*";
         }
         type uint32 {
           range "0 .. 100";
         }
       }
     }
     leaf exclude-prefix-len {
       description "Length of IPv6 prefix to be excluded from delegated prefix";
       type union {
         type string {
           pattern "<.*>|$.*";
         }
         type uint32 {
           range "1 .. 128";
         }
       }
     }
     leaf t1-renewal-time {
       description "T1 renewal time";
       units "seconds";
       junos:must "(!(\".. t2-percentage\"))";
       junos:must-message "T1 must be configured as percentage to match T2";
       junos:must "(!(\".. t1-percentage\"))";
       junos:must-message "T1 time as percentage already configured";
       type union {
         type uint32;
         type string {
           pattern "<.*>|$.*";
         }
       }
     }
     leaf t2-rebinding-time {
       description "T2 rebinding time";
       units "seconds";
       junos:must "(!(\".. t1-percentage\"))";
       junos:must-message "T2 must be configured as percentage to match T1";
       type union {
         type uint32;
         type string {
           pattern "<.*>|$.*";
         }
       }
     }
   }
   grouping domain-map-type {
     description "Domain map configuration";
     uses apply-advanced;
     list map {
       key name;
       ordered-by user;
       description "Domain map definitions";
       leaf name {
         description "Domain map name";
         type string {
           length "1 .. 64";
         }
       }
       uses apply-advanced;
       choice aaa_ri_or_ls {
         case case_1 {
           leaf aaa-routing-instance {
             description "Routing instance to be used for applying AAA services";
             type string;
           }
         }
         case case_2 {
           list aaa-logical-system {
             key name;
             ordered-by user;
             description "Logical system to be used for applying AAA services";
             max-elements 1;
             leaf name {
               description "Logical system name";
               junos:must "(\"logical-systems $$\")";
               junos:must-message "Referenced logical system must be defined";
               type string;
             }
             uses apply-advanced;
             leaf aaa-routing-instance {
               description "Routing instance to be used for applying AAA services";
               type string;
             }
           }
         }
       }
       leaf access-profile {
         description "Access profile to be used for applying AAA services";
         junos:must "(\".. .. .. profile $$\")";
         junos:must-message "Referenced access profile must be defined";
         type string {
           length "1 .. 63";
         }
       }
       leaf address-pool {
         description "Address pool to use for providing address-allocation services";
         type string {
           length "1 .. 63";
           junos:posix-pattern "^[A-Za-z0-9][_0-9A-Za-z-]{0,62}$";
           junos:pattern-message "Must be a string beginning with a number or letter and consisting of no more than 63 total letters, numbers, dashes and underscores.";
         }
       }
       leaf dynamic-profile {
         description "Dynamic profile to be used for this client's session";
         junos:must "(\"dynamic-profiles $$\")";
         junos:must-message "Dynamic profile must be defined";
         type string {
           length "1 .. 80";
         }
       }
       leaf override-password {
         description "Use this password for authentication";
         type string {
           length "1 .. 64";
         }
       }
       list padn {
         key name;
         ordered-by user;
         description "PPPoE Active Discovery Network parameters to apply for this client's session";
         max-elements 16;
         leaf name {
           description "Destination IP address";
           type jt:ipv4addr;
         }
         uses apply-advanced;
         leaf mask {
           description "Destination mask";
           type jt:ipv4addr;
         }
         leaf metric {
           description "Metric value";
           type union {
             type string {
               pattern "<.*>|$.*";
             }
             type uint16 {
               range "0 .. 255";
             }
           }
         }
       }
       choice target_ri_or_ls {
         case case_1 {
           leaf target-routing-instance {
             description "Routing instance the client's session will be mapped to";
             type string;
           }
         }
         case case_2 {
           list target-logical-system {
             key name;
             ordered-by user;
             description "Logical system the client's session will be mapped to";
             max-elements 1;
             leaf name {
               description "Logical system name";
               junos:must "(\"logical-systems $$\")";
               junos:must-message "Referenced logical system must be defined";
               type string;
             }
             uses apply-advanced;
             leaf target-routing-instance {
               description "Routing instance the client's session will be mapped to";
               type string;
             }
           }
         }
       }
       leaf strip-domain {
         description "Enable domain name stripping from the username";
         junos:must "(!(\".. strip-username\"))";
         junos:must-message "Mutually exclusive with strip-username";
         type empty;
       }
       container strip-username {
         presence "enable strip-username";
         junos:must "(!(\".. strip-domain\"))";
         junos:must-message "Mutually exclusive with strip-domain";
         description "Enable user name stripping from the username";
         choice direction {
           case case_1 {
             leaf right-to-left {
               description "Strip to first domain delimiter on the right";
               type empty;
             }
           }
           case case_2 {
             leaf left-to-right {
               description "Strip to first domain delimiter on the left";
               type empty;
             }
           }
         }
       }
     }
     container parse-order {
       description "Order in which search parsing is conducted (i.e. look for domain-namd or realm-name first)";
       choice order {
         case case_1 {
           leaf domain-first {
             description "Search for domain name in username field before searching for realm name";
             type empty;
           }
         }
         case case_2 {
           leaf realm-first {
             description "Search for realm name in username field before searching for domain name";
             type empty;
           }
         }
       }
     }
     container delimiter {
       description "Allowable delimiter characters for domain name separation";
       leaf characters {
         description "Sequence of characters without spaces and commas";
         type string {
           length "1 .. 8";
         }
       }
     }
     container parse-direction {
       description "Domain name parsing direction";
       choice direction {
         case case_1 {
           leaf right-to-left {
             description "Parse the username from right to left";
             type empty;
           }
         }
         case case_2 {
           leaf left-to-right {
             description "Parse the username field from left to right to find domain name";
             type empty;
           }
         }
       }
     }
     container realm-delimiter {
       description "Allowable delimiter characters for realm name separation";
       leaf characters {
         description "Sequence of characters without spaces and commas";
         type string {
           length "1 .. 8";
         }
       }
     }
     container realm-parse-direction {
       description "Realm name parsing direction";
       choice direction {
         case case_1 {
           leaf left-to-right {
             description "Parse the username field from left to right to find realm name";
             type empty;
           }
         }
         case case_2 {
           leaf right-to-left {
             description "Parse the username field from right to left to find realm name";
             type empty;
           }
         }
       }
     }
   }
   grouping group-profile-object {
     leaf name {
       description "Group profile name";
       type string {
         length "1 .. 63";
         junos:posix-pattern "^[[:alnum:]][[:alnum:]_-]*$";
         junos:pattern-message "Must be a string beginning with a number or letter and consisting of letters, numbers, dashes and underscores.";
       }
     }
     uses apply-advanced;
     container ppp {
       presence "enable ppp";
       junos:must "(!(\".. l2tp\"))";
       junos:must-message "A group-profile can have either PPP or L2TP attributes only";
       description "Configuration for Point-to-Point Protocol";
       uses apply-advanced;
       leaf framed-pool {
         description "Address pool used to assign an address for the user";
         junos:must "(\"access address-pool $$\")";
         junos:must-message "referenced address pool must be defined";
         type string {
           length "1 .. 63";
         }
       }
       leaf idle-timeout {
         description "Idle timeout before termination of session";
         default "0";
         units "seconds";
         type union {
           type string {
             pattern "<.*>|$.*";
           }
           type uint32 {
             range "0 .. 4294967295";
           }
         }
       }
       container ppp-options {
         presence "enable ppp-options";
         description "Point-to-Point Protocol interface-specific options";
         uses apply-advanced;
         leaf pap {
           description "Password Authentication Protocol";
           type empty;
         }
         leaf chap {
           description "Challenge Handshake Authentication Protocol";
           type empty;
         }
         container initiate-ncp {
           description "Enable server initiated NCP";
           uses apply-advanced;
           leaf ip {
             description "Enable server initiated IPNCP";
             type empty;
           }
           leaf ipv6 {
             description "Enable server initiated IPv6NCP";
             type empty;
           }
           leaf dual-stack-passive {
             description "Disable server initiated IPNCP/IPv6NCP for dual-stack client";
             type empty;
           }
         }
         leaf peer-ip-address-optional {
           description "Set Peer IP Address Optional in IP NCP Negotiations";
           type empty;
         }
         leaf ipcp-suggest-dns-option {
           description "Suggest peer to negotiate with DNS Adresses options";
           type empty;
         }
         leaf aaa-options {
           description "Attach AAA options name to group-profile";
           junos:must "(\"access aaa-options $$\")";
           junos:must-message "referenced aaa-options name must be defined";
           type string {
             length "1 .. 63";
           }
         }
       }
       leaf keepalive {
         description "PPP keepalive interval";
         default "10";
         units "seconds";
         type union {
           type string {
             pattern "<.*>|$.*";
           }
           type uint16 {
             range "0 .. 32767";
           }
         }
       }
       leaf primary-dns {
         description "Primary DNS server name";
         type string;
       }
       leaf secondary-dns {
         description "Secondary DNS server name";
         type string;
       }
       leaf primary-wins {
         description "Primary wins server name";
         type string;
       }
       leaf secondary-wins {
         description "Secondary wins server name";
         type string;
       }
       leaf encapsulation-overhead {
         description "Encapsulation overhead for Class of Service calculation";
         type union {
           type string {
             pattern "<.*>|$.*";
           }
           type int8 {
             range "-63 .. 64";
           }
         }
       }
       leaf cell-overhead {
         description "ATM cell overhead for Class of Service calculation";
         type empty;
       }
       leaf interface-id {
         description "Interface identifier to look up session information";
         type string {
           length "1 .. 63";
           junos:posix-pattern "^[A-Za-z0-9][_0-9A-Za-z-]{0,62}$";
           junos:pattern-message "Must be a string beginning with a number or letter and consisting of no more than 63 total letters, numbers, dashes and underscores.";
         }
       }
     }
   }
   grouping gx-plus-definition {
     description "GX-PLUS configuration definition";
     uses apply-advanced;
     list partition {
       key name;
       ordered-by user;
       description "GX-PLUS partition configuration";
       leaf name {
         description "GX-PLUS partition name";
         type string {
           length "1 .. 63";
         }
       }
       uses apply-advanced;
       leaf diameter-instance {
         description "GX-PLUS diameter instance";
         junos:must "(\"diameter origin\")";
         junos:must-message "Diameter origin must be defined in the [edit diameter origin] hierarchy";
         type string {
           length "1 .. 63";
           junos:posix-pattern "master";
           junos:pattern-message "Only one diameter instance is supported";
         }
       }
       leaf destination-realm {
         description "GX-PLUS destination realm";
         type string {
           length "1 .. 255";
         }
       }
       leaf destination-host {
         description "GX-PLUS destination host";
         type string {
           length "1 .. 255";
         }
       }
     }
     container global {
       presence "enable global";
       description "GX-PLUS global parameters";
       uses apply-advanced;
       leaf include-ipv6 {
         description "Send provisioning request for IPv6-only subscribers";
         type empty;
       }
       leaf max-outstanding-requests {
         description "Maximum number of outstanding requests";
         default "40";
         type union {
           type string {
             pattern "<.*>|$.*";
           }
           type uint32 {
             range "2 .. 40";
           }
         }
       }
     }
   }
   grouping ldap-server-object {
     leaf name {
       description "Hostname or IPv4 address of LDAP server";
       type string {
         junos:posix-pattern "^[[:alnum:]._-]+$";
         junos:pattern-message "Hostname can only contain alphanumeric characters, '.', '-', and '_'. The format of IPv4 address is 'n.n.n.n'";
       }
     }
     uses apply-advanced;
     leaf port {
       description "LDAP server port number";
       default "389";
       type union {
         type string {
           pattern "<.*>|$.*";
         }
         type uint16 {
           range "1 .. 65535";
         }
       }
     }
     leaf source-address {
       description "Use specified address as source address";
       type jt:ipv4addr;
     }
     leaf routing-instance {
       description "Use specified routing instance";
       junos:must "(\"routing-instances $$\")";
       junos:must-message "referenced routing-instance must be defined";
       type string;
     }
     leaf retry {
       description "Number of times to resend requests";
       default "3";
       type union {
         type string {
           pattern "<.*>|$.*";
         }
         type uint32 {
           range "1 .. 10";
         }
       }
     }
     leaf timeout {
       description "Delay before resending unacknowledged request";
       default "5";
       units "seconds";
       type union {
         type string {
           pattern "<.*>|$.*";
         }
         type uint32 {
           range "3 .. 90";
         }
       }
     }
     leaf tls-type {
       type enumeration {
         enum "start-tls" {
           description "Negotiate start-tls for connection";
         }
       }
     }
     leaf tls-timeout {
       description "Limit on tls handshake time";
       default "5";
       units "seconds";
       type union {
         type string {
           pattern "<.*>|$.*";
         }
         type uint32 {
           range "3 .. 90";
         }
       }
     }
     leaf tls-min-version {
       default "v1.2";
       type enumeration {
         enum "v1.1" {
           description "Require tls 1.1 and 1.2";
         }
         enum "v1.2" {
           description "Require tls 1.2";
         }
       }
     }
     leaf no-tls-certificate-check {
       description "Do not validate peer certificate";
       type empty;
     }
     leaf tls-peer-name {
       description "Expected peer fdqn";
       type string {
         length "1 .. 255";
       }
     }
   }
   grouping macro-data-type {
     leaf name {
       description "Keyword part of the keyword-value pair";
       type string;
     }
     leaf value {
       description "Value part of the keyword-value pair";
       type string;
     }
   }
   grouping nasreq-definition {
     description "NASREQ configuration definition";
     uses apply-advanced;
     list partition {
       key name;
       ordered-by user;
       description "NASREQ partition definition";
       leaf name {
         description "NASREQ partition name";
         type string {
           length "1 .. 63";
         }
       }
       uses apply-advanced;
       leaf diameter-instance {
         description "NASREQ diameter instance";
         junos:must "(\"diameter origin\")";
         junos:must-message "Diameter origin must be defined in the [edit diameter origin] hierarchy";
         type string {
           length "1 .. 63";
           junos:posix-pattern "master";
           junos:pattern-message "Only one diameter instance is supported";
         }
       }
       leaf destination-realm {
         description "NASREQ destination realm";
         type string {
           length "1 .. 255";
         }
       }
       leaf destination-host {
         description "NASREQ destination host";
         type string {
           length "1 .. 255";
         }
       }
     }
     leaf timeout {
       description "Time period that a NASREQ request waits on the transmit queue before failing";
       default "20";
       units "seconds";
       type union {
         type string {
           pattern "<.*>|$.*";
         }
         type uint32 {
           range "5 .. 30";
         }
       }
     }
     leaf request-retry {
       description "Number of times to retry NASREQ request when DIAMETER fails with timeout.";
       default "0";
       type union {
         type string {
           pattern "<.*>|$.*";
         }
         type uint32 {
           range "0 .. 3";
         }
       }
     }
     leaf max-outstanding-requests {
       description "Number of unanswered NASREQ requests sent to server";
       default "40";
       type union {
         type string {
           pattern "<.*>|$.*";
         }
         type uint32 {
           range "20 .. 2000";
         }
       }
     }
   }
   grouping ocs-definition {
     description "OCS configuration definition";
     uses apply-advanced;
     list partition {
       key name;
       ordered-by user;
       description "OCS partition configuration";
       max-elements 1;
       leaf name {
         description "OCS partition name";
         type string {
           length "1 .. 63";
         }
       }
       uses apply-advanced;
       leaf alternative-partition-name {
         description "Alternative diameter partition";
         type string {
           length "1 .. 63";
         }
       }
       leaf called-station-id {
         description "OCS called station id";
         type string {
           length "1 .. 255";
         }
       }
       leaf charging-id {
         description "OCS charging id";
         type union {
           type uint32;
           type string {
             pattern "<.*>|$.*";
           }
         }
       }
       leaf destination-realm {
         description "OCS destination realm";
         type string {
           length "1 .. 255";
         }
       }
       leaf destination-host {
         description "OCS destination host";
         type string {
           length "1 .. 255";
         }
       }
       leaf diameter-instance {
         description "OCS diameter instance";
         junos:must "(\"diameter origin\")";
         junos:must-message "Diameter origin must be defined in the [edit diameter origin] hierarchy";
         type string {
           length "1 .. 63";
           junos:posix-pattern "master";
           junos:pattern-message "Only one diameter instance is supported";
         }
       }
       leaf draining {
         description "Set this PCRF partiton to draining state";
         type empty;
       }
       leaf draining-response-timeout {
         description "Final response timeout in draining mode";
         default "30";
         units "seconds";
         type union {
           type string {
             pattern "<.*>|$.*";
           }
           type uint32 {
             range "1 .. 86400";
           }
         }
       }
       leaf force-continue {
         description "Expect/force 'continue' as cc-failure-handling value";
         type empty;
       }
       leaf ggsn-address {
         description "Value of ggsn-address avp reported to ocs";
         type jt:ipaddr;
       }
       leaf ggsn-mcc-mnc {
         description "Value of 3gpp-ggsn-mcc-mnc avp reported to ocs";
         type string;
       }
       leaf final-response-timeout {
         description "Final response timeout";
         default "86400";
         units "seconds";
         type union {
           type string {
             pattern "<.*>|$.*";
           }
           type uint32 {
             range "1 .. 86400";
           }
         }
       }
       leaf max-outstanding-requests {
         description "Maximum number of outstanding requests";
         default "40";
         type union {
           type string {
             pattern "<.*>|$.*";
           }
           type uint32 {
             range "2 .. 40";
           }
         }
       }
       leaf send-origin-state-id {
         description "Include origin-state-id avp";
         type empty;
       }
       container user-name-include {
         description "Add user-name options";
         uses apply-advanced;
         leaf delimiter {
           description "Change delimiter/separator character";
           type string {
             length 1;
           }
         }
         leaf domain-name {
           description "Domain name";
           type string {
             length "1 .. 64";
           }
         }
         leaf interface-name {
           description "Include interface-name";
           type empty;
         }
         leaf base-interface-name {
           description "Include base-interface-name";
           type empty;
         }
         leaf mac-address {
           description "Include MAC address";
           type empty;
         }
         leaf nas-port-id {
           description "Include nas-port-id";
           type empty;
         }
         leaf origin-host {
           description "Include origin-host";
           type empty;
         }
         leaf origin-realm {
           description "Include origin-host";
           type empty;
         }
         leaf user-prefix {
           description "Add user defined prefix";
           type string {
             length "1 .. 64";
           }
         }
         leaf user-name {
           description "Include user-name";
           type empty;
         }
       }
     }
     container global {
       description "OCS global parameters";
       uses apply-advanced;
       leaf service-context-id {
         description "Service context-id for OCS";
         type string {
           length "1 .. 255";
         }
       }
     }
   }
   grouping pcrf-definition {
     description "PCRF configuration definition";
     uses apply-advanced;
     list partition {
       key name;
       ordered-by user;
       description "PCRF partition configuration";
       max-elements 1;
       leaf name {
         description "PCRF partition name";
         type string {
           length "1 .. 63";
         }
       }
       uses apply-advanced;
       leaf accept-sdr {
         description "Accept service discovery requests";
         type empty;
       }
       leaf destination-realm {
         description "PCRF destination realm";
         type string {
           length "1 .. 255";
         }
       }
       leaf destination-host {
         description "PCRF destination host";
         type string {
           length "1 .. 255";
         }
       }
       leaf diameter-instance {
         description "PCRF diameter instance";
         junos:must "(\"diameter origin\")";
         junos:must-message "Diameter origin must be defined in the [edit diameter origin] hierarchy";
         type string {
           length "1 .. 63";
           junos:posix-pattern "master";
           junos:pattern-message "Only one diameter instance is supported";
         }
       }
       leaf draining {
         description "Set this PCRF partiton to draining state";
         type empty;
       }
       leaf draining-response-timeout {
         description "Logout response timeout in draining mode";
         default "30";
         units "seconds";
         type union {
           type string {
             pattern "<.*>|$.*";
           }
           type uint32 {
             range "1 .. 86400";
           }
         }
       }
       leaf ip-can-type {
         description "Value of IP-CAN-Type AVP for this PCRF partition";
         default "77";
         type union {
           type string {
             pattern "<.*>|$.*";
           }
           type uint32 {
             range "1 .. 2147483647";
           }
         }
       }
       container local-decision {
         description "Local decision configuration";
         uses apply-advanced;
         choice permission {
           case case_1 {
             leaf grant {
               description "Grant user connection by default";
               type empty;
             }
           }
           case case_2 {
             leaf deny {
               description "Deny user connection by default";
               type empty;
             }
           }
         }
         leaf timeout {
           description "Local decision timeout";
           default "90";
           units "seconds";
           type union {
             type string {
               pattern "<.*>|$.*";
             }
             type uint32 {
               range "1 .. 90";
             }
           }
         }
       }
       leaf logout-response-timeout {
         description "Logout response timeout";
         default "86400";
         units "seconds";
         type union {
           type string {
             pattern "<.*>|$.*";
           }
           type uint32 {
             range "1 .. 86400";
           }
         }
       }
       leaf max-outstanding-requests {
         description "Maximum number of outstanding requests";
         default "40";
         type union {
           type string {
             pattern "<.*>|$.*";
           }
           type uint32 {
             range "2 .. 40";
           }
         }
       }
       leaf report-local-rule {
         description "Report installed local rule to PCRF";
         type empty;
       }
       leaf report-resource-allocation {
         description "Report rule installation failuresto PCRF";
         type empty;
       }
       leaf report-successful-resource-allocation {
         description "Report rule installation successes to PCRF";
         type empty;
       }
       leaf send-dyn-subscription-indicator {
         description "Include Juniper-Dyn-Subscription-Indidicator into ccr-i";
         type empty;
       }
       leaf send-network-family-indicator {
         description "Include Juniper-Network-Family-Indidicator into ccr-i";
         type empty;
       }
       leaf send-origin-state-id {
         description "Include origin-state-id avp";
         type empty;
       }
       leaf subscription-id-type {
         description "Value of subscription-id-type AVP for this PCRF partition";
         default "4";
         type union {
           type string {
             pattern "<.*>|$.*";
           }
           type uint32 {
             range "1 .. 2147483647";
           }
         }
       }
       container subscription-id-data-include {
         description "Add subscription-id-data options";
         uses apply-advanced;
         leaf delimiter {
           description "Change delimiter/separator character";
           type string {
             length 1;
           }
         }
         leaf domain-name {
           description "Domain name";
           type string {
             length "1 .. 64";
           }
         }
         leaf interface-name {
           description "Include interface-name";
           type empty;
         }
         leaf base-interface-name {
           description "Include base-interface-name";
           type empty;
         }
         leaf mac-address {
           description "Include MAC address";
           type empty;
         }
         leaf nas-port-id {
           description "Include nas-port-id";
           type empty;
         }
         leaf origin-host {
           description "Include origin-host";
           type empty;
         }
         leaf origin-realm {
           description "Include origin-host";
           type empty;
         }
         leaf user-prefix {
           description "Add user defined prefix";
           type string {
             length "1 .. 64";
           }
         }
         leaf user-name {
           description "Include user-name";
           type empty;
         }
       }
       leaf update-response-timeout {
         description "Update response timeout";
         default "3600";
         units "seconds";
         type union {
           type string {
             pattern "<.*>|$.*";
           }
           type uint32 {
             range "1 .. 86400";
           }
         }
       }
     }
     container global {
       description "PCRF global parameters";
       uses apply-advanced;
       list rule-param {
         key name;
         ordered-by user;
         description "Charging juniper-param avp configuraion";
         leaf name {
           description "Code for this juniper-param avp";
           type union {
             type string {
               pattern "<.*>|$.*";
             }
             type uint32 {
               range "12000 .. 12019";
             }
           }
         }
         uses apply-advanced;
         leaf param-name {
           description "Name associatated with this juniper-param avp";
           type string {
             length "1 .. 255";
           }
         }
         leaf log-name {
           description "Log-name associatated with this juniper-param avp";
           type string {
             length "1 .. 255";
           }
         }
       }
     }
   }
   grouping profile-radius-server-object {
     leaf name {
       description "RADIUS server address";
       type jt:ipaddr;
     }
     uses apply-advanced;
     leaf port {
       description "RADIUS server authentication port number";
       default "1812";
       type union {
         type string {
           pattern "<.*>|$.*";
         }
         type uint16 {
           range "1 .. 65535";
         }
       }
     }
     leaf preauthentication-port {
       description "RADIUS server preauthentication port number";
       type union {
         type string {
           pattern "<.*>|$.*";
         }
         type uint16 {
           range "1 .. 65535";
         }
       }
     }
     leaf accounting-port {
       description "Port number to which to send RADIUS accounting messages";
       default "1813";
       type union {
         type string {
           pattern "<.*>|$.*";
         }
         type uint16 {
           range "1 .. 65535";
         }
       }
     }
     leaf dynamic-request-port {
       description "RADIUS client dynamic request port number";
       default "3799";
       type union {
         type string {
           pattern "<.*>|$.*";
         }
         type uint16 {
           range "1 .. 65535";
         }
       }
     }
     leaf secret {
       description "Shared secret with the RADIUS server";
       type jt:unreadable;
     }
     leaf preauthentication-secret {
       description "Shared secret with the RADIUS server";
       type jt:unreadable;
     }
     leaf timeout {
       description "Request timeout period";
       default "3";
       units "seconds";
       type union {
         type string {
           pattern "<.*>|$.*";
         }
         type uint32 {
           range "1 .. 1000";
         }
       }
     }
     leaf retry {
       description "Retry attempts";
       default "3";
       type union {
         type string {
           pattern "<.*>|$.*";
         }
         type uint32 {
           range "1 .. 100";
         }
       }
     }
     leaf accounting-timeout {
       description "Accounting request timeout period";
       default "0";
       units "seconds";
       type union {
         type string {
           pattern "<.*>|$.*";
         }
         type uint32 {
           range "0 .. 1000";
         }
       }
     }
     leaf accounting-retry {
       description "Accounting retry attempts";
       default "0";
       type union {
         type string {
           pattern "<.*>|$.*";
         }
         type uint32 {
           range "0 .. 100";
         }
       }
     }
     leaf max-outstanding-requests {
       description "Maximum requests in flight to server";
       default "1000";
       type union {
         type string {
           pattern "<.*>|$.*";
         }
         type uint32 {
           range "0 .. 2000";
         }
       }
     }
     leaf source-address {
       description "Use specified address as source address";
       type jt:ipaddr;
     }
     leaf routing-instance {
       description "Use specified routing instance";
       junos:must "(\"routing-instances $$\")";
       junos:must-message "referenced routing-instance must be defined";
       type string;
     }
   }
   grouping protocol-attribute-type {
     description "Protocol specific attribute configuration";
     leaf name {
       description "Name for this protocol attribute group";
       type string {
         length "1 .. 63";
         junos:posix-pattern "^[A-Za-z0-9][_0-9A-Za-z-]{0,62}$";
         junos:pattern-message "Must be a string beginning with a number or letter and consisting of no more than 63 total letters, numbers, dashes and underscores.";
       }
     }
     uses apply-advanced;
     container dhcp {
       description "DHCPv4 configurable attributes";
       uses dhcp-attribute-type;
     }
     container dhcpv6 {
       description "DHCPv6 configurable attributes";
       uses dhcp-attribute-type;
     }
   }
   grouping securid-server-object {
     leaf name {
       description "Name of the SecurID server";
       type string;
     }
     uses apply-advanced;
     leaf configuration-file {
       description "Path to the SecurID server configuration (sdconf.rec) file";
       type string {
         length "1 .. 1024";
       }
     }
   }
 }
