/*
 * Copyright (c) 2017 Juniper Networks, Inc.
 * All rights reserved.
 */
 module junos-es-conf-policy-options {
   namespace "http://yang.juniper.net/junos-es/conf/policy-options";

   prefix jc-policy-options;

   import junos-common-ddl-extensions {
     prefix junos;
   }

   import junos-common-types {
     prefix jt;
   }

   import junos-es-conf-root {
     prefix jc;
   }

   organization "Juniper Networks, Inc.";

   contact "yang-support@juniper.net";

   description "Junos policy-options configuration module";

   revision 2017-01-01 {
     description "Junos: 17.4R1.16";
   }

   augment /jc:configuration {
     uses policy-options-group;
   }
   augment /jc:configuration/jc:groups {
     uses policy-options-group;
   }
   grouping policy-options-group {
     container policy-options {
       description "Policy option configuration";
       uses juniper-policy-options;
     }
   }
   grouping juniper-policy-options {
     description "Define a redundancy policy";
     uses apply-advanced;
     container satellite-policies {
       description "Satellite Policy configuration";
       uses satellite-policy-options;
     }
     list prefix-list {
       key name;
       ordered-by user;
       description "Define a named set of address prefixes";
       leaf name {
         description "Prefix list name";
         type string;
       }
       uses apply-advanced;
       list prefix-list-item {
         key name;
         uses prefix_list_items;
       }
       leaf apply-path {
         description "Apply IP prefixes from a configuration statement";
         type string;
       }
     }
     list route-filter-list {
       key name;
       ordered-by user;
       description "Define a named set of route-filter address prefixes";
       leaf name {
         description "Route filter list name";
         type string;
       }
       uses apply-advanced;
       list rf_list {
         key "address choice-ident choice-value";
         ordered-by user;
         uses route_filter_list_items;
       }
     }
     list source-address-filter-list {
       key name;
       ordered-by user;
       description "Define a named set of source address filter address prefixes";
       leaf name {
         description "Source address filter list name";
         type string;
       }
       uses apply-advanced;
       list saf_list {
         key "address choice-ident choice-value";
         ordered-by user;
         uses source_address_filter_list_items;
       }
     }
     list mac-list {
       key name;
       ordered-by user;
       description "Define a named set of mac addresses";
       leaf name {
         description "MAc Address list name";
         type string;
       }
       uses apply-advanced;
       list mac-addr-list-item {
         key name;
         uses mac_addr_list_items;
       }
     }
     list vsi-policy {
       key name;
       ordered-by user;
       description "Define a named set of VSI policies";
       leaf name {
         description "VSI policy name";
         type string;
       }
       uses apply-advanced;
       container from {
         description "Conditions to match the VSI policy";
         uses apply-advanced;
         list vsi-manager {
           key "vsi-manager-id vsi-type vsi-version vsi-instance";
           ordered-by user;
           description "VSI manager";
           leaf vsi-manager-id {
             description "VSI manager ID";
             type union {
               type string {
                 pattern "<.*>|$.*";
               }
               type uint32 {
                 range "1 .. 255";
               }
             }
           }
           leaf vsi-type {
             description "VSI type";
             type union {
               type string {
                 pattern "<.*>|$.*";
               }
               type uint32 {
                 range "1 .. 16777216";
               }
             }
           }
           leaf vsi-version {
             description "VSI version";
             type union {
               type string {
                 pattern "<.*>|$.*";
               }
               type uint32 {
                 range "1 .. 255";
               }
             }
           }
           leaf vsi-instance {
             description "VSI instance";
             type string;
           }
           uses apply-advanced;
         }
       }
       container then {
         description "Actions to take if 'from' conditions match";
         uses apply-advanced;
         leaf filter {
           description "Filter name";
           junos:must "(\"firewall family ethernet-switching filter $$\")";
           junos:must-message "filter should be defined under 'firewall family ethernet-switching filter'";
           type string;
         }
       }
     }
     list policy-statement {
       key name;
       description "Routing policy";
       leaf name {
         description "Name to identify a policy filter";
         type string;
       }
       uses apply-advanced;
       container defaults {
         description "Policy default behaviour";
         uses apply-advanced;
         container route-filter {
           description "Set route filter behaviour";
           choice scope-choice {
             case case_1 {
               leaf no-walkup {
                 description "Route filter walk up disable";
                 type empty;
               }
             }
             case case_2 {
               leaf walkup {
                 description "Route filter walk up enable";
                 type empty;
               }
             }
           }
         }
       }
       list term {
         key name;
         ordered-by user;
         description "Policy term";
         leaf name {
           type string;
         }
         uses apply-advanced;
         container from {
           description "Conditions to match the source of a route";
           uses apply-advanced;
           leaf instance {
             description "Routing protocol instance";
             type string;
           }
           leaf instance-any {
             description "Any routing protocol instance";
             type empty;
           }
           leaf-list instance-list {
             description "A list of routing protocol instances";
             type string;
           }
           leaf family {
             type enumeration {
               enum "inet" {
                 description "IPv4 family";
               }
               enum "inet-vpn" {
                 description "IPv4-VPN family";
               }
               enum "inet6" {
                 description "IPv6 family";
               }
               enum "inet6-vpn" {
                 description "IPv6-VPN family";
               }
               enum "iso-vpn" {
                 description "ISO-VPN family";
               }
               enum "iso" {
                 description "ISO family";
               }
               enum "evpn" {
                 description "EVPN family";
               }
               enum "inet-mvpn" {
                 description "IPv4 Multicast VPN family";
               }
               enum "inet6-mvpn" {
                 description "IPv6 Multicast VPN family";
               }
               enum "inet-mdt" {
                 description "IPv4 MDT Signaling family";
               }
               enum "route-target" {
                 description "Local route target VPN family";
               }
               enum "traffic-engineering" {
                 description "Traffic Engineering family";
               }
             }
           }
           leaf-list protocol {
             description "Protocol from which route was learned";
             type enumeration {
               enum "aggregate" {
                 description "Aggregate routes";
               }
               enum "bgp" {
                 description "BGP";
               }
               enum "direct" {
                 description "Directly connected routes";
               }
               enum "dvmrp" {
                 description "Distance Vector Multicast Routing Protocol";
               }
               enum "isis" {
                 description "Intermediate System-to-Intermediate System";
               }
               enum "esis" {
                 description "End System-to-Intermediate System";
               }
               enum "l2circuit" {
                 description "Layer 2 circuits";
               }
               enum "l2vpn" {
                 description "Layer 2 MPLS virtual private networks";
               }
               enum "local" {
                 description "Local system addresses";
               }
               enum "ospf" {
                 description "Open Shortest Path First";
               }
               enum "ospf2" {
                 description "Open Shortest Path First Version 2";
               }
               enum "ospf3" {
                 description "Open Shortest Path First Version 3";
               }
               enum "pim" {
                 description "Protocol Independent Multicast";
               }
               enum "rip" {
                 description "Routing Information Protocol";
               }
               enum "ripng" {
                 description "Routing Information Protocol next generation";
               }
               enum "static" {
                 description "Statically defined addresses";
               }
               enum "arp" {
                 description "Addresses learned from ARP";
               }
               enum "frr" {
                 description "Addresses created by Host Fast Re-route";
               }
               enum "mpls" {
                 description "Multiprotocol Label Switching";
               }
               enum "ldp" {
                 description "Label Distribution Protocol";
               }
               enum "rsvp" {
                 description "Resource Reservation Protocol";
               }
               enum "msdp" {
                 description "Multicast Source Discovery Protocol";
               }
               enum "route-target" {
                 description "Local route target VPN membership";
               }
               enum "access" {
                 description "Access server routes";
               }
               enum "access-internal" {
                 description "Internal routes to directly connected clients";
               }
               enum "anchor" {
                 description "Anchor routes connected to UEs";
               }
               enum "bgp-static" {
                 description "BGP static routes";
               }
               enum "vpls" {
                 description "Virtual Private LAN Service";
               }
               enum "evpn" {
                 description "Ethernet VPN Service";
               }
               enum "spring-te" {
                 description "SPRING Traffic-Engineered";
               }
             }
           }
           leaf rib {
             description "Routing table";
             type string;
           }
           leaf-list neighbor {
             description "Neighboring router";
             type jt:ipaddr;
           }
           leaf-list next-hop {
             description "Next-hop router";
             type jt:ipaddr;
           }
           leaf-list interface {
             description "Interface name or address";
             type union {
               type jt:ipaddr-or-interface;
               type string {
                 pattern "<.*>|$.*";
               }
             }
           }
           leaf area {
             description "OSPF area identifier";
             type jt:areaid;
           }
           leaf-list as-path {
             description "Name of AS path regular expression (BGP only)";
             type string;
           }
           leaf-list as-path-group {
             description "Name of AS path group (BGP only)";
             type string;
           }
           leaf origin {
             description "BGP origin attribute";
             type enumeration {
               enum "igp" {
                 description "Path originated in the local IGP";
               }
               enum "egp" {
                 description "Path originated in another AS";
               }
               enum "incomplete" {
                 description "Path was learned by some other means";
               }
             }
           }
           leaf-list community {
             description "BGP community";
             type string;
           }
           leaf level {
             description "IS-IS level";
             type union {
               type uint32;
               type string {
                 pattern "<.*>|$.*";
               }
             }
           }
           container external {
             presence "enable external";
             description "External route";
             uses apply-advanced;
             leaf type {
               description "OSPF external metric type";
               type union {
                 type string {
                   pattern "<.*>|$.*";
                 }
                 type int32 {
                   range "1 .. 2";
                 }
               }
             }
           }
           leaf validation-database {
             description "Name to identify a validation-state";
             type enumeration {
               enum "valid" {
                 description "Match for valid database validation-state";
               }
               enum "invalid" {
                 description "Match for invalid database validation-state";
               }
               enum "unknown" {
                 description "Match for unknown database validation-state";
               }
             }
           }
           leaf metric {
             description "Metric value";
             type union {
               type uint32;
               type string {
                 pattern "<.*>|$.*";
               }
             }
           }
           leaf metric2 {
             description "Metric value 2";
             type union {
               type uint32;
               type string {
                 pattern "<.*>|$.*";
               }
             }
           }
           leaf metric3 {
             description "Metric value 3";
             type union {
               type uint32;
               type string {
                 pattern "<.*>|$.*";
               }
             }
           }
           leaf metric4 {
             description "Metric value 4";
             type union {
               type uint32;
               type string {
                 pattern "<.*>|$.*";
               }
             }
           }
           leaf-list tag {
             description "Tag string";
             type union {
               type uint32;
               type string {
                 pattern "<.*>|$.*";
               }
             }
           }
           leaf tag2 {
             description "Tag string 2";
             type union {
               type uint32;
               type string {
                 pattern "<.*>|$.*";
               }
             }
           }
           leaf preference {
             description "Preference value";
             type union {
               type uint32;
               type string {
                 pattern "<.*>|$.*";
               }
             }
           }
           leaf preference2 {
             description "Preference value 2";
             type union {
               type uint32;
               type string {
                 pattern "<.*>|$.*";
               }
             }
           }
           leaf color {
             description "Color (preference) value";
             type union {
               type uint32;
               type string {
                 pattern "<.*>|$.*";
               }
             }
           }
           leaf color2 {
             description "Color (preference) value 2";
             type union {
               type uint32;
               type string {
                 pattern "<.*>|$.*";
               }
             }
           }
           leaf local-preference {
             description "Local preference associated with a route";
             type union {
               type uint32;
               type string {
                 pattern "<.*>|$.*";
               }
             }
           }
           leaf-list policy {
             description "Name of policy to evaluate";
             type jt:policy-algebra;
           }
           list route-filter {
             key "address choice-ident choice-value";
             ordered-by user;
             description "List of routes to match";
             uses control_route_filter_type;
           }
           list source-address-filter {
             key "address choice-ident choice-value";
             ordered-by user;
             description "List of source addresses to match";
             uses control_source_address_filter_type;
           }
           list prefix-list {
             key name;
             ordered-by user;
             description "List of prefix-lists of routes to match";
             uses control_prefix_list_type;
           }
           list prefix-list-filter {
             key "list_name choice-ident choice-value";
             ordered-by user;
             description "List of prefix-list-filters to match";
             uses control_prefix_list_filter_type;
           }
           list rtf-prefix-list {
             key name;
             ordered-by user;
             description "List of rtf-prefix-lists of routes to match";
             uses control_rtf_prefix_list_type;
           }
           list route-filter-list {
             key name;
             ordered-by user;
             description "List of route-filter-lists of routes to match";
             uses control_route_filter_list_type;
           }
           list source-address-filter-list {
             key name;
             ordered-by user;
             description "List of source-address-filter-lists of routes to match";
             uses control_source_address_filter_list_type;
           }
           container multicast-scope {
             description "Multicast scope to match";
             choice scope-choice {
               case case_1 {
                 leaf node-local {
                   description "Node-local scope";
                   type empty;
                 }
               }
               case case_2 {
                 leaf link-local {
                   description "Link-local scope";
                   type empty;
                 }
               }
               case case_3 {
                 leaf site-local {
                   description "Site-local scope";
                   type empty;
                 }
               }
               case case_4 {
                 leaf organization-local {
                   description "Organization-local scope";
                   type empty;
                 }
               }
               case case_5 {
                 leaf global {
                   description "Global scope";
                   type empty;
                 }
               }
               case case_6 {
                 leaf scope_value {
                   description "Scope value";
                   type union {
                     type string {
                       pattern "<.*>|$.*";
                     }
                     type uint32 {
                       range "0 .. 15";
                     }
                   }
                 }
               }
             }
             choice scope-operator {
               case case_1 {
                 leaf orhigher {
                   description "Match higher values";
                   type empty;
                 }
               }
               case case_2 {
                 leaf orlower {
                   description "Match lower values";
                   type empty;
                 }
               }
             }
           }
           leaf aggregate-contributor {
             description "Match more specifics of an aggregate";
             type empty;
           }
           leaf state {
             description "Route state";
             type enumeration {
               enum "active" {
                 description "Active route";
               }
               enum "inactive" {
                 description "Inactive route";
               }
             }
           }
           leaf route-type {
             description "Route type";
             type enumeration {
               enum "internal" {
                 description "Internal route";
               }
               enum "external" {
                 description "External route";
               }
             }
           }
           leaf-list nlri-route-type {
             description "Route type from NLRI";
             junos:must "((\".. family evpn\" || (\".. family inet-mvpn\" || \".. family inet6-mvpn\")))";
             junos:must-message "nlri-route-type is only valid with a family qualifier such as evpn, inet-mvpn, inet6-mvpn, or other family that supports a route type";
             type union {
               type string {
                 pattern "<.*>|$.*";
               }
               type uint32 {
                 range "1 .. 10";
               }
             }
           }
           leaf next-hop-type {
             description "Next-hop type";
             type enumeration {
               enum "merged" {
                 description "Merged next hop";
               }
             }
           }
           leaf-list condition {
             description "Condition to match on";
             type string;
           }
           list community-count {
             key name;
             ordered-by user;
             description "Number of BGP communities";
             uses community_count_type;
           }
           list as-path-unique-count {
             key name;
             ordered-by user;
             description "Number of unique BGP ASes excluding confederations";
             uses as-path-unique-count-type;
           }
           container traffic-engineering {
             presence "enable traffic-engineering";
             junos:must "(!(\".. family\"))";
             junos:must-message "traffic-engineering family implied";
             description "Traffic-Engineering related parameters";
             uses apply-advanced;
             leaf-list protocol {
               description "Protocol that originated the entry";
               type enumeration {
                 enum "direct" {
                   description "Directly originated";
                 }
                 enum "ospf" {
                   description "OSPF originated";
                 }
                 enum "isis-level-1" {
                   description "ISIS level-1 originated";
                 }
                 enum "isis-level-2" {
                   description "ISIS level-2 originated";
                 }
                 enum "static" {
                   description "Statically originated";
                 }
                 enum "unknown" {
                   description "Originated by unknown sources";
                 }
               }
             }
             container node {
               presence "enable node";
               junos:must "(!((\".. link\" || \".. ipv4-prefix\")))";
               junos:must-message "Link, prefix and node parameters cannot be configured at the same time";
               description "Node-related parameters";
               uses apply-advanced;
               leaf as {
                 description "AS number";
                 type string {
                   junos:posix-pattern "^[0-9]+(.[0-9]+)?$";
                   junos:pattern-message "Use format 'x' or 'x.y' to specify number 'x' (Range 1 .. 4294967295) or number with higher 2 bytes 'x' (Range 0 .. 65535) and lower 2 bytes 'y' (Range 0 .. 65535) respectively";
                 }
               }
               leaf node-type {
                 description "Real or pseudo-node";
                 type enumeration {
                   enum "router" {
                     description "Real node";
                   }
                   enum "pseudo-node" {
                     description "Pseudo-node";
                   }
                 }
               }
               leaf router-id {
                 description "IP prefix to match the router-id against";
                 type jt:ipprefix;
               }
               leaf sys-id {
                 description "ISO address of the node";
                 type jt:sysid;
               }
             }
             container ipv4-prefix {
               presence "enable ipv4-prefix";
               junos:must "(!((\".. link\" || \".. node\")))";
               junos:must-message "Link, prefix and node parameters cannot be configured at the same time";
               description "IPV4 prefix-related parameters";
               uses apply-advanced;
               leaf as {
                 description "AS number";
                 type string {
                   junos:posix-pattern "^[0-9]+(.[0-9]+)?$";
                   junos:pattern-message "Use format 'x' or 'x.y' to specify number 'x' (Range 1 .. 4294967295) or number with higher 2 bytes 'x' (Range 0 .. 65535) and lower 2 bytes 'y' (Range 0 .. 65535) respectively";
                 }
               }
               leaf router-id {
                 description "IP prefix to match the router-id against";
                 type jt:ipprefix;
               }
               leaf prefix {
                 description "IP prefix to match against";
                 type jt:ipprefix;
               }
               leaf sys-id {
                 description "ISO address of the node";
                 type jt:sysid;
               }
             }
             container link {
               presence "enable link";
               junos:must "(!((\".. node\" || \".. ipv4-prefix\")))";
               junos:must-message "Link, prefix and node parameters cannot be configured at the same time";
               description "Link-related parameters";
               uses apply-advanced;
               container from {
                 description "Specify parameter of the 'from' side";
                 uses apply-advanced;
                 leaf as {
                   description "AS number";
                   type string {
                     junos:posix-pattern "^[0-9]+(.[0-9]+)?$";
                     junos:pattern-message "Use format 'x' or 'x.y' to specify number 'x' (Range 1 .. 4294967295) or number with higher 2 bytes 'x' (Range 0 .. 65535) and lower 2 bytes 'y' (Range 0 .. 65535) respectively";
                   }
                 }
                 leaf router-id {
                   description "IP prefix to match the router-id against";
                   type jt:ipprefix;
                 }
                 leaf sys-id {
                   description "System-ID of the node";
                   type jt:sysid;
                 }
                 leaf node-type {
                   description "Type of the node";
                   type enumeration {
                     enum "router" {
                       description "Real node";
                     }
                     enum "pseudo-node" {
                       description "Pseudo-node";
                     }
                   }
                 }
                 leaf link-address {
                   description "IP prefix to match the link address against";
                   type jt:ipprefix;
                 }
               }
               container to {
                 description "Specify parameters of the 'to' side";
                 uses apply-advanced;
                 leaf as {
                   description "AS number";
                   type string {
                     junos:posix-pattern "^[0-9]+(.[0-9]+)?$";
                     junos:pattern-message "Use format 'x' or 'x.y' to specify number 'x' (Range 1 .. 4294967295) or number with higher 2 bytes 'x' (Range 0 .. 65535) and lower 2 bytes 'y' (Range 0 .. 65535) respectively";
                   }
                 }
                 leaf router-id {
                   description "IP prefix to match the router-id against";
                   type jt:ipprefix;
                 }
                 leaf sys-id {
                   description "System-ID of the node";
                   type jt:sysid;
                 }
                 leaf node-type {
                   description "Type of the node";
                   type enumeration {
                     enum "router" {
                       description "Real node";
                     }
                     enum "pseudo-node" {
                       description "Pseudo-node";
                     }
                   }
                 }
                 leaf link-address {
                   description "IP prefix to match the link address against";
                   type jt:ipprefix;
                 }
               }
             }
           }
           leaf-list route-distinguisher {
             description "Name of the route-distinguisher";
             type string;
           }
         }
         container to {
           description "Conditions to match the destination of a route";
           uses apply-advanced;
           leaf instance {
             description "Routing protocol instance";
             type string;
           }
           leaf instance-any {
             description "Any routing protocol instance";
             type empty;
           }
           leaf-list instance-list {
             description "A list of routing protocol instances";
             type string;
           }
           leaf family {
             type enumeration {
               enum "inet" {
                 description "IPv4 family";
               }
               enum "inet-vpn" {
                 description "IPv4-VPN family";
               }
               enum "inet6" {
                 description "IPv6 family";
               }
               enum "inet6-vpn" {
                 description "IPv6-VPN family";
               }
               enum "iso-vpn" {
                 description "ISO-VPN family";
               }
               enum "iso" {
                 description "ISO family";
               }
               enum "evpn" {
                 description "EVPN family";
               }
               enum "inet-mvpn" {
                 description "IPv4 Multicast VPN family";
               }
               enum "inet6-mvpn" {
                 description "IPv6 Multicast VPN family";
               }
               enum "inet-mdt" {
                 description "IPv4 MDT Signaling family";
               }
               enum "route-target" {
                 description "Local route target VPN family";
               }
               enum "traffic-engineering" {
                 description "Traffic Engineering family";
               }
             }
           }
           leaf-list protocol {
             description "Protocol from which route was learned";
             type enumeration {
               enum "aggregate" {
                 description "Aggregate routes";
               }
               enum "bgp" {
                 description "BGP";
               }
               enum "direct" {
                 description "Directly connected routes";
               }
               enum "dvmrp" {
                 description "Distance Vector Multicast Routing Protocol";
               }
               enum "isis" {
                 description "Intermediate System-to-Intermediate System";
               }
               enum "esis" {
                 description "End System-to-Intermediate System";
               }
               enum "l2circuit" {
                 description "Layer 2 circuits";
               }
               enum "l2vpn" {
                 description "Layer 2 MPLS virtual private networks";
               }
               enum "local" {
                 description "Local system addresses";
               }
               enum "ospf" {
                 description "Open Shortest Path First";
               }
               enum "ospf2" {
                 description "Open Shortest Path First Version 2";
               }
               enum "ospf3" {
                 description "Open Shortest Path First Version 3";
               }
               enum "pim" {
                 description "Protocol Independent Multicast";
               }
               enum "rip" {
                 description "Routing Information Protocol";
               }
               enum "ripng" {
                 description "Routing Information Protocol next generation";
               }
               enum "static" {
                 description "Statically defined addresses";
               }
               enum "arp" {
                 description "Addresses learned from ARP";
               }
               enum "frr" {
                 description "Addresses created by Host Fast Re-route";
               }
               enum "mpls" {
                 description "Multiprotocol Label Switching";
               }
               enum "ldp" {
                 description "Label Distribution Protocol";
               }
               enum "rsvp" {
                 description "Resource Reservation Protocol";
               }
               enum "msdp" {
                 description "Multicast Source Discovery Protocol";
               }
               enum "route-target" {
                 description "Local route target VPN membership";
               }
               enum "access" {
                 description "Access server routes";
               }
               enum "access-internal" {
                 description "Internal routes to directly connected clients";
               }
               enum "anchor" {
                 description "Anchor routes connected to UEs";
               }
               enum "bgp-static" {
                 description "BGP static routes";
               }
               enum "vpls" {
                 description "Virtual Private LAN Service";
               }
               enum "evpn" {
                 description "Ethernet VPN Service";
               }
               enum "spring-te" {
                 description "SPRING Traffic-Engineered";
               }
             }
           }
           leaf rib {
             description "Routing table";
             type string;
           }
           leaf-list neighbor {
             description "Neighboring router";
             type jt:ipaddr;
           }
           leaf-list next-hop {
             description "Next-hop router";
             type jt:ipaddr;
           }
           leaf-list interface {
             description "Interface name or address";
             type union {
               type jt:ipaddr-or-interface;
               type string {
                 pattern "<.*>|$.*";
               }
             }
           }
           leaf area {
             description "OSPF area identifier";
             type jt:areaid;
           }
           leaf-list as-path {
             description "Name of AS path regular expression (BGP only)";
             type string;
           }
           leaf-list as-path-group {
             description "Name of AS path group (BGP only)";
             type string;
           }
           leaf origin {
             description "BGP origin attribute";
             type enumeration {
               enum "igp" {
                 description "Path originated in the local IGP";
               }
               enum "egp" {
                 description "Path originated in another AS";
               }
               enum "incomplete" {
                 description "Path was learned by some other means";
               }
             }
           }
           leaf-list community {
             description "BGP community";
             type string;
           }
           leaf level {
             description "IS-IS level";
             type union {
               type uint32;
               type string {
                 pattern "<.*>|$.*";
               }
             }
           }
           container external {
             presence "enable external";
             description "External route";
             uses apply-advanced;
             leaf type {
               description "OSPF external metric type";
               type union {
                 type string {
                   pattern "<.*>|$.*";
                 }
                 type int32 {
                   range "1 .. 2";
                 }
               }
             }
           }
           leaf validation-database {
             description "Name to identify a validation-state";
             type enumeration {
               enum "valid" {
                 description "Match for valid database validation-state";
               }
               enum "invalid" {
                 description "Match for invalid database validation-state";
               }
               enum "unknown" {
                 description "Match for unknown database validation-state";
               }
             }
           }
           leaf metric {
             description "Metric value";
             type union {
               type uint32;
               type string {
                 pattern "<.*>|$.*";
               }
             }
           }
           leaf metric2 {
             description "Metric value 2";
             type union {
               type uint32;
               type string {
                 pattern "<.*>|$.*";
               }
             }
           }
           leaf metric3 {
             description "Metric value 3";
             type union {
               type uint32;
               type string {
                 pattern "<.*>|$.*";
               }
             }
           }
           leaf metric4 {
             description "Metric value 4";
             type union {
               type uint32;
               type string {
                 pattern "<.*>|$.*";
               }
             }
           }
           leaf-list tag {
             description "Tag string";
             type union {
               type uint32;
               type string {
                 pattern "<.*>|$.*";
               }
             }
           }
           leaf tag2 {
             description "Tag string 2";
             type union {
               type uint32;
               type string {
                 pattern "<.*>|$.*";
               }
             }
           }
           leaf preference {
             description "Preference value";
             type union {
               type uint32;
               type string {
                 pattern "<.*>|$.*";
               }
             }
           }
           leaf preference2 {
             description "Preference value 2";
             type union {
               type uint32;
               type string {
                 pattern "<.*>|$.*";
               }
             }
           }
           leaf color {
             description "Color (preference) value";
             type union {
               type uint32;
               type string {
                 pattern "<.*>|$.*";
               }
             }
           }
           leaf color2 {
             description "Color (preference) value 2";
             type union {
               type uint32;
               type string {
                 pattern "<.*>|$.*";
               }
             }
           }
           leaf local-preference {
             description "Local preference associated with a route";
             type union {
               type uint32;
               type string {
                 pattern "<.*>|$.*";
               }
             }
           }
           leaf-list policy {
             description "Name of policy to evaluate";
             type jt:policy-algebra;
           }
         }
         container then {
           description "Actions to take if 'from' and 'to' conditions match";
           uses apply-advanced;
           container metric {
             description "Metric value";
             uses apply-advanced;
             choice metric_action {
               case case_1 {
                 leaf metric {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
               case case_4 {
                 container igp {
                   presence "enable igp";
                   description "Track the IGP metric (BGP only)";
                   leaf metric_offset {
                     description "Metric offset for MED";
                     type union {
                       type int32;
                       type string {
                         pattern "<.*>|$.*";
                       }
                     }
                   }
                 }
               }
               case case_5 {
                 container minimum-igp {
                   presence "enable minimum-igp";
                   description "Track the minimum IGP metric (BGP only)";
                   leaf metric_offset {
                     description "Metric offset for MED";
                     type union {
                       type int32;
                       type string {
                         pattern "<.*>|$.*";
                       }
                     }
                   }
                 }
               }
               case case_6 {
                 container expression {
                   description "Calculate value based on route metric and metric2";
                   uses metric_expression_type;
                 }
               }
               case case_7 {
                 leaf aigp {
                   description "Use aigp, if it exists, to set the IGP metric";
                   type empty;
                 }
               }
             }
           }
           container metric2 {
             description "Metric value 2";
             uses apply-advanced;
             choice metric_action {
               case case_1 {
                 leaf metric2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container metric3 {
             description "Metric value 3";
             uses apply-advanced;
             choice metric_action {
               case case_1 {
                 leaf metric3 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container metric4 {
             description "Metric value 4";
             uses apply-advanced;
             choice metric_action {
               case case_1 {
                 leaf metric4 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container tag {
             description "Tag string";
             uses apply-advanced;
             choice metric_action {
               case case_1 {
                 leaf tag {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container tag2 {
             description "Tag string 2";
             uses apply-advanced;
             choice metric_action {
               case case_1 {
                 leaf tag2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container preference {
             description "Preference value";
             uses apply-advanced;
             choice metric_action {
               case case_1 {
                 leaf preference {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container preference2 {
             description "Preference value 2";
             uses apply-advanced;
             choice metric_action {
               case case_1 {
                 leaf preference2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container color {
             description "Color (preference) value";
             uses apply-advanced;
             choice metric_action {
               case case_1 {
                 leaf color {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container color2 {
             description "Color (preference) value 2";
             uses apply-advanced;
             choice metric_action {
               case case_1 {
                 leaf color2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container local-preference {
             description "Local preference associated with a route";
             uses apply-advanced;
             choice metric_action {
               case case_1 {
                 leaf local-preference {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           leaf priority {
             description "Set priority for route installation";
             type enumeration {
               enum "high" {
                 description "Set priority to high";
               }
               enum "medium" {
                 description "Set priority to medium";
               }
               enum "low" {
                 description "Set priority to low";
               }
             }
           }
           container prefix-segment {
             junos:must "(\".. .. then\")";
             junos:must-message "prefix-segment is only a then action";
             junos:must "(\". index\")";
             junos:must-message "prefix-segment index is mandatory";
             description "Set prefix segment attributes";
             leaf index {
               description "Set prefix segment index ";
               type union {
                 type string {
                   pattern "<.*>|$.*";
                 }
                 type uint32 {
                   range "0 .. 199999";
                 }
               }
             }
             leaf node-segment {
               description "Set node segment flag for this prefix segment";
               type empty;
             }
           }
           leaf label-allocation {
             description "Set label allocation mode";
             type enumeration {
               enum "per-table" {
                 description "Set per-table label allocation mode";
               }
               enum "per-nexthop" {
                 description "Set per-nexthop label allocation mode";
               }
               enum "per-table-localize" {
                 description "Set per-table-localize label allocation mode";
               }
             }
           }
           container add-path {
             junos:must "((!(\".. .. then next-hop self\") && !(\".. .. then next-hop\")))";
             junos:must-message "add-path requires unique next-hops";
             junos:must "(\".. .. then\")";
             junos:must-message "add-path is only a then action";
             description "Set BGP add-path attributes";
             leaf send-count {
               description "Number of add-paths sent";
               type union {
                 type string {
                   pattern "<.*>|$.*";
                 }
                 type uint32 {
                   range "2 .. 20";
                 }
               }
             }
           }
           leaf validation-state {
             description "Set validation-state of a route";
             type enumeration {
               enum "valid" {
                 description "Set validaton-state to valid";
               }
               enum "invalid" {
                 description "Set validation-state to invalid";
               }
               enum "unknown" {
                 description "Set validation-state to unknown";
               }
             }
           }
           leaf origin {
             description "BGP path origin";
             type enumeration {
               enum "igp" {
                 description "Path originated in the local IGP";
               }
               enum "egp" {
                 description "Path originated in another AS";
               }
               enum "incomplete" {
                 description "Path was learned by some other means";
               }
             }
           }
           container aigp-originate {
             presence "enable aigp-originate";
             junos:must "((\".. .. then next-hop self\" || \".. .. then next-hop\"))";
             junos:must-message "aigp-originate requires 'next-hop'";
             description "Originate a BGP AIGP attribute";
             leaf distance {
               description "AIGP distance";
               type union {
                 type uint32;
                 type string {
                   pattern "<.*>|$.*";
                 }
               }
             }
           }
           container aigp-adjust {
             description "Adjust a BGP AIGP attribute";
             choice math-op {
               case case_1 {
                 leaf add {
                   type empty;
                 }
               }
               case case_2 {
                 leaf subtract {
                   type empty;
                 }
               }
               case case_3 {
                 leaf multiply {
                   type empty;
                 }
               }
               case case_4 {
                 leaf divide {
                   type empty;
                 }
               }
             }
             choice adjust-value {
               case case_1 {
                 leaf user-value {
                   description "Adjustment value";
                   type union {
                     type uint64;
                     type string {
                       pattern "<.*>|$.*";
                     }
                   }
                 }
               }
               case case_2 {
                 leaf distance-to-protocol-nexthop {
                   description "Metric2";
                   type empty;
                 }
               }
             }
           }
           list community {
             key "choice-ident choice-value community-name";
             ordered-by user;
             description "BGP community properties associated with a route";
             leaf choice-ident {
               type enumeration {
                 enum "equal-literal" {
                 }
                 enum "set" {
                 }
                 enum "plus-literal" {
                 }
                 enum "add" {
                 }
                 enum "minus-literal" {
                 }
                 enum "delete" {
                 }
                 enum "community-name" {
                 }
               }
             }
             leaf choice-value {
               type string;
             }
             leaf community-name {
               description "Name to identify a BGP community";
               type string;
             }
           }
           leaf damping {
             description "Define BGP route flap damping parameters";
             type string;
           }
           leaf aggregate-bandwidth {
             description "Advertise aggregate outbound link bandwidth";
             type empty;
           }
           leaf limit-bandwidth {
             description "Limit advertised aggregate outbound link bandwidth";
             type union {
               type string {
                 pattern "<.*>|$.*";
               }
               type uint32 {
                 range "0 .. 4294967295";
               }
             }
           }
           leaf no-entropy-label-capability {
             description "Don't advertise entropy label capability";
             type empty;
           }
           leaf as-path-prepend {
             description "Prepend AS numbers to an AS path (BGP only)";
             type string;
           }
           container as-path-expand {
             description "Prepend AS numbers prior to adding local-as (BGP only)";
             choice aspath_exp_value {
               case case_1 {
                 container last-as {
                   presence "enable last-as";
                   description "Prepend last AS";
                   leaf count {
                     description "Repeat count";
                     type union {
                       type string {
                         pattern "<.*>|$.*";
                       }
                       type uint32 {
                         range "1 .. 32";
                       }
                     }
                   }
                 }
               }
               case case_2 {
                 leaf aspath {
                   description "AS path string";
                   type string;
                 }
               }
             }
           }
           container next-hop {
             description "Set the address of the next-hop router";
             choice nexthop_value {
               case case_1 {
                 leaf self {
                   description "Use a local address as the next-hop address";
                   type empty;
                 }
               }
               case case_2 {
                 leaf peer-address {
                   description "Use the remote peer address as the next-hop address";
                   type empty;
                 }
               }
               case case_3 {
                 leaf address {
                   description "Next-hop address";
                   type jt:ipaddr;
                 }
               }
               case case_4 {
                 leaf reject {
                   description "Use a reject next hop";
                   type empty;
                 }
               }
               case case_5 {
                 leaf discard {
                   description "Use a discard next hop";
                   type empty;
                 }
               }
               case case_6 {
                 leaf next-table {
                   description "Perform a forwarding lookup in the specified table";
                   type string;
                 }
               }
             }
           }
           container install-nexthop {
             description "Choose the next hop to be used for forwarding";
             leaf strict {
               description "Do not use any other available next hops";
               type empty;
             }
             choice nexthop-value {
               case case_1 {
                 leaf-list lsp {
                   description "Next-hop LSP name";
                   type string;
                 }
               }
               case case_2 {
                 leaf-list lsp-regex {
                   description "Next-hop LSP name regular expression";
                   type string;
                 }
               }
               case case_3 {
                 leaf-list static-lsp {
                   description "Next-hop static LSP name";
                   type string;
                 }
               }
               case case_4 {
                 leaf-list static-lsp-regex {
                   description "Next-hop static LSP name regular expression";
                   type string;
                 }
               }
             }
             container except {
               description "Do not choose to install matching next hops";
               uses apply-advanced;
               choice nexthop-value {
                 case case_1 {
                   leaf-list lsp {
                     description "Next-hop LSP name";
                     type string;
                   }
                 }
                 case case_2 {
                   leaf-list lsp-regex {
                     description "Next-hop LSP name regular expression";
                     type string;
                   }
                 }
                 case case_3 {
                   leaf-list static-lsp {
                     description "Next-hop static LSP name";
                     type string;
                   }
                 }
                 case case_4 {
                   leaf-list static-lsp-regex {
                     description "Next-hop static LSP name regular expression";
                     type string;
                   }
                 }
               }
             }
           }
           leaf trace {
             description "Log matches to a trace file";
             type empty;
           }
           container external {
             presence "enable external";
             junos:must "((\". type\" || \". nssa-only\"))";
             junos:must-message "type OR nssa-only configuration is mandatory";
             description "External route";
             uses apply-advanced;
             leaf type {
               description "OSPF external metric type";
               type union {
                 type string {
                   pattern "<.*>|$.*";
                 }
                 type int32 {
                   range "1 .. 2";
                 }
               }
             }
             leaf nssa-only {
               description "Clear P-bit on lsa type 7";
               type empty;
             }
           }
           container load-balance {
             description "Type of load balancing in forwarding table";
             choice load_balance_type {
               case case_1 {
                 leaf per-packet {
                   description "Load balance on a per-packet basis";
                   type empty;
                 }
               }
               case case_2 {
               }
               case case_3 {
               }
               case case_4 {
                 leaf consistent-hash {
                   description "Give a prefix consistent load-balancing";
                   type empty;
                 }
               }
               case case_5 {
               }
               case case_6 {
               }
             }
           }
           leaf analyze {
             description "Send to registered controllers for analysis";
             type empty;
           }
           leaf class {
             description "Set class-of-service parameters";
             type string;
           }
           leaf destination-class {
             description "Set destination class in forwarding table";
             type string;
           }
           leaf source-class {
             description "Set source class in forwarding table";
             type string;
           }
           leaf forwarding-class {
             description "Set source or destination class in forwarding table";
             type string;
           }
           container map-to-interface {
             description "Set output logical interface";
             choice map_to_interface_value {
               case case_1 {
                 leaf self {
                   description "Map the interface to itself";
                   type empty;
                 }
               }
               case case_2 {
                 leaf interface {
                   description "Output logical interface";
                   type union {
                     type jt:interface-name;
                     type string {
                       pattern "<.*>|$.*";
                     }
                   }
                 }
               }
             }
           }
           leaf-list ssm-source {
             description "List of Sources for SSM mapping";
             type jt:ipaddr;
           }
           container p2mp-lsp-root {
             description "P2mp lsp root address";
             uses apply-advanced;
             leaf address {
               description "Ipv4 root address";
               type jt:ipv4addr;
             }
           }
           leaf cos-next-hop-map {
             description "Set CoS-based next-hop map in forwarding table";
             type string;
           }
           leaf dynamic-tunnel-attributes {
             description "Choose the dynamic tunnel attributes used for forwarding";
             type string;
           }
           leaf selected-mldp-egress {
             description "This node should act as egress node for MLDP inband signalling";
             type empty;
           }
           leaf mhop-bfd-port {
             description "Use port number 4784 for MPLS-BFD as per RFC5884";
             type empty;
           }
           leaf default-action {
             description "Set default policy action";
             type enumeration {
               enum "accept" {
                 description "Accept a route";
               }
               enum "reject" {
                 description "Reject a route";
               }
             }
           }
           leaf next {
             description "Skip to next policy or term";
             type enumeration {
               enum "policy" {
                 description "Skip to next policy filter";
               }
               enum "term" {
                 description "Skip to next term in a policy filter";
               }
             }
           }
           choice accept_reject {
             case case_1 {
               leaf accept {
                 description "Accept a route";
                 type empty;
               }
             }
             case case_2 {
               leaf reject {
                 description "Reject a route";
                 type empty;
               }
             }
           }
           container bgp-output-queue-priority {
             description "Set the BGP Update output queue priority.";
             choice class {
               case case_1 {
                 leaf priority {
                   description "Output queue priority; higher is better";
                   type union {
                     type string {
                       pattern "<.*>|$.*";
                     }
                     type uint32 {
                       range "1 .. 16";
                     }
                   }
                 }
               }
               case case_2 {
                 leaf expedited {
                   description "Expedited queue; highest priority";
                   type empty;
                 }
               }
             }
           }
           leaf multipath-resolve {
             description "Use all paths for resolution over this prefix";
             type empty;
           }
         }
       }
       container from {
         description "Conditions to match the source of a route";
         uses apply-advanced;
         leaf instance {
           description "Routing protocol instance";
           type string;
         }
         leaf instance-any {
           description "Any routing protocol instance";
           type empty;
         }
         leaf-list instance-list {
           description "A list of routing protocol instances";
           type string;
         }
         leaf family {
           type enumeration {
             enum "inet" {
               description "IPv4 family";
             }
             enum "inet-vpn" {
               description "IPv4-VPN family";
             }
             enum "inet6" {
               description "IPv6 family";
             }
             enum "inet6-vpn" {
               description "IPv6-VPN family";
             }
             enum "iso-vpn" {
               description "ISO-VPN family";
             }
             enum "iso" {
               description "ISO family";
             }
             enum "evpn" {
               description "EVPN family";
             }
             enum "inet-mvpn" {
               description "IPv4 Multicast VPN family";
             }
             enum "inet6-mvpn" {
               description "IPv6 Multicast VPN family";
             }
             enum "inet-mdt" {
               description "IPv4 MDT Signaling family";
             }
             enum "route-target" {
               description "Local route target VPN family";
             }
             enum "traffic-engineering" {
               description "Traffic Engineering family";
             }
           }
         }
         leaf-list protocol {
           description "Protocol from which route was learned";
           type enumeration {
             enum "aggregate" {
               description "Aggregate routes";
             }
             enum "bgp" {
               description "BGP";
             }
             enum "direct" {
               description "Directly connected routes";
             }
             enum "dvmrp" {
               description "Distance Vector Multicast Routing Protocol";
             }
             enum "isis" {
               description "Intermediate System-to-Intermediate System";
             }
             enum "esis" {
               description "End System-to-Intermediate System";
             }
             enum "l2circuit" {
               description "Layer 2 circuits";
             }
             enum "l2vpn" {
               description "Layer 2 MPLS virtual private networks";
             }
             enum "local" {
               description "Local system addresses";
             }
             enum "ospf" {
               description "Open Shortest Path First";
             }
             enum "ospf2" {
               description "Open Shortest Path First Version 2";
             }
             enum "ospf3" {
               description "Open Shortest Path First Version 3";
             }
             enum "pim" {
               description "Protocol Independent Multicast";
             }
             enum "rip" {
               description "Routing Information Protocol";
             }
             enum "ripng" {
               description "Routing Information Protocol next generation";
             }
             enum "static" {
               description "Statically defined addresses";
             }
             enum "arp" {
               description "Addresses learned from ARP";
             }
             enum "frr" {
               description "Addresses created by Host Fast Re-route";
             }
             enum "mpls" {
               description "Multiprotocol Label Switching";
             }
             enum "ldp" {
               description "Label Distribution Protocol";
             }
             enum "rsvp" {
               description "Resource Reservation Protocol";
             }
             enum "msdp" {
               description "Multicast Source Discovery Protocol";
             }
             enum "route-target" {
               description "Local route target VPN membership";
             }
             enum "access" {
               description "Access server routes";
             }
             enum "access-internal" {
               description "Internal routes to directly connected clients";
             }
             enum "anchor" {
               description "Anchor routes connected to UEs";
             }
             enum "bgp-static" {
               description "BGP static routes";
             }
             enum "vpls" {
               description "Virtual Private LAN Service";
             }
             enum "evpn" {
               description "Ethernet VPN Service";
             }
             enum "spring-te" {
               description "SPRING Traffic-Engineered";
             }
           }
         }
         leaf rib {
           description "Routing table";
           type string;
         }
         leaf-list neighbor {
           description "Neighboring router";
           type jt:ipaddr;
         }
         leaf-list next-hop {
           description "Next-hop router";
           type jt:ipaddr;
         }
         leaf-list interface {
           description "Interface name or address";
           type union {
             type jt:ipaddr-or-interface;
             type string {
               pattern "<.*>|$.*";
             }
           }
         }
         leaf area {
           description "OSPF area identifier";
           type jt:areaid;
         }
         leaf-list as-path {
           description "Name of AS path regular expression (BGP only)";
           type string;
         }
         leaf-list as-path-group {
           description "Name of AS path group (BGP only)";
           type string;
         }
         leaf origin {
           description "BGP origin attribute";
           type enumeration {
             enum "igp" {
               description "Path originated in the local IGP";
             }
             enum "egp" {
               description "Path originated in another AS";
             }
             enum "incomplete" {
               description "Path was learned by some other means";
             }
           }
         }
         leaf-list community {
           description "BGP community";
           type string;
         }
         leaf level {
           description "IS-IS level";
           type union {
             type uint32;
             type string {
               pattern "<.*>|$.*";
             }
           }
         }
         container external {
           presence "enable external";
           description "External route";
           uses apply-advanced;
           leaf type {
             description "OSPF external metric type";
             type union {
               type string {
                 pattern "<.*>|$.*";
               }
               type int32 {
                 range "1 .. 2";
               }
             }
           }
         }
         leaf validation-database {
           description "Name to identify a validation-state";
           type enumeration {
             enum "valid" {
               description "Match for valid database validation-state";
             }
             enum "invalid" {
               description "Match for invalid database validation-state";
             }
             enum "unknown" {
               description "Match for unknown database validation-state";
             }
           }
         }
         leaf metric {
           description "Metric value";
           type union {
             type uint32;
             type string {
               pattern "<.*>|$.*";
             }
           }
         }
         leaf metric2 {
           description "Metric value 2";
           type union {
             type uint32;
             type string {
               pattern "<.*>|$.*";
             }
           }
         }
         leaf metric3 {
           description "Metric value 3";
           type union {
             type uint32;
             type string {
               pattern "<.*>|$.*";
             }
           }
         }
         leaf metric4 {
           description "Metric value 4";
           type union {
             type uint32;
             type string {
               pattern "<.*>|$.*";
             }
           }
         }
         leaf-list tag {
           description "Tag string";
           type union {
             type uint32;
             type string {
               pattern "<.*>|$.*";
             }
           }
         }
         leaf tag2 {
           description "Tag string 2";
           type union {
             type uint32;
             type string {
               pattern "<.*>|$.*";
             }
           }
         }
         leaf preference {
           description "Preference value";
           type union {
             type uint32;
             type string {
               pattern "<.*>|$.*";
             }
           }
         }
         leaf preference2 {
           description "Preference value 2";
           type union {
             type uint32;
             type string {
               pattern "<.*>|$.*";
             }
           }
         }
         leaf color {
           description "Color (preference) value";
           type union {
             type uint32;
             type string {
               pattern "<.*>|$.*";
             }
           }
         }
         leaf color2 {
           description "Color (preference) value 2";
           type union {
             type uint32;
             type string {
               pattern "<.*>|$.*";
             }
           }
         }
         leaf local-preference {
           description "Local preference associated with a route";
           type union {
             type uint32;
             type string {
               pattern "<.*>|$.*";
             }
           }
         }
         leaf-list policy {
           description "Name of policy to evaluate";
           type jt:policy-algebra;
         }
         list route-filter {
           key "address choice-ident choice-value";
           ordered-by user;
           description "List of routes to match";
           uses control_route_filter_type;
         }
         list source-address-filter {
           key "address choice-ident choice-value";
           ordered-by user;
           description "List of source addresses to match";
           uses control_source_address_filter_type;
         }
         list prefix-list {
           key name;
           ordered-by user;
           description "List of prefix-lists of routes to match";
           uses control_prefix_list_type;
         }
         list prefix-list-filter {
           key "list_name choice-ident choice-value";
           ordered-by user;
           description "List of prefix-list-filters to match";
           uses control_prefix_list_filter_type;
         }
         list rtf-prefix-list {
           key name;
           ordered-by user;
           description "List of rtf-prefix-lists of routes to match";
           uses control_rtf_prefix_list_type;
         }
         list route-filter-list {
           key name;
           ordered-by user;
           description "List of route-filter-lists of routes to match";
           uses control_route_filter_list_type;
         }
         list source-address-filter-list {
           key name;
           ordered-by user;
           description "List of source-address-filter-lists of routes to match";
           uses control_source_address_filter_list_type;
         }
         container multicast-scope {
           description "Multicast scope to match";
           choice scope-choice {
             case case_1 {
               leaf node-local {
                 description "Node-local scope";
                 type empty;
               }
             }
             case case_2 {
               leaf link-local {
                 description "Link-local scope";
                 type empty;
               }
             }
             case case_3 {
               leaf site-local {
                 description "Site-local scope";
                 type empty;
               }
             }
             case case_4 {
               leaf organization-local {
                 description "Organization-local scope";
                 type empty;
               }
             }
             case case_5 {
               leaf global {
                 description "Global scope";
                 type empty;
               }
             }
             case case_6 {
               leaf scope_value {
                 description "Scope value";
                 type union {
                   type string {
                     pattern "<.*>|$.*";
                   }
                   type uint32 {
                     range "0 .. 15";
                   }
                 }
               }
             }
           }
           choice scope-operator {
             case case_1 {
               leaf orhigher {
                 description "Match higher values";
                 type empty;
               }
             }
             case case_2 {
               leaf orlower {
                 description "Match lower values";
                 type empty;
               }
             }
           }
         }
         leaf aggregate-contributor {
           description "Match more specifics of an aggregate";
           type empty;
         }
         leaf state {
           description "Route state";
           type enumeration {
             enum "active" {
               description "Active route";
             }
             enum "inactive" {
               description "Inactive route";
             }
           }
         }
         leaf route-type {
           description "Route type";
           type enumeration {
             enum "internal" {
               description "Internal route";
             }
             enum "external" {
               description "External route";
             }
           }
         }
         leaf-list nlri-route-type {
           description "Route type from NLRI";
           junos:must "((\".. family evpn\" || (\".. family inet-mvpn\" || \".. family inet6-mvpn\")))";
           junos:must-message "nlri-route-type is only valid with a family qualifier such as evpn, inet-mvpn, inet6-mvpn, or other family that supports a route type";
           type union {
             type string {
               pattern "<.*>|$.*";
             }
             type uint32 {
               range "1 .. 10";
             }
           }
         }
         leaf next-hop-type {
           description "Next-hop type";
           type enumeration {
             enum "merged" {
               description "Merged next hop";
             }
           }
         }
         leaf-list condition {
           description "Condition to match on";
           type string;
         }
         list community-count {
           key name;
           ordered-by user;
           description "Number of BGP communities";
           uses community_count_type;
         }
         list as-path-unique-count {
           key name;
           ordered-by user;
           description "Number of unique BGP ASes excluding confederations";
           uses as-path-unique-count-type;
         }
         container traffic-engineering {
           presence "enable traffic-engineering";
           junos:must "(!(\".. family\"))";
           junos:must-message "traffic-engineering family implied";
           description "Traffic-Engineering related parameters";
           uses apply-advanced;
           leaf-list protocol {
             description "Protocol that originated the entry";
             type enumeration {
               enum "direct" {
                 description "Directly originated";
               }
               enum "ospf" {
                 description "OSPF originated";
               }
               enum "isis-level-1" {
                 description "ISIS level-1 originated";
               }
               enum "isis-level-2" {
                 description "ISIS level-2 originated";
               }
               enum "static" {
                 description "Statically originated";
               }
               enum "unknown" {
                 description "Originated by unknown sources";
               }
             }
           }
           container node {
             presence "enable node";
             junos:must "(!((\".. link\" || \".. ipv4-prefix\")))";
             junos:must-message "Link, prefix and node parameters cannot be configured at the same time";
             description "Node-related parameters";
             uses apply-advanced;
             leaf as {
               description "AS number";
               type string {
                 junos:posix-pattern "^[0-9]+(.[0-9]+)?$";
                 junos:pattern-message "Use format 'x' or 'x.y' to specify number 'x' (Range 1 .. 4294967295) or number with higher 2 bytes 'x' (Range 0 .. 65535) and lower 2 bytes 'y' (Range 0 .. 65535) respectively";
               }
             }
             leaf node-type {
               description "Real or pseudo-node";
               type enumeration {
                 enum "router" {
                   description "Real node";
                 }
                 enum "pseudo-node" {
                   description "Pseudo-node";
                 }
               }
             }
             leaf router-id {
               description "IP prefix to match the router-id against";
               type jt:ipprefix;
             }
             leaf sys-id {
               description "ISO address of the node";
               type jt:sysid;
             }
           }
           container ipv4-prefix {
             presence "enable ipv4-prefix";
             junos:must "(!((\".. link\" || \".. node\")))";
             junos:must-message "Link, prefix and node parameters cannot be configured at the same time";
             description "IPV4 prefix-related parameters";
             uses apply-advanced;
             leaf as {
               description "AS number";
               type string {
                 junos:posix-pattern "^[0-9]+(.[0-9]+)?$";
                 junos:pattern-message "Use format 'x' or 'x.y' to specify number 'x' (Range 1 .. 4294967295) or number with higher 2 bytes 'x' (Range 0 .. 65535) and lower 2 bytes 'y' (Range 0 .. 65535) respectively";
               }
             }
             leaf router-id {
               description "IP prefix to match the router-id against";
               type jt:ipprefix;
             }
             leaf prefix {
               description "IP prefix to match against";
               type jt:ipprefix;
             }
             leaf sys-id {
               description "ISO address of the node";
               type jt:sysid;
             }
           }
           container link {
             presence "enable link";
             junos:must "(!((\".. node\" || \".. ipv4-prefix\")))";
             junos:must-message "Link, prefix and node parameters cannot be configured at the same time";
             description "Link-related parameters";
             uses apply-advanced;
             container from {
               description "Specify parameter of the 'from' side";
               uses apply-advanced;
               leaf as {
                 description "AS number";
                 type string {
                   junos:posix-pattern "^[0-9]+(.[0-9]+)?$";
                   junos:pattern-message "Use format 'x' or 'x.y' to specify number 'x' (Range 1 .. 4294967295) or number with higher 2 bytes 'x' (Range 0 .. 65535) and lower 2 bytes 'y' (Range 0 .. 65535) respectively";
                 }
               }
               leaf router-id {
                 description "IP prefix to match the router-id against";
                 type jt:ipprefix;
               }
               leaf sys-id {
                 description "System-ID of the node";
                 type jt:sysid;
               }
               leaf node-type {
                 description "Type of the node";
                 type enumeration {
                   enum "router" {
                     description "Real node";
                   }
                   enum "pseudo-node" {
                     description "Pseudo-node";
                   }
                 }
               }
               leaf link-address {
                 description "IP prefix to match the link address against";
                 type jt:ipprefix;
               }
             }
             container to {
               description "Specify parameters of the 'to' side";
               uses apply-advanced;
               leaf as {
                 description "AS number";
                 type string {
                   junos:posix-pattern "^[0-9]+(.[0-9]+)?$";
                   junos:pattern-message "Use format 'x' or 'x.y' to specify number 'x' (Range 1 .. 4294967295) or number with higher 2 bytes 'x' (Range 0 .. 65535) and lower 2 bytes 'y' (Range 0 .. 65535) respectively";
                 }
               }
               leaf router-id {
                 description "IP prefix to match the router-id against";
                 type jt:ipprefix;
               }
               leaf sys-id {
                 description "System-ID of the node";
                 type jt:sysid;
               }
               leaf node-type {
                 description "Type of the node";
                 type enumeration {
                   enum "router" {
                     description "Real node";
                   }
                   enum "pseudo-node" {
                     description "Pseudo-node";
                   }
                 }
               }
               leaf link-address {
                 description "IP prefix to match the link address against";
                 type jt:ipprefix;
               }
             }
           }
         }
         leaf-list route-distinguisher {
           description "Name of the route-distinguisher";
           type string;
         }
       }
       container to {
         description "Conditions to match the destination of a route";
         uses apply-advanced;
         leaf instance {
           description "Routing protocol instance";
           type string;
         }
         leaf instance-any {
           description "Any routing protocol instance";
           type empty;
         }
         leaf-list instance-list {
           description "A list of routing protocol instances";
           type string;
         }
         leaf family {
           type enumeration {
             enum "inet" {
               description "IPv4 family";
             }
             enum "inet-vpn" {
               description "IPv4-VPN family";
             }
             enum "inet6" {
               description "IPv6 family";
             }
             enum "inet6-vpn" {
               description "IPv6-VPN family";
             }
             enum "iso-vpn" {
               description "ISO-VPN family";
             }
             enum "iso" {
               description "ISO family";
             }
             enum "evpn" {
               description "EVPN family";
             }
             enum "inet-mvpn" {
               description "IPv4 Multicast VPN family";
             }
             enum "inet6-mvpn" {
               description "IPv6 Multicast VPN family";
             }
             enum "inet-mdt" {
               description "IPv4 MDT Signaling family";
             }
             enum "route-target" {
               description "Local route target VPN family";
             }
             enum "traffic-engineering" {
               description "Traffic Engineering family";
             }
           }
         }
         leaf-list protocol {
           description "Protocol from which route was learned";
           type enumeration {
             enum "aggregate" {
               description "Aggregate routes";
             }
             enum "bgp" {
               description "BGP";
             }
             enum "direct" {
               description "Directly connected routes";
             }
             enum "dvmrp" {
               description "Distance Vector Multicast Routing Protocol";
             }
             enum "isis" {
               description "Intermediate System-to-Intermediate System";
             }
             enum "esis" {
               description "End System-to-Intermediate System";
             }
             enum "l2circuit" {
               description "Layer 2 circuits";
             }
             enum "l2vpn" {
               description "Layer 2 MPLS virtual private networks";
             }
             enum "local" {
               description "Local system addresses";
             }
             enum "ospf" {
               description "Open Shortest Path First";
             }
             enum "ospf2" {
               description "Open Shortest Path First Version 2";
             }
             enum "ospf3" {
               description "Open Shortest Path First Version 3";
             }
             enum "pim" {
               description "Protocol Independent Multicast";
             }
             enum "rip" {
               description "Routing Information Protocol";
             }
             enum "ripng" {
               description "Routing Information Protocol next generation";
             }
             enum "static" {
               description "Statically defined addresses";
             }
             enum "arp" {
               description "Addresses learned from ARP";
             }
             enum "frr" {
               description "Addresses created by Host Fast Re-route";
             }
             enum "mpls" {
               description "Multiprotocol Label Switching";
             }
             enum "ldp" {
               description "Label Distribution Protocol";
             }
             enum "rsvp" {
               description "Resource Reservation Protocol";
             }
             enum "msdp" {
               description "Multicast Source Discovery Protocol";
             }
             enum "route-target" {
               description "Local route target VPN membership";
             }
             enum "access" {
               description "Access server routes";
             }
             enum "access-internal" {
               description "Internal routes to directly connected clients";
             }
             enum "anchor" {
               description "Anchor routes connected to UEs";
             }
             enum "bgp-static" {
               description "BGP static routes";
             }
             enum "vpls" {
               description "Virtual Private LAN Service";
             }
             enum "evpn" {
               description "Ethernet VPN Service";
             }
             enum "spring-te" {
               description "SPRING Traffic-Engineered";
             }
           }
         }
         leaf rib {
           description "Routing table";
           type string;
         }
         leaf-list neighbor {
           description "Neighboring router";
           type jt:ipaddr;
         }
         leaf-list next-hop {
           description "Next-hop router";
           type jt:ipaddr;
         }
         leaf-list interface {
           description "Interface name or address";
           type union {
             type jt:ipaddr-or-interface;
             type string {
               pattern "<.*>|$.*";
             }
           }
         }
         leaf area {
           description "OSPF area identifier";
           type jt:areaid;
         }
         leaf-list as-path {
           description "Name of AS path regular expression (BGP only)";
           type string;
         }
         leaf-list as-path-group {
           description "Name of AS path group (BGP only)";
           type string;
         }
         leaf origin {
           description "BGP origin attribute";
           type enumeration {
             enum "igp" {
               description "Path originated in the local IGP";
             }
             enum "egp" {
               description "Path originated in another AS";
             }
             enum "incomplete" {
               description "Path was learned by some other means";
             }
           }
         }
         leaf-list community {
           description "BGP community";
           type string;
         }
         leaf level {
           description "IS-IS level";
           type union {
             type uint32;
             type string {
               pattern "<.*>|$.*";
             }
           }
         }
         container external {
           presence "enable external";
           description "External route";
           uses apply-advanced;
           leaf type {
             description "OSPF external metric type";
             type union {
               type string {
                 pattern "<.*>|$.*";
               }
               type int32 {
                 range "1 .. 2";
               }
             }
           }
         }
         leaf validation-database {
           description "Name to identify a validation-state";
           type enumeration {
             enum "valid" {
               description "Match for valid database validation-state";
             }
             enum "invalid" {
               description "Match for invalid database validation-state";
             }
             enum "unknown" {
               description "Match for unknown database validation-state";
             }
           }
         }
         leaf metric {
           description "Metric value";
           type union {
             type uint32;
             type string {
               pattern "<.*>|$.*";
             }
           }
         }
         leaf metric2 {
           description "Metric value 2";
           type union {
             type uint32;
             type string {
               pattern "<.*>|$.*";
             }
           }
         }
         leaf metric3 {
           description "Metric value 3";
           type union {
             type uint32;
             type string {
               pattern "<.*>|$.*";
             }
           }
         }
         leaf metric4 {
           description "Metric value 4";
           type union {
             type uint32;
             type string {
               pattern "<.*>|$.*";
             }
           }
         }
         leaf-list tag {
           description "Tag string";
           type union {
             type uint32;
             type string {
               pattern "<.*>|$.*";
             }
           }
         }
         leaf tag2 {
           description "Tag string 2";
           type union {
             type uint32;
             type string {
               pattern "<.*>|$.*";
             }
           }
         }
         leaf preference {
           description "Preference value";
           type union {
             type uint32;
             type string {
               pattern "<.*>|$.*";
             }
           }
         }
         leaf preference2 {
           description "Preference value 2";
           type union {
             type uint32;
             type string {
               pattern "<.*>|$.*";
             }
           }
         }
         leaf color {
           description "Color (preference) value";
           type union {
             type uint32;
             type string {
               pattern "<.*>|$.*";
             }
           }
         }
         leaf color2 {
           description "Color (preference) value 2";
           type union {
             type uint32;
             type string {
               pattern "<.*>|$.*";
             }
           }
         }
         leaf local-preference {
           description "Local preference associated with a route";
           type union {
             type uint32;
             type string {
               pattern "<.*>|$.*";
             }
           }
         }
         leaf-list policy {
           description "Name of policy to evaluate";
           type jt:policy-algebra;
         }
       }
       container then {
         description "Actions to take if 'from' and 'to' conditions match";
         uses apply-advanced;
         container metric {
           description "Metric value";
           uses apply-advanced;
           choice metric_action {
             case case_1 {
               leaf metric {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
             case case_4 {
               container igp {
                 presence "enable igp";
                 description "Track the IGP metric (BGP only)";
                 leaf metric_offset {
                   description "Metric offset for MED";
                   type union {
                     type int32;
                     type string {
                       pattern "<.*>|$.*";
                     }
                   }
                 }
               }
             }
             case case_5 {
               container minimum-igp {
                 presence "enable minimum-igp";
                 description "Track the minimum IGP metric (BGP only)";
                 leaf metric_offset {
                   description "Metric offset for MED";
                   type union {
                     type int32;
                     type string {
                       pattern "<.*>|$.*";
                     }
                   }
                 }
               }
             }
             case case_6 {
               container expression {
                 description "Calculate value based on route metric and metric2";
                 uses metric_expression_type;
               }
             }
             case case_7 {
               leaf aigp {
                 description "Use aigp, if it exists, to set the IGP metric";
                 type empty;
               }
             }
           }
         }
         container metric2 {
           description "Metric value 2";
           uses apply-advanced;
           choice metric_action {
             case case_1 {
               leaf metric2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container metric3 {
           description "Metric value 3";
           uses apply-advanced;
           choice metric_action {
             case case_1 {
               leaf metric3 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container metric4 {
           description "Metric value 4";
           uses apply-advanced;
           choice metric_action {
             case case_1 {
               leaf metric4 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container tag {
           description "Tag string";
           uses apply-advanced;
           choice metric_action {
             case case_1 {
               leaf tag {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container tag2 {
           description "Tag string 2";
           uses apply-advanced;
           choice metric_action {
             case case_1 {
               leaf tag2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container preference {
           description "Preference value";
           uses apply-advanced;
           choice metric_action {
             case case_1 {
               leaf preference {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container preference2 {
           description "Preference value 2";
           uses apply-advanced;
           choice metric_action {
             case case_1 {
               leaf preference2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container color {
           description "Color (preference) value";
           uses apply-advanced;
           choice metric_action {
             case case_1 {
               leaf color {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container color2 {
           description "Color (preference) value 2";
           uses apply-advanced;
           choice metric_action {
             case case_1 {
               leaf color2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container local-preference {
           description "Local preference associated with a route";
           uses apply-advanced;
           choice metric_action {
             case case_1 {
               leaf local-preference {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         leaf priority {
           description "Set priority for route installation";
           type enumeration {
             enum "high" {
               description "Set priority to high";
             }
             enum "medium" {
               description "Set priority to medium";
             }
             enum "low" {
               description "Set priority to low";
             }
           }
         }
         container prefix-segment {
           junos:must "(\".. .. then\")";
           junos:must-message "prefix-segment is only a then action";
           junos:must "(\". index\")";
           junos:must-message "prefix-segment index is mandatory";
           description "Set prefix segment attributes";
           leaf index {
             description "Set prefix segment index ";
             type union {
               type string {
                 pattern "<.*>|$.*";
               }
               type uint32 {
                 range "0 .. 199999";
               }
             }
           }
           leaf node-segment {
             description "Set node segment flag for this prefix segment";
             type empty;
           }
         }
         leaf label-allocation {
           description "Set label allocation mode";
           type enumeration {
             enum "per-table" {
               description "Set per-table label allocation mode";
             }
             enum "per-nexthop" {
               description "Set per-nexthop label allocation mode";
             }
             enum "per-table-localize" {
               description "Set per-table-localize label allocation mode";
             }
           }
         }
         container add-path {
           junos:must "((!(\".. .. then next-hop self\") && !(\".. .. then next-hop\")))";
           junos:must-message "add-path requires unique next-hops";
           junos:must "(\".. .. then\")";
           junos:must-message "add-path is only a then action";
           description "Set BGP add-path attributes";
           leaf send-count {
             description "Number of add-paths sent";
             type union {
               type string {
                 pattern "<.*>|$.*";
               }
               type uint32 {
                 range "2 .. 20";
               }
             }
           }
         }
         leaf validation-state {
           description "Set validation-state of a route";
           type enumeration {
             enum "valid" {
               description "Set validaton-state to valid";
             }
             enum "invalid" {
               description "Set validation-state to invalid";
             }
             enum "unknown" {
               description "Set validation-state to unknown";
             }
           }
         }
         leaf origin {
           description "BGP path origin";
           type enumeration {
             enum "igp" {
               description "Path originated in the local IGP";
             }
             enum "egp" {
               description "Path originated in another AS";
             }
             enum "incomplete" {
               description "Path was learned by some other means";
             }
           }
         }
         container aigp-originate {
           presence "enable aigp-originate";
           junos:must "((\".. .. then next-hop self\" || \".. .. then next-hop\"))";
           junos:must-message "aigp-originate requires 'next-hop'";
           description "Originate a BGP AIGP attribute";
           leaf distance {
             description "AIGP distance";
             type union {
               type uint32;
               type string {
                 pattern "<.*>|$.*";
               }
             }
           }
         }
         container aigp-adjust {
           description "Adjust a BGP AIGP attribute";
           choice math-op {
             case case_1 {
               leaf add {
                 type empty;
               }
             }
             case case_2 {
               leaf subtract {
                 type empty;
               }
             }
             case case_3 {
               leaf multiply {
                 type empty;
               }
             }
             case case_4 {
               leaf divide {
                 type empty;
               }
             }
           }
           choice adjust-value {
             case case_1 {
               leaf user-value {
                 description "Adjustment value";
                 type union {
                   type uint64;
                   type string {
                     pattern "<.*>|$.*";
                   }
                 }
               }
             }
             case case_2 {
               leaf distance-to-protocol-nexthop {
                 description "Metric2";
                 type empty;
               }
             }
           }
         }
         list community {
           key "choice-ident choice-value community-name";
           ordered-by user;
           description "BGP community properties associated with a route";
           leaf choice-ident {
             type enumeration {
               enum "equal-literal" {
               }
               enum "set" {
               }
               enum "plus-literal" {
               }
               enum "add" {
               }
               enum "minus-literal" {
               }
               enum "delete" {
               }
               enum "community-name" {
               }
             }
           }
           leaf choice-value {
             type string;
           }
           leaf community-name {
             description "Name to identify a BGP community";
             type string;
           }
         }
         leaf damping {
           description "Define BGP route flap damping parameters";
           type string;
         }
         leaf aggregate-bandwidth {
           description "Advertise aggregate outbound link bandwidth";
           type empty;
         }
         leaf limit-bandwidth {
           description "Limit advertised aggregate outbound link bandwidth";
           type union {
             type string {
               pattern "<.*>|$.*";
             }
             type uint32 {
               range "0 .. 4294967295";
             }
           }
         }
         leaf no-entropy-label-capability {
           description "Don't advertise entropy label capability";
           type empty;
         }
         leaf as-path-prepend {
           description "Prepend AS numbers to an AS path (BGP only)";
           type string;
         }
         container as-path-expand {
           description "Prepend AS numbers prior to adding local-as (BGP only)";
           choice aspath_exp_value {
             case case_1 {
               container last-as {
                 presence "enable last-as";
                 description "Prepend last AS";
                 leaf count {
                   description "Repeat count";
                   type union {
                     type string {
                       pattern "<.*>|$.*";
                     }
                     type uint32 {
                       range "1 .. 32";
                     }
                   }
                 }
               }
             }
             case case_2 {
               leaf aspath {
                 description "AS path string";
                 type string;
               }
             }
           }
         }
         container next-hop {
           description "Set the address of the next-hop router";
           choice nexthop_value {
             case case_1 {
               leaf self {
                 description "Use a local address as the next-hop address";
                 type empty;
               }
             }
             case case_2 {
               leaf peer-address {
                 description "Use the remote peer address as the next-hop address";
                 type empty;
               }
             }
             case case_3 {
               leaf address {
                 description "Next-hop address";
                 type jt:ipaddr;
               }
             }
             case case_4 {
               leaf reject {
                 description "Use a reject next hop";
                 type empty;
               }
             }
             case case_5 {
               leaf discard {
                 description "Use a discard next hop";
                 type empty;
               }
             }
             case case_6 {
               leaf next-table {
                 description "Perform a forwarding lookup in the specified table";
                 type string;
               }
             }
           }
         }
         container install-nexthop {
           description "Choose the next hop to be used for forwarding";
           leaf strict {
             description "Do not use any other available next hops";
             type empty;
           }
           choice nexthop-value {
             case case_1 {
               leaf-list lsp {
                 description "Next-hop LSP name";
                 type string;
               }
             }
             case case_2 {
               leaf-list lsp-regex {
                 description "Next-hop LSP name regular expression";
                 type string;
               }
             }
             case case_3 {
               leaf-list static-lsp {
                 description "Next-hop static LSP name";
                 type string;
               }
             }
             case case_4 {
               leaf-list static-lsp-regex {
                 description "Next-hop static LSP name regular expression";
                 type string;
               }
             }
           }
           container except {
             description "Do not choose to install matching next hops";
             uses apply-advanced;
             choice nexthop-value {
               case case_1 {
                 leaf-list lsp {
                   description "Next-hop LSP name";
                   type string;
                 }
               }
               case case_2 {
                 leaf-list lsp-regex {
                   description "Next-hop LSP name regular expression";
                   type string;
                 }
               }
               case case_3 {
                 leaf-list static-lsp {
                   description "Next-hop static LSP name";
                   type string;
                 }
               }
               case case_4 {
                 leaf-list static-lsp-regex {
                   description "Next-hop static LSP name regular expression";
                   type string;
                 }
               }
             }
           }
         }
         leaf trace {
           description "Log matches to a trace file";
           type empty;
         }
         container external {
           presence "enable external";
           junos:must "((\". type\" || \". nssa-only\"))";
           junos:must-message "type OR nssa-only configuration is mandatory";
           description "External route";
           uses apply-advanced;
           leaf type {
             description "OSPF external metric type";
             type union {
               type string {
                 pattern "<.*>|$.*";
               }
               type int32 {
                 range "1 .. 2";
               }
             }
           }
           leaf nssa-only {
             description "Clear P-bit on lsa type 7";
             type empty;
           }
         }
         container load-balance {
           description "Type of load balancing in forwarding table";
           choice load_balance_type {
             case case_1 {
               leaf per-packet {
                 description "Load balance on a per-packet basis";
                 type empty;
               }
             }
             case case_2 {
             }
             case case_3 {
             }
             case case_4 {
               leaf consistent-hash {
                 description "Give a prefix consistent load-balancing";
                 type empty;
               }
             }
             case case_5 {
             }
             case case_6 {
             }
           }
         }
         leaf analyze {
           description "Send to registered controllers for analysis";
           type empty;
         }
         leaf class {
           description "Set class-of-service parameters";
           type string;
         }
         leaf destination-class {
           description "Set destination class in forwarding table";
           type string;
         }
         leaf source-class {
           description "Set source class in forwarding table";
           type string;
         }
         leaf forwarding-class {
           description "Set source or destination class in forwarding table";
           type string;
         }
         container map-to-interface {
           description "Set output logical interface";
           choice map_to_interface_value {
             case case_1 {
               leaf self {
                 description "Map the interface to itself";
                 type empty;
               }
             }
             case case_2 {
               leaf interface {
                 description "Output logical interface";
                 type union {
                   type jt:interface-name;
                   type string {
                     pattern "<.*>|$.*";
                   }
                 }
               }
             }
           }
         }
         leaf-list ssm-source {
           description "List of Sources for SSM mapping";
           type jt:ipaddr;
         }
         container p2mp-lsp-root {
           description "P2mp lsp root address";
           uses apply-advanced;
           leaf address {
             description "Ipv4 root address";
             type jt:ipv4addr;
           }
         }
         leaf cos-next-hop-map {
           description "Set CoS-based next-hop map in forwarding table";
           type string;
         }
         leaf dynamic-tunnel-attributes {
           description "Choose the dynamic tunnel attributes used for forwarding";
           type string;
         }
         leaf selected-mldp-egress {
           description "This node should act as egress node for MLDP inband signalling";
           type empty;
         }
         leaf mhop-bfd-port {
           description "Use port number 4784 for MPLS-BFD as per RFC5884";
           type empty;
         }
         leaf default-action {
           description "Set default policy action";
           type enumeration {
             enum "accept" {
               description "Accept a route";
             }
             enum "reject" {
               description "Reject a route";
             }
           }
         }
         leaf next {
           description "Skip to next policy or term";
           type enumeration {
             enum "policy" {
               description "Skip to next policy filter";
             }
             enum "term" {
               description "Skip to next term in a policy filter";
             }
           }
         }
         choice accept_reject {
           case case_1 {
             leaf accept {
               description "Accept a route";
               type empty;
             }
           }
           case case_2 {
             leaf reject {
               description "Reject a route";
               type empty;
             }
           }
         }
         container bgp-output-queue-priority {
           description "Set the BGP Update output queue priority.";
           choice class {
             case case_1 {
               leaf priority {
                 description "Output queue priority; higher is better";
                 type union {
                   type string {
                     pattern "<.*>|$.*";
                   }
                   type uint32 {
                     range "1 .. 16";
                   }
                 }
               }
             }
             case case_2 {
               leaf expedited {
                 description "Expedited queue; highest priority";
                 type empty;
               }
             }
           }
         }
         leaf multipath-resolve {
           description "Use all paths for resolution over this prefix";
           type empty;
         }
       }
     }
     container defaults {
       description "Policy default behaviour";
       uses apply-advanced;
       container route-filter {
         description "Set route filter behaviour";
         leaf walkup {
           description "Route filter walk up enable";
           type empty;
         }
       }
     }
     list community {
       key name;
       description "BGP community information";
       leaf name {
         description "Name to identify BGP community";
         type string;
       }
       uses apply-advanced;
       leaf invert-match {
         description "Invert the result of the community expression matching";
         type empty;
       }
       leaf-list members {
         description "Community members";
         type string;
       }
     }
     list route-distinguisher {
       key name;
       description "Route-distinguisher information";
       leaf name {
         description "Name to identify route-distinguisher";
         type string;
       }
       uses apply-advanced;
       leaf-list members {
         description "Route distinguisher string in ( *:X ) or ( Y:* ) or (X:Y) format";
         type string;
       }
     }
     list as-path {
       key name;
       ordered-by user;
       description "BGP autonomous system path regular expression";
       leaf name {
         description "Name to identify AS path regular expression";
         type string;
       }
       uses apply-advanced;
       leaf path {
         description "AS path regular expression";
         type string {
           junos:posix-pattern "![;#~&<>/a-zA-Z]";
           junos:pattern-message "^$-,|*!+?{}.[]()0123456789: Only these characters are allowed";
         }
       }
     }
     list as-path-group {
       key name;
       ordered-by user;
       description "Group a set of AS paths";
       leaf name {
         description "Name to identify AS path group";
         type string;
       }
       uses apply-advanced;
       list as-path {
         key name;
         ordered-by user;
         description "BGP autonomous system path regular expression";
         leaf name {
           description "Name to identify AS path regular expression";
           type string;
         }
         leaf path {
           description "AS path regular expression";
           type string {
             junos:posix-pattern "![;#~&<>/a-zA-Z]";
             junos:pattern-message "^$-,|*!+?{}.[]()0123456789: Only these characters are allowed";
           }
         }
       }
     }
     list damping {
       key name;
       ordered-by user;
       description "BGP route flap damping properties";
       leaf name {
         description "Name to identify route flap damping parameters";
         type string;
       }
       uses apply-advanced;
       choice enable-disable {
         case case_1 {
           leaf disable {
             description "Disable damping";
             type empty;
           }
         }
       }
       leaf half-life {
         description "Decay half-life";
         units "minutes";
         type union {
           type string {
             pattern "<.*>|$.*";
           }
           type uint32 {
             range "1 .. 45";
           }
         }
       }
       leaf reuse {
         description "Reuse threshold (figure-of-merit value)";
         type union {
           type string {
             pattern "<.*>|$.*";
           }
           type uint32 {
             range "1 .. 20000";
           }
         }
       }
       leaf suppress {
         description "Cutoff threshold (figure-of-merit value)";
         type union {
           type string {
             pattern "<.*>|$.*";
           }
           type uint32 {
             range "1 .. 20000";
           }
         }
       }
       leaf max-suppress {
         description "Maximum hold-down time";
         units "minutes";
         type union {
           type string {
             pattern "<.*>|$.*";
           }
           type uint32 {
             range "1 .. 720";
           }
         }
       }
     }
     list condition {
       key name;
       description "Define a route advertisement condition";
       leaf name {
         description "Name to identify Condition";
         type string;
       }
       uses apply-advanced;
       choice condition_type {
         case case_1 {
           leaf route-active-on {
             description "Route is active on a specific node";
             type enumeration {
               enum "node0" {
                 description "Route active on node 0";
               }
               enum "node1" {
                 description "Route active on node 1";
               }
             }
           }
         }
         case case_2 {
           container if-route-exists {
             presence "enable if-route-exists";
             description "Route exists in a specific routing table";
             uses apply-advanced;
             container address-family {
               presence "enable address-family";
               description "Indicates the address family of the route to match on";
               uses apply-advanced;
               choice address-family {
                 case case_1 {
                   container inet {
                     presence "enable inet";
                     description "Route to match corresponds to an inet/inet6 prefix";
                     uses apply-advanced;
                     leaf address {
                       description "Exact address of the route";
                       junos:must "(!(\".. .. .. address\"))";
                       junos:must-message "A unique address field is allowed per condition";
                       junos:must "(!((\".. .. ccc\" || \".. .. mpls\")))";
                       junos:must-message "Only one address-family type can be configured per condition";
                       type jt:ipprefix;
                     }
                     leaf table {
                       description "Routing table in which route should exist";
                       type string;
                     }
                   }
                 }
                 case case_2 {
                   container ccc {
                     presence "enable ccc";
                     description "Route to match corresponds to a ccc prefix";
                     uses apply-advanced;
                     leaf address {
                       description "Logical interface used to establish ccc route";
                       junos:must "(!(\".. .. .. address\"))";
                       junos:must-message "A unique address field is allowed per condition";
                       junos:must "(!((\".. .. inet\" || \".. .. mpls\")))";
                       junos:must-message "Only one address-family type can be configured per condition";
                       type union {
                         type jt:interface-name;
                         type string {
                           pattern "<.*>|$.*";
                         }
                       }
                     }
                     leaf table {
                       description "Routing table in which route should exist";
                       type string;
                     }
                     leaf standby {
                       description "Indicates if route must be in standby state to be considered a match";
                       type empty;
                     }
                     leaf peer-unit {
                       description "Associated LT ifl's peer-unit. Required for LT-based routes";
                       type union {
                         type string {
                           pattern "<.*>|$.*";
                         }
                         type uint32 {
                           range "0 .. 8192";
                         }
                       }
                     }
                   }
                 }
               }
             }
             leaf address {
               description "Exact address of the route";
               junos:must "(!(\".. address-family\"))";
               junos:must-message "Explicit address-family previously configured. Only one address-family type can be configured per condition";
               type jt:ipprefix;
             }
             leaf table {
               description "Routing table in which route should exist";
               junos:must "(!(\".. address-family\"))";
               junos:must-message "Explicit address-family previously configured. No route-table is allowed at this level";
               type string;
             }
           }
         }
       }
     }
     list rtf-prefix-list {
       key name;
       ordered-by user;
       description "Define a named set of family route target prefixes";
       leaf name {
         description "RTF prefix list name";
         type string;
       }
       uses apply-advanced;
       list prefix-list {
         key name;
         uses rtf_prefix_list_items;
       }
     }
     list application-maps {
       key name;
       ordered-by user;
       description "Define application maps";
       uses application_map_object;
     }
     list redundancy-policy {
       key name;
       leaf name {
         description "Redundancy policy name";
         type string {
           length "1 .. 63";
         }
       }
       uses apply-advanced;
       leaf-list redundancy-events {
         description "Events related services redundancy under event-options";
         type string;
       }
       container then {
         description "Action to take when of the event occurs";
         junos:must "(\".. redundancy-events\")";
         junos:must-message "Redundancy policy needs to have a redundancy-events-then condition";
         uses srd-ev-action-object;
         junos:must "(\".. redundancy-events\")";
         junos:must-message "Redundancy policy needs to have a redundancy-events-then condition";
       }
     }
   }
   grouping application_map_object {
     leaf name {
       description "Name of application map";
       type string {
         length "1 .. 63";
         junos:posix-pattern "^[[:alnum:]][[:alnum:]_-]*$";
         junos:pattern-message "Must be a string beginning with a number or letter and consisting of letters, numbers, dashes and underscores.";
       }
     }
     uses apply-advanced;
     list application {
       key name;
       ordered-by user;
       description "Name of the application";
       leaf name {
         description "Name of the application";
         junos:must "(\"applications application $$\")";
         junos:must-message "The referenced application is not defined";
         type string {
           length "1 .. 63";
         }
       }
       leaf-list code-points {
         description "List of code point bit strings";
         type string;
       }
     }
   }
   grouping apply-advanced {
     description "Apply advanced configuration logic";
     leaf-list apply-groups {
       description "Groups from which to inherit configuration data";
       type string;
     }
     leaf-list apply-groups-except {
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping as-path-unique-count-type {
     description "Number of unique BGP ASes excluding confederation ASes";
     leaf name {
       description "Number of ASes";
       type union {
         type string {
           pattern "<.*>|$.*";
         }
         type uint32 {
           range "0 .. 1024";
         }
       }
     }
     choice count-operator {
       case case_1 {
         leaf equal {
           description "Match equal values";
           type empty;
         }
       }
       case case_2 {
         leaf orhigher {
           description "Match higher or equal	values";
           type empty;
         }
       }
       case case_3 {
         leaf orlower {
           description "Match lower or equal values";
           type empty;
         }
       }
     }
   }
   grouping community_count_type {
     description "Number of BGP communities";
     leaf name {
       description "Number of communities";
       type union {
         type string {
           pattern "<.*>|$.*";
         }
         type uint32 {
           range "0 .. 1024";
         }
       }
     }
     choice count-operator {
       case case_1 {
         leaf equal {
           description "Match equal values";
           type empty;
         }
       }
       case case_2 {
         leaf orhigher {
           description "Match higher or equal	values";
           type empty;
         }
       }
       case case_3 {
         leaf orlower {
           description "Match lower or equal values";
           type empty;
         }
       }
     }
   }
   grouping control_prefix_list_filter_type {
     leaf list_name {
       description "Name of prefix-list of routes to match";
       type string;
     }
     leaf choice-ident {
       type enumeration {
         enum "exact" {
         }
         enum "longer" {
         }
         enum "orlonger" {
         }
         enum "apply-advanced" {
         }
         enum "metric" {
         }
         enum "metric2" {
         }
         enum "metric3" {
         }
         enum "metric4" {
         }
         enum "tag" {
         }
         enum "tag2" {
         }
         enum "preference" {
         }
         enum "preference2" {
         }
         enum "color" {
         }
         enum "color2" {
         }
         enum "local-preference" {
         }
         enum "priority" {
         }
         enum "prefix-segment" {
         }
         enum "label-allocation" {
         }
         enum "add-path" {
         }
         enum "validation-state" {
         }
         enum "origin" {
         }
         enum "aigp-originate" {
         }
         enum "aigp-adjust" {
         }
         enum "community" {
         }
         enum "damping" {
         }
         enum "aggregate-bandwidth" {
         }
         enum "limit-bandwidth" {
         }
         enum "no-entropy-label-capability" {
         }
         enum "as-path-prepend" {
         }
         enum "as-path-expand" {
         }
         enum "next-hop" {
         }
         enum "install-nexthop" {
         }
         enum "trace" {
         }
         enum "external" {
         }
         enum "load-balance" {
         }
         enum "no-route-localize" {
         }
         enum "install-to-fib" {
         }
         enum "analyze" {
         }
         enum "class" {
         }
         enum "destination-class" {
         }
         enum "source-class" {
         }
         enum "forwarding-class" {
         }
         enum "map-to-interface" {
         }
         enum "ssm-source" {
         }
         enum "p2mp-lsp-root" {
         }
         enum "cos-next-hop-map" {
         }
         enum "dynamic-tunnel-attributes" {
         }
         enum "selected-mldp-egress" {
         }
         enum "mhop-bfd-port" {
         }
         enum "default-action" {
         }
         enum "next" {
         }
         enum "accept_reject" {
         }
         enum "bgp-output-queue-priority" {
         }
         enum "multipath-resolve" {
         }
       }
     }
     leaf choice-value {
       type string;
     }
     uses apply-advanced;
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       junos:must "(\".. .. then\")";
       junos:must-message "prefix-segment is only a then action";
       junos:must "(\". index\")";
       junos:must-message "prefix-segment index is mandatory";
       description "Set prefix segment attributes";
       leaf index {
         description "Set prefix segment index ";
         type union {
           type string {
             pattern "<.*>|$.*";
           }
           type uint32 {
             range "0 .. 199999";
           }
         }
       }
       leaf node-segment {
         description "Set node segment flag for this prefix segment";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       junos:must "((!(\".. .. then next-hop self\") && !(\".. .. then next-hop\")))";
       junos:must-message "add-path requires unique next-hops";
       junos:must "(\".. .. then\")";
       junos:must-message "add-path is only a then action";
       description "Set BGP add-path attributes";
       leaf send-count {
         description "Number of add-paths sent";
         type union {
           type string {
             pattern "<.*>|$.*";
           }
           type uint32 {
             range "2 .. 20";
           }
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container aigp-originate {
       presence "enable aigp-originate";
       junos:must "((\".. .. then next-hop self\" || \".. .. then next-hop\"))";
       junos:must-message "aigp-originate requires 'next-hop'";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
           enum "community-name" {
           }
         }
       }
       leaf choice-value {
         type string;
       }
       leaf community-name {
         description "Name to identify a BGP community";
         type string;
       }
     }
     leaf damping {
       description "Define BGP route flap damping parameters";
       type string;
     }
     leaf aggregate-bandwidth {
       description "Advertise aggregate outbound link bandwidth";
       type empty;
     }
     leaf limit-bandwidth {
       description "Limit advertised aggregate outbound link bandwidth";
       type union {
         type string {
           pattern "<.*>|$.*";
         }
         type uint32 {
           range "0 .. 4294967295";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       leaf strict {
         description "Do not use any other available next hops";
         type empty;
       }
       choice nexthop-value {
         case case_1 {
           leaf-list lsp {
             description "Next-hop LSP name";
             type string;
           }
         }
         case case_2 {
           leaf-list lsp-regex {
             description "Next-hop LSP name regular expression";
             type string;
           }
         }
         case case_3 {
           leaf-list static-lsp {
             description "Next-hop static LSP name";
             type string;
           }
         }
         case case_4 {
           leaf-list static-lsp-regex {
             description "Next-hop static LSP name regular expression";
             type string;
           }
         }
       }
       container except {
         description "Do not choose to install matching next hops";
         uses apply-advanced;
         choice nexthop-value {
           case case_1 {
             leaf-list lsp {
               description "Next-hop LSP name";
               type string;
             }
           }
           case case_2 {
             leaf-list lsp-regex {
               description "Next-hop LSP name regular expression";
               type string;
             }
           }
           case case_3 {
             leaf-list static-lsp {
               description "Next-hop static LSP name";
               type string;
             }
           }
           case case_4 {
             leaf-list static-lsp-regex {
               description "Next-hop static LSP name regular expression";
               type string;
             }
           }
         }
       }
     }
     leaf trace {
       description "Log matches to a trace file";
       type empty;
     }
     container external {
       presence "enable external";
       junos:must "((\". type\" || \". nssa-only\"))";
       junos:must-message "type OR nssa-only configuration is mandatory";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis";
             type empty;
           }
         }
         case case_2 {
         }
         case case_3 {
         }
         case case_4 {
           leaf consistent-hash {
             description "Give a prefix consistent load-balancing";
             type empty;
           }
         }
         case case_5 {
         }
         case case_6 {
         }
       }
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf selected-mldp-egress {
       description "This node should act as egress node for MLDP inband signalling";
       type empty;
     }
     leaf mhop-bfd-port {
       description "Use port number 4784 for MPLS-BFD as per RFC5884";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
   }
   grouping control_prefix_list_type {
     leaf name {
       description "Name of prefix-list of routes to match";
       type string;
     }
     uses apply-advanced;
   }
   grouping control_route_filter_list_type {
     leaf name {
       description "Name of route-filter-list of routes to match";
       type string;
     }
     uses apply-advanced;
   }
   grouping control_route_filter_type {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "address-mask" {
         }
         enum "apply-advanced" {
         }
         enum "metric" {
         }
         enum "metric2" {
         }
         enum "metric3" {
         }
         enum "metric4" {
         }
         enum "tag" {
         }
         enum "tag2" {
         }
         enum "preference" {
         }
         enum "preference2" {
         }
         enum "color" {
         }
         enum "color2" {
         }
         enum "local-preference" {
         }
         enum "priority" {
         }
         enum "prefix-segment" {
         }
         enum "label-allocation" {
         }
         enum "add-path" {
         }
         enum "validation-state" {
         }
         enum "origin" {
         }
         enum "aigp-originate" {
         }
         enum "aigp-adjust" {
         }
         enum "community" {
         }
         enum "damping" {
         }
         enum "aggregate-bandwidth" {
         }
         enum "limit-bandwidth" {
         }
         enum "no-entropy-label-capability" {
         }
         enum "as-path-prepend" {
         }
         enum "as-path-expand" {
         }
         enum "next-hop" {
         }
         enum "install-nexthop" {
         }
         enum "trace" {
         }
         enum "external" {
         }
         enum "load-balance" {
         }
         enum "no-route-localize" {
         }
         enum "install-to-fib" {
         }
         enum "analyze" {
         }
         enum "class" {
         }
         enum "destination-class" {
         }
         enum "source-class" {
         }
         enum "forwarding-class" {
         }
         enum "map-to-interface" {
         }
         enum "ssm-source" {
         }
         enum "p2mp-lsp-root" {
         }
         enum "cos-next-hop-map" {
         }
         enum "dynamic-tunnel-attributes" {
         }
         enum "selected-mldp-egress" {
         }
         enum "mhop-bfd-port" {
         }
         enum "default-action" {
         }
         enum "next" {
         }
         enum "accept_reject" {
         }
         enum "bgp-output-queue-priority" {
         }
         enum "multipath-resolve" {
         }
       }
     }
     leaf choice-value {
       type string;
     }
     uses apply-advanced;
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       junos:must "(\".. .. then\")";
       junos:must-message "prefix-segment is only a then action";
       junos:must "(\". index\")";
       junos:must-message "prefix-segment index is mandatory";
       description "Set prefix segment attributes";
       leaf index {
         description "Set prefix segment index ";
         type union {
           type string {
             pattern "<.*>|$.*";
           }
           type uint32 {
             range "0 .. 199999";
           }
         }
       }
       leaf node-segment {
         description "Set node segment flag for this prefix segment";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       junos:must "((!(\".. .. then next-hop self\") && !(\".. .. then next-hop\")))";
       junos:must-message "add-path requires unique next-hops";
       junos:must "(\".. .. then\")";
       junos:must-message "add-path is only a then action";
       description "Set BGP add-path attributes";
       leaf send-count {
         description "Number of add-paths sent";
         type union {
           type string {
             pattern "<.*>|$.*";
           }
           type uint32 {
             range "2 .. 20";
           }
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container aigp-originate {
       presence "enable aigp-originate";
       junos:must "((\".. .. then next-hop self\" || \".. .. then next-hop\"))";
       junos:must-message "aigp-originate requires 'next-hop'";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
           enum "community-name" {
           }
         }
       }
       leaf choice-value {
         type string;
       }
       leaf community-name {
         description "Name to identify a BGP community";
         type string;
       }
     }
     leaf damping {
       description "Define BGP route flap damping parameters";
       type string;
     }
     leaf aggregate-bandwidth {
       description "Advertise aggregate outbound link bandwidth";
       type empty;
     }
     leaf limit-bandwidth {
       description "Limit advertised aggregate outbound link bandwidth";
       type union {
         type string {
           pattern "<.*>|$.*";
         }
         type uint32 {
           range "0 .. 4294967295";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       leaf strict {
         description "Do not use any other available next hops";
         type empty;
       }
       choice nexthop-value {
         case case_1 {
           leaf-list lsp {
             description "Next-hop LSP name";
             type string;
           }
         }
         case case_2 {
           leaf-list lsp-regex {
             description "Next-hop LSP name regular expression";
             type string;
           }
         }
         case case_3 {
           leaf-list static-lsp {
             description "Next-hop static LSP name";
             type string;
           }
         }
         case case_4 {
           leaf-list static-lsp-regex {
             description "Next-hop static LSP name regular expression";
             type string;
           }
         }
       }
       container except {
         description "Do not choose to install matching next hops";
         uses apply-advanced;
         choice nexthop-value {
           case case_1 {
             leaf-list lsp {
               description "Next-hop LSP name";
               type string;
             }
           }
           case case_2 {
             leaf-list lsp-regex {
               description "Next-hop LSP name regular expression";
               type string;
             }
           }
           case case_3 {
             leaf-list static-lsp {
               description "Next-hop static LSP name";
               type string;
             }
           }
           case case_4 {
             leaf-list static-lsp-regex {
               description "Next-hop static LSP name regular expression";
               type string;
             }
           }
         }
       }
     }
     leaf trace {
       description "Log matches to a trace file";
       type empty;
     }
     container external {
       presence "enable external";
       junos:must "((\". type\" || \". nssa-only\"))";
       junos:must-message "type OR nssa-only configuration is mandatory";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis";
             type empty;
           }
         }
         case case_2 {
         }
         case case_3 {
         }
         case case_4 {
           leaf consistent-hash {
             description "Give a prefix consistent load-balancing";
             type empty;
           }
         }
         case case_5 {
         }
         case case_6 {
         }
       }
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf selected-mldp-egress {
       description "This node should act as egress node for MLDP inband signalling";
       type empty;
     }
     leaf mhop-bfd-port {
       description "Use port number 4784 for MPLS-BFD as per RFC5884";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
   }
   grouping control_rtf_prefix_list_type {
     description "RTF prefix list";
     leaf name {
       description "Name of rtf-prefix-list of routes to match";
       type string;
     }
     uses apply-advanced;
   }
   grouping control_source_address_filter_list_type {
     leaf name {
       description "Name of source-address-filter-list of routes to match";
       type string;
     }
     uses apply-advanced;
   }
   grouping control_source_address_filter_type {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "apply-advanced" {
         }
         enum "metric" {
         }
         enum "metric2" {
         }
         enum "metric3" {
         }
         enum "metric4" {
         }
         enum "tag" {
         }
         enum "tag2" {
         }
         enum "preference" {
         }
         enum "preference2" {
         }
         enum "color" {
         }
         enum "color2" {
         }
         enum "local-preference" {
         }
         enum "priority" {
         }
         enum "prefix-segment" {
         }
         enum "label-allocation" {
         }
         enum "add-path" {
         }
         enum "validation-state" {
         }
         enum "origin" {
         }
         enum "aigp-originate" {
         }
         enum "aigp-adjust" {
         }
         enum "community" {
         }
         enum "damping" {
         }
         enum "aggregate-bandwidth" {
         }
         enum "limit-bandwidth" {
         }
         enum "no-entropy-label-capability" {
         }
         enum "as-path-prepend" {
         }
         enum "as-path-expand" {
         }
         enum "next-hop" {
         }
         enum "install-nexthop" {
         }
         enum "trace" {
         }
         enum "external" {
         }
         enum "load-balance" {
         }
         enum "no-route-localize" {
         }
         enum "install-to-fib" {
         }
         enum "analyze" {
         }
         enum "class" {
         }
         enum "destination-class" {
         }
         enum "source-class" {
         }
         enum "forwarding-class" {
         }
         enum "map-to-interface" {
         }
         enum "ssm-source" {
         }
         enum "p2mp-lsp-root" {
         }
         enum "cos-next-hop-map" {
         }
         enum "dynamic-tunnel-attributes" {
         }
         enum "selected-mldp-egress" {
         }
         enum "mhop-bfd-port" {
         }
         enum "default-action" {
         }
         enum "next" {
         }
         enum "accept_reject" {
         }
         enum "bgp-output-queue-priority" {
         }
         enum "multipath-resolve" {
         }
       }
     }
     leaf choice-value {
       type string;
     }
     uses apply-advanced;
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       junos:must "(\".. .. then\")";
       junos:must-message "prefix-segment is only a then action";
       junos:must "(\". index\")";
       junos:must-message "prefix-segment index is mandatory";
       description "Set prefix segment attributes";
       leaf index {
         description "Set prefix segment index ";
         type union {
           type string {
             pattern "<.*>|$.*";
           }
           type uint32 {
             range "0 .. 199999";
           }
         }
       }
       leaf node-segment {
         description "Set node segment flag for this prefix segment";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       junos:must "((!(\".. .. then next-hop self\") && !(\".. .. then next-hop\")))";
       junos:must-message "add-path requires unique next-hops";
       junos:must "(\".. .. then\")";
       junos:must-message "add-path is only a then action";
       description "Set BGP add-path attributes";
       leaf send-count {
         description "Number of add-paths sent";
         type union {
           type string {
             pattern "<.*>|$.*";
           }
           type uint32 {
             range "2 .. 20";
           }
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container aigp-originate {
       presence "enable aigp-originate";
       junos:must "((\".. .. then next-hop self\" || \".. .. then next-hop\"))";
       junos:must-message "aigp-originate requires 'next-hop'";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
           enum "community-name" {
           }
         }
       }
       leaf choice-value {
         type string;
       }
       leaf community-name {
         description "Name to identify a BGP community";
         type string;
       }
     }
     leaf damping {
       description "Define BGP route flap damping parameters";
       type string;
     }
     leaf aggregate-bandwidth {
       description "Advertise aggregate outbound link bandwidth";
       type empty;
     }
     leaf limit-bandwidth {
       description "Limit advertised aggregate outbound link bandwidth";
       type union {
         type string {
           pattern "<.*>|$.*";
         }
         type uint32 {
           range "0 .. 4294967295";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       leaf strict {
         description "Do not use any other available next hops";
         type empty;
       }
       choice nexthop-value {
         case case_1 {
           leaf-list lsp {
             description "Next-hop LSP name";
             type string;
           }
         }
         case case_2 {
           leaf-list lsp-regex {
             description "Next-hop LSP name regular expression";
             type string;
           }
         }
         case case_3 {
           leaf-list static-lsp {
             description "Next-hop static LSP name";
             type string;
           }
         }
         case case_4 {
           leaf-list static-lsp-regex {
             description "Next-hop static LSP name regular expression";
             type string;
           }
         }
       }
       container except {
         description "Do not choose to install matching next hops";
         uses apply-advanced;
         choice nexthop-value {
           case case_1 {
             leaf-list lsp {
               description "Next-hop LSP name";
               type string;
             }
           }
           case case_2 {
             leaf-list lsp-regex {
               description "Next-hop LSP name regular expression";
               type string;
             }
           }
           case case_3 {
             leaf-list static-lsp {
               description "Next-hop static LSP name";
               type string;
             }
           }
           case case_4 {
             leaf-list static-lsp-regex {
               description "Next-hop static LSP name regular expression";
               type string;
             }
           }
         }
       }
     }
     leaf trace {
       description "Log matches to a trace file";
       type empty;
     }
     container external {
       presence "enable external";
       junos:must "((\". type\" || \". nssa-only\"))";
       junos:must-message "type OR nssa-only configuration is mandatory";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis";
             type empty;
           }
         }
         case case_2 {
         }
         case case_3 {
         }
         case case_4 {
           leaf consistent-hash {
             description "Give a prefix consistent load-balancing";
             type empty;
           }
         }
         case case_5 {
         }
         case case_6 {
         }
       }
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf selected-mldp-egress {
       description "This node should act as egress node for MLDP inband signalling";
       type empty;
     }
     leaf mhop-bfd-port {
       description "Use port number 4784 for MPLS-BFD as per RFC5884";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
   }
   grouping mac_addr_list_items {
     leaf name {
       description "Mac Address";
       type jt:mac-addr;
     }
     uses apply-advanced;
   }
   grouping macro-data-type {
     leaf name {
       description "Keyword part of the keyword-value pair";
       type string;
     }
     leaf value {
       description "Value part of the keyword-value pair";
       type string;
     }
   }
   grouping metric_expression_type {
     uses apply-advanced;
     container metric {
       description "Parameters for metric attribute";
       leaf multiplier {
         description "Coefficient for metric attribute";
         type decimal64 {
           fraction-digits 2;
         }
       }
       leaf offset {
         description "Offset for metric attribute";
         type union {
           type int32;
           type string {
             pattern "<.*>|$.*";
           }
         }
       }
     }
     container metric2 {
       description "Parameters for metric2 attribute";
       leaf multiplier {
         description "Coefficient for metric2 attribute";
         default "1.0";
         type decimal64 {
           fraction-digits 2;
         }
       }
       leaf offset {
         description "Offset for metric2 attribute";
         type union {
           type int32;
           type string {
             pattern "<.*>|$.*";
           }
         }
       }
     }
   }
   grouping prefix_list_items {
     leaf name {
       description "Address prefix";
       type jt:ipprefix-only;
     }
     uses apply-advanced;
   }
   grouping route_filter_list_items {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "address-mask" {
         }
         enum "apply-advanced" {
         }
         enum "metric" {
         }
         enum "metric2" {
         }
         enum "metric3" {
         }
         enum "metric4" {
         }
         enum "tag" {
         }
         enum "tag2" {
         }
         enum "preference" {
         }
         enum "preference2" {
         }
         enum "color" {
         }
         enum "color2" {
         }
         enum "local-preference" {
         }
         enum "priority" {
         }
         enum "prefix-segment" {
         }
         enum "label-allocation" {
         }
         enum "add-path" {
         }
         enum "validation-state" {
         }
         enum "origin" {
         }
         enum "aigp-originate" {
         }
         enum "aigp-adjust" {
         }
         enum "community" {
         }
         enum "damping" {
         }
         enum "aggregate-bandwidth" {
         }
         enum "limit-bandwidth" {
         }
         enum "no-entropy-label-capability" {
         }
         enum "as-path-prepend" {
         }
         enum "as-path-expand" {
         }
         enum "next-hop" {
         }
         enum "install-nexthop" {
         }
         enum "trace" {
         }
         enum "external" {
         }
         enum "load-balance" {
         }
         enum "no-route-localize" {
         }
         enum "install-to-fib" {
         }
         enum "analyze" {
         }
         enum "class" {
         }
         enum "destination-class" {
         }
         enum "source-class" {
         }
         enum "forwarding-class" {
         }
         enum "map-to-interface" {
         }
         enum "ssm-source" {
         }
         enum "p2mp-lsp-root" {
         }
         enum "cos-next-hop-map" {
         }
         enum "dynamic-tunnel-attributes" {
         }
         enum "selected-mldp-egress" {
         }
         enum "mhop-bfd-port" {
         }
         enum "default-action" {
         }
         enum "next" {
         }
         enum "accept_reject" {
         }
         enum "bgp-output-queue-priority" {
         }
         enum "multipath-resolve" {
         }
       }
     }
     leaf choice-value {
       type string;
     }
     uses apply-advanced;
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       junos:must "(\".. .. then\")";
       junos:must-message "prefix-segment is only a then action";
       junos:must "(\". index\")";
       junos:must-message "prefix-segment index is mandatory";
       description "Set prefix segment attributes";
       leaf index {
         description "Set prefix segment index ";
         type union {
           type string {
             pattern "<.*>|$.*";
           }
           type uint32 {
             range "0 .. 199999";
           }
         }
       }
       leaf node-segment {
         description "Set node segment flag for this prefix segment";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       junos:must "((!(\".. .. then next-hop self\") && !(\".. .. then next-hop\")))";
       junos:must-message "add-path requires unique next-hops";
       junos:must "(\".. .. then\")";
       junos:must-message "add-path is only a then action";
       description "Set BGP add-path attributes";
       leaf send-count {
         description "Number of add-paths sent";
         type union {
           type string {
             pattern "<.*>|$.*";
           }
           type uint32 {
             range "2 .. 20";
           }
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container aigp-originate {
       presence "enable aigp-originate";
       junos:must "((\".. .. then next-hop self\" || \".. .. then next-hop\"))";
       junos:must-message "aigp-originate requires 'next-hop'";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
           enum "community-name" {
           }
         }
       }
       leaf choice-value {
         type string;
       }
       leaf community-name {
         description "Name to identify a BGP community";
         type string;
       }
     }
     leaf damping {
       description "Define BGP route flap damping parameters";
       type string;
     }
     leaf aggregate-bandwidth {
       description "Advertise aggregate outbound link bandwidth";
       type empty;
     }
     leaf limit-bandwidth {
       description "Limit advertised aggregate outbound link bandwidth";
       type union {
         type string {
           pattern "<.*>|$.*";
         }
         type uint32 {
           range "0 .. 4294967295";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       leaf strict {
         description "Do not use any other available next hops";
         type empty;
       }
       choice nexthop-value {
         case case_1 {
           leaf-list lsp {
             description "Next-hop LSP name";
             type string;
           }
         }
         case case_2 {
           leaf-list lsp-regex {
             description "Next-hop LSP name regular expression";
             type string;
           }
         }
         case case_3 {
           leaf-list static-lsp {
             description "Next-hop static LSP name";
             type string;
           }
         }
         case case_4 {
           leaf-list static-lsp-regex {
             description "Next-hop static LSP name regular expression";
             type string;
           }
         }
       }
       container except {
         description "Do not choose to install matching next hops";
         uses apply-advanced;
         choice nexthop-value {
           case case_1 {
             leaf-list lsp {
               description "Next-hop LSP name";
               type string;
             }
           }
           case case_2 {
             leaf-list lsp-regex {
               description "Next-hop LSP name regular expression";
               type string;
             }
           }
           case case_3 {
             leaf-list static-lsp {
               description "Next-hop static LSP name";
               type string;
             }
           }
           case case_4 {
             leaf-list static-lsp-regex {
               description "Next-hop static LSP name regular expression";
               type string;
             }
           }
         }
       }
     }
     leaf trace {
       description "Log matches to a trace file";
       type empty;
     }
     container external {
       presence "enable external";
       junos:must "((\". type\" || \". nssa-only\"))";
       junos:must-message "type OR nssa-only configuration is mandatory";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis";
             type empty;
           }
         }
         case case_2 {
         }
         case case_3 {
         }
         case case_4 {
           leaf consistent-hash {
             description "Give a prefix consistent load-balancing";
             type empty;
           }
         }
         case case_5 {
         }
         case case_6 {
         }
       }
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf selected-mldp-egress {
       description "This node should act as egress node for MLDP inband signalling";
       type empty;
     }
     leaf mhop-bfd-port {
       description "Use port number 4784 for MPLS-BFD as per RFC5884";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
   }
   grouping rtf_prefix_list_items {
     leaf name {
       description "Family route-target prefix";
       type string {
         length "1 .. 63";
         junos:posix-pattern "^[0-9]{1,15}:[0-9.]{1,15}L?:[0-9]{1,10}/(0|3[2-9]|[4-8][0-9]|9[0-6])$";
         junos:pattern-message "Use format 'as:x:y/len' where 'as' is an AS number and 'x' is an AS number followed by an optional 'L' (To indicate 4 byte AS), or an IP address and 'y' is a number. e.g. 123456L:100 and len is a prefix length from 32 to 96 or 0";
       }
     }
     uses apply-advanced;
   }
   grouping satellite-policy-options {
     uses apply-advanced;
     list extended-ports-template {
       key name;
       ordered-by user;
       description "Extended ports template";
       leaf name {
         type string {
           length "1 .. 32";
         }
       }
       uses apply-advanced;
       list pic {
         key name;
         description "PIC attributes";
         uses satellite-pic-type;
       }
     }
     list port-group-alias {
       key name;
       ordered-by user;
       description "Port group alias";
       leaf name {
         type string {
           length "1 .. 32";
         }
       }
       uses apply-advanced;
       list pic {
         key name;
         ordered-by user;
         description "Satellite PIC information";
         leaf name {
           description "PIC identifier";
           type union {
             type int32;
             type string {
               pattern "<.*>|$.*";
             }
           }
         }
         uses apply-advanced;
         leaf-list port {
           description "Port id or range or all";
           type union {
             type string {
               pattern "<.*>|$.*";
             }
             type uint32 {
               range "0 .. 1024";
             }
           }
         }
       }
     }
     list extended-ports-policy {
       key name;
       ordered-by user;
       description "Define a extended-ports-policy";
       leaf name {
         description "Policy name";
         type string {
           length "1 .. 32";
         }
       }
       uses apply-advanced;
       list term {
         key name;
         ordered-by user;
         description "Policy term";
         leaf name {
           type string {
             length "1 .. 32";
           }
         }
         uses apply-advanced;
         container from {
           description "Condition to match the satellite";
           uses apply-advanced;
           leaf-list product-model {
             description "Product Model Name";
             type string {
               length "1 .. 64";
             }
           }
           leaf extended-ports-template {
             description "Apply extended ports template to satellite matching conditions defined in this term";
             junos:must "(\"policy-options satellite-policies extended-ports-template $$\")";
             junos:must-message "Extended ports template not defined";
             type string;
           }
         }
       }
     }
     list candidate-uplink-port-policy {
       key name;
       ordered-by user;
       description "Define a candidate uplink-port policy";
       leaf name {
         description "Policy name";
         type string {
           length "1 .. 32";
         }
       }
       uses apply-advanced;
       leaf uplink-port-group {
         description "Uplink port group alias name";
         junos:must "(\"policy-options satellite-policies port-group-alias $$\")";
         junos:must-message "port-group-alias not defined";
         type string;
       }
       leaf minimum-links {
         description "Minimum child links to keep extended-ports UP";
         type union {
           type string {
             pattern "<.*>|$.*";
           }
           type uint16 {
             range "1 .. 32";
           }
         }
       }
       leaf holddown {
         description "Time to hold down after uplink failure";
         units "seconds";
         type union {
           type string {
             pattern "<.*>|$.*";
           }
           type uint32 {
             range "1 .. 600";
           }
         }
       }
       list term {
         key name;
         ordered-by user;
         description "Policy term";
         leaf name {
           type string {
             length "1 .. 32";
           }
         }
         uses apply-advanced;
         container from {
           description "Condition to match the satellite";
           uses apply-advanced;
           leaf-list product-model {
             description "Product Model Name";
             type string {
               length "1 .. 64";
             }
           }
           leaf uplink-port-group {
             description "Uplink port group alias name";
             junos:must "(\"policy-options satellite-policies port-group-alias $$\")";
             junos:must-message "port-group-alias not defined";
             type string;
           }
           leaf minimum-links {
             description "Minimum child links to keep extended-ports UP";
             type union {
               type string {
                 pattern "<.*>|$.*";
               }
               type uint16 {
                 range "1 .. 32";
               }
             }
           }
           leaf holddown {
             description "Time to hold down after uplink failure";
             units "seconds";
             type union {
               type string {
                 pattern "<.*>|$.*";
               }
               type uint32 {
                 range "1 .. 600";
               }
             }
           }
         }
       }
     }
     list environment-monitoring-policy {
       key name;
       ordered-by user;
       description "Define a environment monitoring policy";
       leaf name {
         description "Policy name";
         type string {
           length "1 .. 32";
         }
       }
       uses apply-advanced;
       container alarm {
         presence "enable alarm";
         description "Policy default alarm policy";
         uses apply-advanced;
         leaf linkdown {
           description "Policy default linkdown alarm";
           type enumeration {
             enum "ignore" {
               description "Ignore ethernet linkdown";
             }
             enum "red" {
               description "Raise major alarm for ethernet linkdown";
             }
             enum "yellow" {
               description "Raise minor alarm for ethernet linkdown";
             }
           }
         }
       }
       list term {
         key name;
         ordered-by user;
         description "Policy term";
         leaf name {
           type string {
             length "1 .. 32";
           }
         }
         uses apply-advanced;
         container from {
           description "Condition to match the satellite";
           uses apply-advanced;
           leaf-list product-model {
             description "Product Model Name";
             type string {
               length "1 .. 64";
             }
           }
           container alarm {
             presence "enable alarm";
             description "Term alarm policy";
             uses apply-advanced;
             leaf linkdown {
               description "Set linkdown alarm";
               type enumeration {
                 enum "ignore" {
                   description "Ignore ethernet linkdown";
                 }
                 enum "red" {
                   description "Raise major alarm for ethernet linkdown";
                 }
                 enum "yellow" {
                   description "Raise minor alarm for ethernet linkdown";
                 }
               }
             }
           }
         }
       }
     }
     list forwarding-policy {
       key name;
       ordered-by user;
       description "Define forwarding policy for extended ports";
       leaf name {
         description "Policy name";
         type string {
           length "1 .. 32";
         }
       }
       uses apply-advanced;
       list port-group-extended {
         key name;
         ordered-by user;
         description "Define a extend port group mapping";
         uses port-extend-type;
       }
       list term {
         key name;
         ordered-by user;
         description "Policy term";
         leaf name {
           type string {
             length "1 .. 32";
           }
         }
         uses apply-advanced;
         container from {
           description "Condition to match the satellite";
           uses apply-advanced;
           leaf-list product-model {
             description "Product Model Name";
             type string {
               length "1 .. 64";
             }
           }
           list port-group-extended {
             key name;
             ordered-by user;
             description "Define a extend port group mapping";
             uses port-extend-type;
           }
         }
       }
     }
   }
   grouping port-extend-type {
     leaf name {
       description "Extended port group alias name policy applied on";
       type string;
     }
     uses apply-advanced;
     leaf filter {
       description "Assign a filter for uplink selection";
       junos:must "((\"chassis satellite-management firewall family bridge filter $$\" || \"chassis satellite-management firewall family ethernet-switching filter $$\"))";
       junos:must-message "Filter should be defined under 'chassis satellite-management firewall family bridge filter'";
       type string;
     }
     container port-group-uplink {
       description "Define a uplink port group mapping";
       uses apply-advanced;
       leaf port-group-uplink-alias {
         description "Uplink port group alias name used for uplink pinning mode";
         junos:must "(\"policy-options satellite-policies port-group-alias $$\")";
         junos:must-message "port-group-alias not defined";
         type string;
       }
       leaf minimum-links {
         description "Minimum child links to keep extended-ports UP";
         type union {
           type string {
             pattern "<.*>|$.*";
           }
           type uint16 {
             range "1 .. 32";
           }
         }
       }
       leaf holddown {
         description "Time to hold down after uplink failure";
         units "seconds";
         type union {
           type string {
             pattern "<.*>|$.*";
           }
           type uint32 {
             range "1 .. 600";
           }
         }
       }
     }
     container mirror-ingress {
       description "Define a ingress port mirror";
       uses apply-advanced;
       leaf port-group-mirror {
         description "Mirror port group alias name for local port mirroring";
         junos:must "(\"policy-options satellite-policies port-group-alias $$\")";
         junos:must-message "port-group-alias not defined";
         type string;
       }
     }
     container mirror-egress {
       description "Define a egress port mirror";
       uses apply-advanced;
       leaf port-group-mirror {
         description "Mirror port group alias name for local port mirroring";
         junos:must "(\"policy-options satellite-policies port-group-alias $$\")";
         junos:must-message "port-group-alias not defined";
         type string;
       }
     }
   }
   grouping satellite-pic-type {
     leaf name {
       description "PIC slot number";
       type union {
         type string {
           pattern "<.*>|$.*";
         }
         type uint32 {
           range "0 .. 4";
         }
       }
     }
     uses apply-advanced;
     list port {
       key name;
       description "Port number";
       uses satellite-pic-port-attr;
     }
     list port-range {
       key "port-range-low port-range-high";
       ordered-by user;
       description "Physical ports to channelize";
       leaf port-range-low {
         description "Port range low number";
         type union {
           type string {
             pattern "<.*>|$.*";
           }
           type uint32 {
             range "0 .. 127";
           }
         }
       }
       leaf port-range-high {
         description "Port range high number";
         type union {
           type string {
             pattern "<.*>|$.*";
           }
           type uint32 {
             range "0 .. 127";
           }
         }
       }
       uses apply-advanced;
       leaf channel-speed {
         description "Port channel speed";
         type enumeration {
           enum "10g" {
             description "Set the port speed to 10G";
           }
           enum "disable-auto-speed-detection" {
             description "Disables automatic speed detection";
           }
         }
       }
     }
   }
   grouping satellite-pic-port-attr {
     leaf name {
       description "Port number";
       type union {
         type string {
           pattern "<.*>|$.*";
         }
         type uint32 {
           range "0 .. 127";
         }
       }
     }
     uses apply-advanced;
     leaf channel-speed {
       description "Port channel speed";
       type enumeration {
         enum "10g" {
           description "Set the port speed to 10G";
         }
         enum "25g" {
           description "Set the port speed to 25G";
         }
         enum "50g" {
           description "Set the port speed to 50G";
         }
         enum "disable-auto-speed-detection" {
           description "Disables automatic speed detection";
         }
       }
     }
   }
   grouping source_address_filter_list_items {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "apply-advanced" {
         }
         enum "metric" {
         }
         enum "metric2" {
         }
         enum "metric3" {
         }
         enum "metric4" {
         }
         enum "tag" {
         }
         enum "tag2" {
         }
         enum "preference" {
         }
         enum "preference2" {
         }
         enum "color" {
         }
         enum "color2" {
         }
         enum "local-preference" {
         }
         enum "priority" {
         }
         enum "prefix-segment" {
         }
         enum "label-allocation" {
         }
         enum "add-path" {
         }
         enum "validation-state" {
         }
         enum "origin" {
         }
         enum "aigp-originate" {
         }
         enum "aigp-adjust" {
         }
         enum "community" {
         }
         enum "damping" {
         }
         enum "aggregate-bandwidth" {
         }
         enum "limit-bandwidth" {
         }
         enum "no-entropy-label-capability" {
         }
         enum "as-path-prepend" {
         }
         enum "as-path-expand" {
         }
         enum "next-hop" {
         }
         enum "install-nexthop" {
         }
         enum "trace" {
         }
         enum "external" {
         }
         enum "load-balance" {
         }
         enum "no-route-localize" {
         }
         enum "install-to-fib" {
         }
         enum "analyze" {
         }
         enum "class" {
         }
         enum "destination-class" {
         }
         enum "source-class" {
         }
         enum "forwarding-class" {
         }
         enum "map-to-interface" {
         }
         enum "ssm-source" {
         }
         enum "p2mp-lsp-root" {
         }
         enum "cos-next-hop-map" {
         }
         enum "dynamic-tunnel-attributes" {
         }
         enum "selected-mldp-egress" {
         }
         enum "mhop-bfd-port" {
         }
         enum "default-action" {
         }
         enum "next" {
         }
         enum "accept_reject" {
         }
         enum "bgp-output-queue-priority" {
         }
         enum "multipath-resolve" {
         }
       }
     }
     leaf choice-value {
       type string;
     }
     uses apply-advanced;
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       junos:must "(\".. .. then\")";
       junos:must-message "prefix-segment is only a then action";
       junos:must "(\". index\")";
       junos:must-message "prefix-segment index is mandatory";
       description "Set prefix segment attributes";
       leaf index {
         description "Set prefix segment index ";
         type union {
           type string {
             pattern "<.*>|$.*";
           }
           type uint32 {
             range "0 .. 199999";
           }
         }
       }
       leaf node-segment {
         description "Set node segment flag for this prefix segment";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       junos:must "((!(\".. .. then next-hop self\") && !(\".. .. then next-hop\")))";
       junos:must-message "add-path requires unique next-hops";
       junos:must "(\".. .. then\")";
       junos:must-message "add-path is only a then action";
       description "Set BGP add-path attributes";
       leaf send-count {
         description "Number of add-paths sent";
         type union {
           type string {
             pattern "<.*>|$.*";
           }
           type uint32 {
             range "2 .. 20";
           }
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container aigp-originate {
       presence "enable aigp-originate";
       junos:must "((\".. .. then next-hop self\" || \".. .. then next-hop\"))";
       junos:must-message "aigp-originate requires 'next-hop'";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
           enum "community-name" {
           }
         }
       }
       leaf choice-value {
         type string;
       }
       leaf community-name {
         description "Name to identify a BGP community";
         type string;
       }
     }
     leaf damping {
       description "Define BGP route flap damping parameters";
       type string;
     }
     leaf aggregate-bandwidth {
       description "Advertise aggregate outbound link bandwidth";
       type empty;
     }
     leaf limit-bandwidth {
       description "Limit advertised aggregate outbound link bandwidth";
       type union {
         type string {
           pattern "<.*>|$.*";
         }
         type uint32 {
           range "0 .. 4294967295";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       leaf strict {
         description "Do not use any other available next hops";
         type empty;
       }
       choice nexthop-value {
         case case_1 {
           leaf-list lsp {
             description "Next-hop LSP name";
             type string;
           }
         }
         case case_2 {
           leaf-list lsp-regex {
             description "Next-hop LSP name regular expression";
             type string;
           }
         }
         case case_3 {
           leaf-list static-lsp {
             description "Next-hop static LSP name";
             type string;
           }
         }
         case case_4 {
           leaf-list static-lsp-regex {
             description "Next-hop static LSP name regular expression";
             type string;
           }
         }
       }
       container except {
         description "Do not choose to install matching next hops";
         uses apply-advanced;
         choice nexthop-value {
           case case_1 {
             leaf-list lsp {
               description "Next-hop LSP name";
               type string;
             }
           }
           case case_2 {
             leaf-list lsp-regex {
               description "Next-hop LSP name regular expression";
               type string;
             }
           }
           case case_3 {
             leaf-list static-lsp {
               description "Next-hop static LSP name";
               type string;
             }
           }
           case case_4 {
             leaf-list static-lsp-regex {
               description "Next-hop static LSP name regular expression";
               type string;
             }
           }
         }
       }
     }
     leaf trace {
       description "Log matches to a trace file";
       type empty;
     }
     container external {
       presence "enable external";
       junos:must "((\". type\" || \". nssa-only\"))";
       junos:must-message "type OR nssa-only configuration is mandatory";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis";
             type empty;
           }
         }
         case case_2 {
         }
         case case_3 {
         }
         case case_4 {
           leaf consistent-hash {
             description "Give a prefix consistent load-balancing";
             type empty;
           }
         }
         case case_5 {
         }
         case case_6 {
         }
       }
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf selected-mldp-egress {
       description "This node should act as egress node for MLDP inband signalling";
       type empty;
     }
     leaf mhop-bfd-port {
       description "Use port number 4784 for MPLS-BFD as per RFC5884";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
   }
   grouping srd-ev-action-object {
     junos:must "((\"add-static-route\" || \"delete-static-route\"))";
     junos:must-message "Add or delete of static route needed";
     description "Action to be taken on the occurence if defined events";
     uses apply-advanced;
     leaf mship-actions {
       description "Mastership related actions";
       type enumeration {
         enum "acquire-mastership" {
           description "Attempt to acquire mastership";
         }
         enum "release-mastership" {
           description "Attempt to release mastership";
         }
         enum "release-mastership-force" {
           description "Attempt to release mastership";
         }
         enum "release-mastership-if-standby-clear" {
           description "Attempt to release mastership if standby has no warning";
         }
         enum "broadcast-warning" {
           description "Attempt to release mastership";
         }
       }
     }
     list add-static-route {
       key name;
       ordered-by user;
       description "Add a static route in the specified routing table";
       max-elements 1;
       uses srd-route-add-object;
     }
     list delete-static-route {
       key name;
       ordered-by user;
       description "Delete a static route in the specified routing table";
       max-elements 1;
       uses srd-route-delete-object;
     }
   }
   grouping srd-route-add-object {
     description "Route details";
     leaf name {
       description " Destination route address with prefix length";
       type jt:ipv4prefix-mandatory;
     }
     uses apply-advanced;
     choice next-hop-details {
       case case_1 {
         leaf next-hop {
           description "Next-hop (interface) to destination";
           type string;
         }
       }
       case case_2 {
         leaf receive {
           description "Install a receive route for the destination";
           type empty;
         }
       }
     }
     leaf routing-instance {
       description "Routing instance where the route should be added";
       type string;
     }
   }
   grouping srd-route-delete-object {
     description "Route details";
     leaf name {
       description "Destination route address with prefix length";
       type jt:ipv4prefix-mandatory;
     }
     uses apply-advanced;
     leaf routing-instance {
       description "Routing instance where the route should be added";
       type string;
     }
   }
 }
