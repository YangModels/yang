/*
 * Copyright (c) 2017 Juniper Networks, Inc.
 * All rights reserved.
 */
 module junos-es-conf-schedulers {
   namespace "http://yang.juniper.net/junos-es/conf/schedulers";

   prefix jc-schedulers;

   import junos-common-ddl-extensions {
     prefix junos;
   }

   import junos-common-types {
     prefix jt;
   }

   import junos-es-conf-root {
     prefix jc;
   }

   organization "Juniper Networks, Inc.";

   contact "yang-support@juniper.net";

   description "Junos schedulers configuration module";

   revision 2017-01-01 {
     description "Junos: 17.4R1.16";
   }

   augment /jc:configuration {
     uses schedulers-group;
   }
   augment /jc:configuration/jc:groups {
     uses schedulers-group;
   }
   grouping schedulers-group {
     container schedulers {
       description "Security scheduler";
       uses apply-advanced;
       list scheduler {
         key name;
         ordered-by user;
         description "Scheduler configuration";
         uses scheduler_object_type;
       }
     }
   }
   grouping apply-advanced {
     description "Apply advanced configuration logic";
     leaf-list apply-groups {
       description "Groups from which to inherit configuration data";
       type string;
     }
     leaf-list apply-groups-except {
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping macro-data-type {
     leaf name {
       description "Keyword part of the keyword-value pair";
       type string;
     }
     leaf value {
       description "Value part of the keyword-value pair";
       type string;
     }
   }
   grouping scheduler_object_type {
     leaf name {
       description "Name of security scheduler";
       type string {
         length "1 .. 63";
         junos:posix-pattern "^[[:alnum:]][[:alnum:]_-]*$";
         junos:pattern-message "Must be a string beginning with a number or letter and consisting of letters, numbers, dashes and underscores.";
       }
     }
     uses apply-advanced;
     leaf description {
       description "Text description of scheduler";
       type string {
         length "1 .. 900";
         junos:posix-pattern "^[^&<>\n]+$";
         junos:pattern-message "Must be a string excluding '&', '<', '>' and '\n'";
       }
     }
     list start-date {
       key "start-date stop-date";
       ordered-by user;
       description "Start date and time ([YYYY-]MM-DD.hh:mm)";
       max-elements 2;
       leaf start-date {
         description "Start date and time ([YYYY-]MM-DD.hh:mm)";
         type string {
           junos:posix-pattern "^((2[0-9][0-9][0-9][-])?(0[1-9]|1[012])[-](0[1-9]|[12][0-9]|3[01])[.][0-9]{2,2}[:][0-9]{2,2})$";
           junos:pattern-message "Invalid date format [YYYY-]MM-DD.hh:mm";
         }
       }
       leaf stop-date {
         description "Stop date and time ([YYYY-]MM-DD.hh:mm)";
         type string {
           junos:posix-pattern "^((2[0-9][0-9][0-9][-])?(0[1-9]|1[012])[-](0[1-9]|[12][0-9]|3[01])[.][0-9]{2,2}[:][0-9]{2,2})$";
           junos:pattern-message "Invalid date format [YYYY-]MM-DD.hh:mm";
         }
       }
       uses apply-advanced;
     }
     container daily {
       description "Everyday; can be overwritten by specific weekday";
       uses daily-object;
     }
     container sunday {
       description "Every Sunday";
       uses daily-object;
     }
     container monday {
       description "Every Monday";
       uses daily-object;
     }
     container tuesday {
       description "Every Tuesday";
       uses daily-object;
     }
     container wednesday {
       description "Every Wednesday";
       uses daily-object;
     }
     container thursday {
       description "Every Thursday";
       uses daily-object;
     }
     container friday {
       description "Every Friday";
       uses daily-object;
     }
     container saturday {
       description "Every Saturday";
       uses daily-object;
     }
   }
   grouping daily-object {
     description "Daily schedule";
     uses apply-advanced;
     choice daily_type {
       case case_1 {
         list start-time {
           key "start-time-value stop-time";
           description "Time range for day";
           max-elements 2;
           leaf start-time-value {
             description "Start time for day (hh:mm)";
             type string {
               junos:posix-pattern "^((0[0-9]|1[0-9]|2[0-3])([:][0-5][0-9])?([:][0-5][0-9])?)$";
               junos:pattern-message "Must be a valid time in hh:mm format";
             }
           }
           leaf stop-time {
             description "Stop time for day (hh:mm)";
             type string {
               junos:posix-pattern "^((0[0-9]|1[0-9]|2[0-3])([:][0-5][0-9])?([:][0-5][0-9])?)$";
               junos:pattern-message "Must be a valid time in hh:mm format";
             }
           }
           uses apply-advanced;
         }
       }
       case case_2 {
         leaf exclude {
           description "Exclude day from week";
           type empty;
         }
       }
       case case_3 {
         leaf all-day {
           description "Include complete day";
           type empty;
         }
       }
     }
   }
 }
