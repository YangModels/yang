module arcos-openconfig-aft-augments {
  yang-version 1.1;
  namespace "http://yang.arrcus.com/arcos/openconfig/aft/augments";
  prefix arc-oc-aft-aug;

  import openconfig-network-instance {
    prefix oc-ni;
  }

  import arcos-openconfig-network-instance-augments {
    prefix arc-oc-netinst-aug;
  }

  import openconfig-yang-types {
    prefix oc-yang;
  }

  import arcos-aft-types {
    prefix arc-aft-types;
  }

  import arcos-aft {
    prefix arc-aft;
  }

  organization
    "Arrcus, Inc.";

    contact
        "Email: eng@arrcus.com";

  description
    "This module defines augmentation for Arrcus
     implemention of the openconfig aft module.";

  revision 2018-08-14 {
     description "ArcOS release 2.2.1";

     reference
	"RFC 6020: YANG - A Data Modeling Language for the
       	 Network Configuration Protocol (NETCONF)";
  }

  augment "/oc-ni:network-instances/oc-ni:network-instance" +
    "/oc-ni:afts/oc-ni:ipv4-unicast/oc-ni:ipv4-entry/oc-ni:next-hops/oc-ni:next-hop" +
    "/oc-ni:state" {
    leaf nexthop-type {
      type arc-aft-types:dpal-nexthop-type;
      description
	"nexthop type";
    }
    leaf nexthop-tunnel-id {
      type leafref {
        path "/oc-ni:network-instances/oc-ni:network-instance/" +
             "arc-oc-netinst-aug:ip-tunnels/arc-oc-netinst-aug:tunnels/" +
             "arc-oc-netinst-aug:tunnel-id";
      }
      description
	"ID of tunnel that nexthop recurses over";
    }
  }

  augment "/oc-ni:network-instances/oc-ni:network-instance" +
    "/oc-ni:afts-units/oc-ni:aft-unit-entry/oc-ni:afts" +
    "/oc-ni:ipv4-unicast/oc-ni:ipv4-entry/oc-ni:next-hops/oc-ni:next-hop" +
    "/oc-ni:state" {
    leaf nexthop-type {
      type arc-aft-types:dpal-nexthop-type;
      description
	"nexthop type";
    }
    leaf nexthop-tunnel-id {
      type leafref {
        path "/oc-ni:network-instances/oc-ni:network-instance/" +
             "arc-oc-netinst-aug:ip-tunnels/arc-oc-netinst-aug:tunnels/" +
             "arc-oc-netinst-aug:tunnel-id";
      }
      description
	"ID of tunnel that nexthop recurses over";
    }
  }


  augment "/oc-ni:network-instances/oc-ni:network-instance" +
    "/oc-ni:afts/oc-ni:ipv6-unicast/oc-ni:ipv6-entry/oc-ni:next-hops/oc-ni:next-hop" +
    "/oc-ni:state" {
    leaf nexthop-type {
      type arc-aft-types:dpal-nexthop-type;
      description
	"nexthop type";
    }
    leaf nexthop-tunnel-id {
      type leafref {
        path "/oc-ni:network-instances/oc-ni:network-instance/" +
             "arc-oc-netinst-aug:ip-tunnels/arc-oc-netinst-aug:tunnels/" +
             "arc-oc-netinst-aug:tunnel-id";
      }
      description
	"ID of tunnel that nexthop recurses over";
    }
  }

  augment "/oc-ni:network-instances/oc-ni:network-instance" +
    "/oc-ni:afts-units/oc-ni:aft-unit-entry/oc-ni:afts" +
    "/oc-ni:ipv6-unicast/oc-ni:ipv6-entry/oc-ni:next-hops/oc-ni:next-hop" +
    "/oc-ni:state" {
    leaf nexthop-type {
      type arc-aft-types:dpal-nexthop-type;
      description
	"nexthop type";
    }
    leaf nexthop-tunnel-id {
      type leafref {
        path "/oc-ni:network-instances/oc-ni:network-instance/" +
             "arc-oc-netinst-aug:ip-tunnels/arc-oc-netinst-aug:tunnels/" +
             "arc-oc-netinst-aug:tunnel-id";
      }
      description
	"ID of tunnel that nexthop recurses over";
    }
  }

  augment "/oc-ni:network-instances/oc-ni:network-instance" +
    "/oc-ni:afts/oc-ni:mpls/oc-ni:label-entry/oc-ni:next-hops/oc-ni:next-hop" +
    "/oc-ni:state" {
    leaf nexthop-type {
      type arc-aft-types:dpal-nexthop-type;
      description
	"nexthop type";
    }
  }

  augment "/oc-ni:network-instances/oc-ni:network-instance" +
    "/oc-ni:afts-units/oc-ni:aft-unit-entry/oc-ni:afts" +
    "/oc-ni:mpls/oc-ni:label-entry/oc-ni:next-hops/oc-ni:next-hop" +
    "/oc-ni:state" {
    leaf nexthop-type {
      type arc-aft-types:dpal-nexthop-type;
      description
	"nexthop type";
    }
  }

  augment "/oc-ni:network-instances/oc-ni:network-instance" +
          "/oc-ni:afts" {
    uses arc-aft:aft-srv6-sids;
  }
}
