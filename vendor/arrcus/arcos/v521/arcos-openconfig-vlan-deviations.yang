module arcos-openconfig-vlan-deviations {
  yang-version 1.1;
  namespace "http://yang.arrcus.com/arcos/openconfig/vlan/deviations";
  prefix arc-oc-vlan-dev;

  import openconfig-vlan {
    prefix oc-vlan;
  }

  import arcos-platform {
    prefix arc-platform;
  }
  import openconfig-interfaces {prefix oc-if; }
  import openconfig-vlan-types { prefix oc-vlan-types; }
  import arcos-openconfig-vlan-types { prefix arc-oc-vlan-types;}

  organization
    "Arrcus, Inc.";
  contact
    "Arrcus, Inc.
     2077 Gateway Place
     Suite 400
     San Jose, CA 95110
     E-mail: yang-support@arrcus.com";
  description
    "This module defines deviations statements for the
     for OpenConfig vlan module.
     Copyright (c) 2016-2023 by Arrcus, Inc.
     All rights reserved.";

  revision 2023-03-13 {
    description
      "extend vlan-stack-action with double tag actions";
  }
  
  deviation "/oc-vlan:vlans/oc-vlan:vlan/oc-vlan:config" +
            "/oc-vlan:status" {
    deviate not-supported;
    description "Not supported in this release";
  }

  deviation "/oc-if:interfaces/oc-if:interface/oc-if:subinterfaces/oc-if:subinterface/" +
            "oc-vlan:vlan/oc-vlan:ingress-mapping/oc-vlan:config/oc-vlan:vlan-stack-action" {
    deviate replace {
        type arc-oc-vlan-types:vlan-stack-action-extend;
    }
  }
  deviation "/oc-if:interfaces/oc-if:interface/oc-if:subinterfaces/oc-if:subinterface/" +
            "oc-vlan:vlan/oc-vlan:egress-mapping/oc-vlan:config/oc-vlan:vlan-stack-action" {
    deviate replace {
      type union {
        type oc-vlan-types:vlan-stack-action;
        type arc-oc-vlan-types:vlan-stack-action-extend;
      }
    }
  }

  deviation "/oc-if:interfaces/oc-if:interface/oc-if:subinterfaces/oc-if:subinterface/" +
            "oc-vlan:vlan/oc-vlan:ingress-mapping/oc-vlan:state/oc-vlan:vlan-stack-action" {
    deviate replace {
      type union {
        type oc-vlan-types:vlan-stack-action;
        type arc-oc-vlan-types:vlan-stack-action-extend;
      }
    }
  }
  deviation "/oc-if:interfaces/oc-if:interface/oc-if:subinterfaces/oc-if:subinterface/" +
            "oc-vlan:vlan/oc-vlan:egress-mapping/oc-vlan:state/oc-vlan:vlan-stack-action" {
    deviate replace {
      type union {
        type oc-vlan-types:vlan-stack-action;
        type arc-oc-vlan-types:vlan-stack-action-extend;
      }
    }
  }
}
