module arcos-openconfig-network-instance-types {
  yang-version 1.1;
  namespace "http://yang.arrcus.com/arcos/openconfig/network-instance/types";
  prefix arc-oc-ni-types;

  import openconfig-network-instance-types {
    prefix oc-ni-types;
  }

  organization
    "Arrcus, Inc.";

  contact
    "Arrcus, Inc.
     2077 Gateway Place
     Suite 400
     San Jose, CA 95110

     E-mail: yang-support@arrcus.com";

  description
    "This module defines additional types/identities
     that base off of OpenConfig network-instance types.

     Copyright (c) 2020 by Arrcus, Inc.
     All rights reserved.";

  identity L2P2P_EVPN {
    base oc-ni-types:NETWORK_INSTANCE_TYPE;
    description
      "A private Layer 2 only forwarding instance which acts as
      a point to point connection between two endpoints. Endpoint
      discovery is accomplished using EVPN BGP";
  }

  identity L2VLAN_AWARE_BUNDLE {
    base oc-ni-types:NETWORK_INSTANCE_TYPE;
    description
      "An EVPN Network Instance for VLAN-Aware Bundle service.
      This service allows multiple VLANs to be extended using a single EVPN
      Instance (EVI), while maintaining separate bridge tables.";
  }
}
