module arcos-rov-types {
  yang-version 1.1;
  namespace "http://yang.arrcus.com/arcos/rov/types";

  prefix arc-rov-types;

  organization
    "Arrcus, Inc.";

  contact
    "Arrcus, Inc.
     Customer Service
     Postal: 2077 Gateway Place
     San Jose, CA 95110
     Tel: +1 1XXX XXX-XXXX
     E-mail: xxx@arrcus.com";

  description
    "This module defines Arrcus implemention of the ROV types module.";

  revision 2021-10-25 {
    description
      "Initial Revision
       * Add ROV state
      ";

    reference
      "RFC 6020: YANG - A Data Modeling Language for the
       Network Configuration Protocol (NETCONF)";
  }

  identity ROV_STATE {
    description
      "Base identity for ROV state";
  }

  identity UNKNOWN {
    base ROV_STATE;
    description
      "ROV unknown state; Either record not found or server not available";
  }

  identity INVALID {
    base ROV_STATE;
    description
      "ROV invalid state";
  }

  identity VALID {
    base ROV_STATE;
    description
      "ROV valid state";
  }
}
