module arcos-acl-clear {
  yang-version 1.1;
  namespace "http://yang.arrcus.com/arcos/acl/clear";
  prefix arc-acl-clr;

  import openconfig-acl {
    prefix oc-acl;
  }

  container acl-counters {
    description
      "Clear ACL statistics";

    action all {
      description
        "Clear stats counters for all ACL sets and entries";

      output {
        leaf result {
          type string;
          description
            "The status of the clear operation";
        }
      }
    }

    action set {
      description
        "Clear stats counters for a specific ACL set or entry";

      input {
        leaf name {
          type leafref {
            path "/oc-acl:acl/oc-acl:acl-sets/oc-acl:acl-set/oc-acl:config" +
                 "/oc-acl:name";
          }
          mandatory true;
          description
            "The ACL name";
        }

        leaf type {
          type leafref {
            path "/oc-acl:acl/oc-acl:acl-sets" +
                 "/oc-acl:acl-set[oc-acl:name=current()/../name]" +
                 "/oc-acl:config/oc-acl:type";
          }
          mandatory true;
          description
            "The ACL type";
        }

        leaf acl-entry {
          type leafref {
            path "/oc-acl:acl/oc-acl:acl-sets" +
                 "/oc-acl:acl-set[oc-acl:name=current()/../name] " +
                 "[oc-acl:type=current()/../type]/oc-acl:acl-entries" +
                 "/oc-acl:acl-entry/oc-acl:config/oc-acl:sequence-id";
          }
          description
            "The ACL entry sequence-id";
        }
      }
      output {
        leaf result {
          type string;
          description
            "The status of the clear operation";
        }
      }
    }
  }
}
