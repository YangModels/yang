module arcos-policy-action-types {
  yang-version 1.1;
  namespace "http://yang.arrcus.com/arcos/policy/action/types";
  prefix arc-pol-actn-types;

  identity ACTION_TYPE {
    description
      "This is an identity of base action-type";
  }

  identity DROP {
    base ACTION_TYPE;
    description
      "drop action type extended from the base action type";
  }

  identity TRANSMIT {
    base ACTION_TYPE;
    description
      "drop action type extended from the base action type";
  }

  identity MARK {
    base ACTION_TYPE;
    description
      "marking action type extended from the base action type";
  }

  identity POLICE {
    base ACTION_TYPE;
    description
      "police action type";
  }
}
