module arcos-datapath-tunnel {
  yang-version 1.1;
  namespace "http://yang.arrcus.com/arcos/datapath/tunnel";
  prefix arc-dp-tunnel;
  import arcos-datapath-aft-types {
    prefix arcos-dp-aft-types;
  }
  import ietf-inet-types {
    prefix inet;
  }

  grouping tunnel-state {
    description
      "Parameters relating to a tunnel within the AFT entry";

    leaf tunnel-type {
      type arcos-dp-aft-types:encapsulation-header-type;
      description
        "Type of IP tunnel";
    }

    leaf src-ip-address {
      type inet:ip-address;
      description
        "Source IP address of tunnel";
    }

    leaf dst-ip-address {
      type inet:ip-address;
      description
        "Destination IP address of tunnel";
    }

    leaf-list sid-list {
      type inet:ipv6-address-no-zone;
      description
        "The list of SIDs added to SRv6 tunnel header";
    }

    leaf-list hw-id-list {
      type uint32;
      description
        "The list of ASIC specific IDs";
    }

    leaf ing-ucast-packets {
      type uint64;
      description
        "Destination ingress packets of ucast";
    }

    leaf ing-mcast-packets {
      type uint64;
      description
        "Destination ingress packets of mcast";
    }

    leaf ing-bcast-packets {
      type uint64;
      description
        "Destination ingress packets of bcast";
    }

    leaf egr-ucast-packets {
      type uint64;
      description
        "Destination egress packets of ucast";
    }

    leaf egr-mcast-packets {
      type uint64;
      description
        "Destination egress packets of mcast";
    }

    leaf egr-bcast-packets {
      type uint64;
      description
        "Destination egress packets of bcast";
    }

    leaf ing-ucast-bytes {
      type uint64;
      description
        "Destination ingress bytes of ucast";
    }

    leaf ing-mcast-bytes {
      type uint64;
      description
        "Destination ingress bytes of mcast";
    }

    leaf ing-bcast-bytes {
      type uint64;
      description
        "Destination ingress bytes of bcast";
    }

    leaf egr-ucast-bytes {
      type uint64;
      description
        "Destination egress bytes of ucast";
    }

    leaf egr-mcast-bytes {
      type uint64;
      description
        "Destination egress bytes of mcast";
    }

    leaf egr-bcast-bytes {
      type uint64;
      description
        "Destination egress bytes of bcast";
    }
  }

  grouping tunnel-state-flat {
  description
    "Structural grouping describing a tunnel entry in HW.";

    container tunnel {
      config false;
      description
        "The list of tunnels programmed into the ASIC.";
      leaf tunnel-id {
        type uint32;
        description
          "Tunnel identifier";
      }
      uses tunnel-state;
    }
  }

  grouping tunnel-top {
  description
    "Structural grouping describing a tunnel entry in HW.";

    container tunnels {
      config false;
      description
        "The list of tunnels programmed into the ASIC.";
      list tunnel {
        key tunnel-id;
        description
          "List of IP tunnels";
  
        leaf tunnel-id {
          type uint32;
          description
            "Tunnel identifier";
        }
  
        container state {
          uses tunnel-state;
        }
      }
    }
  }
  uses tunnel-top;
}
