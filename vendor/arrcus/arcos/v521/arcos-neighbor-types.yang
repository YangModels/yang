module arcos-neighbor-types {
  yang-version 1.1;
  namespace "http://yang.arrcus.com/arcos/neighbor/types";
  prefix arc-nbr-types;

  organization
    "Arrcus, Inc.";

  contact
    "Arrcus, Inc.
     2077 Gateway Place
     Suite 400
     San Jose, CA 95110

     E-mail: yang-support@arrcus.com";

  description
    "This module defines native ArcOS neighbor
     types.

     Copyright (c) 2016-2019 by Arrcus, Inc.
     All rights reserved.";


  revision 2019-10-29 {
    description "Initial version";
  }

  typedef adj-debug-state {
    type enumeration {
      enum on {
        description
          "Enable debug";
      }
      enum off {
        description
          "Disable debug";
      }
    }
  }

  typedef adj-debug-type {
    type enumeration {
      enum control {
        description
          "Control processing debugs";
      }
    }
  }

}
