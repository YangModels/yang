module arcos-oam {
  yang-version 1.1;
  namespace "http://yang.arrcus.com/arcos/oam";
  prefix arc-oam;


  import ietf-yang-types {
    prefix yang;
  }

  import ietf-inet-types {
    prefix inet;
  }

  import openconfig-network-instance {
    prefix oc-netinst;
  }

  import arcos-oam-types {
    prefix arc-oam-types;
  }

  import openconfig-policy-types { prefix "oc-pol-types"; }

   grouping oam-endpoint-events {
    description
      "historical events for the endpoint";
    container events {
      config false;
      list event {
        key "timestamp";
        description
          "list of historical event for this endpoint.";

        leaf timestamp {
          type yang:date-and-time;
          description
            "Indicates the time the event was recorded.";
        }
        leaf event-description {
          type string;
          description
            "event details.";
        }
      }
    }
  }

   grouping oam-endpoint-common-stats {
    leaf avg-latency {
      type decimal64 {
        fraction-digits 1;
      }
      description
        "Average latency value.";
    }
    leaf avg-long-latency {
      type decimal64 {
        fraction-digits 2;
      }
      description
        "Average long latency value.";
    }
    leaf latency-ratio-percent {
      type decimal64 {
        fraction-digits 1;
      }
      description
        "Percentage change of short latency value over long latency value.";
    }
    leaf avg-pkt-loss-percent {
      type decimal64 {
        fraction-digits 1;
      }
      description
        "avg percent pkts lost.";
    }
    leaf num-consecutive-pkt-loss {
      type yang:counter64;
      description
        "number of consecutive pkts lost.";
    }
  }

   grouping oam-endpoint-stats {
    leaf num-state-chg {
      type yang:counter32;
      description
        "number of state changes.";
    }
    leaf probe-requests-sent {
      type yang:counter64;
      description
        "Number of probe requests sent.";
    }
    leaf probe-replies-received {
      type yang:counter64;
      description
        "Number of probe replies received.";
    }
    leaf max-latency {
      type decimal64 {
        fraction-digits 1;
      }
      description
        "Maximum latency value.";
    }
    leaf min-latency {
      type decimal64 {
        fraction-digits 1;
      }
      description
        "Minumum latency value.";
    }
    uses oam-endpoint-common-stats;
  }
  
   grouping oam-history-stats-common {
    list entries {
      leaf timestamp {
        type yang:date-and-time;
        description
          "Indicates the time the metric was recorded.";
      }
      uses oam-endpoint-common-stats;
    }
   }
   
   grouping oam-endpoint-history-stats {
      list stats {
        key "type";
        description
          "list of historical raw stats for this endpoint.";
      
        leaf type {
          type identityref {
           base arc-oam-types:OAM_STAT_TYPE;
         }
         description
            "Indicates the type of the history statistics (raw/average)";
        }
        uses oam-history-stats-common;
      }
  }
  

  grouping oam-endpoint-state {
    description
      "endpoint specific state and counters";

    leaf network-instance {
      type leafref {
        path "/oc-netinst:network-instances/oc-netinst:network-instance" +
            "/oc-netinst:name";
      }
      description
        "OAM endpoint network instance";
    }
    leaf destination {
      type string;
      description
        "OAM-endpoint destination value";
    }
    leaf source {
      type string;
      description
        "OAM-endpoint source value";
    }
    leaf profile-name {
      type string {
        length "1..79";
      }
      description
        "OAM profile attached to this endpoint.";
    }
    
    leaf-list clients {
      type identityref {
        base oc-pol-types:INSTALL_PROTOCOL_TYPE;
      }
      description
        "OAM clients monitoring this endpoint.";
    }
    leaf oam-state {
       type identityref {
         base arc-oam-types:OAM_ENDPOINT_STATE;
       }
       description
         "Current eligibility state of the endpoint.";
    }
    leaf-list ineligibility-reason {
      type identityref {
         base arc-oam-types:OAM_INELIGIBILITY_REASON_TYPE;
      }
       description
         "Reason this endpoint is marked ineligible if applicable.";
    }
    leaf last-state-change-time {
       type yang:date-and-time;
       description
         "Indicates the last time the endpoint state was updated.";
    }
    uses oam-endpoint-stats;
  }

  grouping oam-endpoint-top {
    container endpoints {
      config false;
      list endpoint {
        key "network-instance destination source";
        description
          "The list of OAM endpoints.";

        leaf network-instance {
          type leafref {
            path "../state/network-instance";
          }
          description
            "type of OAM endpoint";
        }
        leaf destination {
          type leafref {
            path "../state/destination";
          }
          description
            "Destination Value of OAM endpoint";
        }
        leaf source {
          type leafref {
            path "../state/source";
          }
          description
            "Source Value of OAM endpoint";
        }
        container state {
          uses oam-endpoint-state;
        }
      }
    }
  }

  grouping oam-endpoint-history-top {
    container endpoint-history {
      config false;
      list endpoint {
        key "network-instance destination source";
        description
          "The list of OAM endpoints.";

        leaf network-instance {
          type leafref {
            path "../../../endpoints/endpoint/state/network-instance";
          }
          description
            "type of OAM endpoint";
        }
        leaf destination {
          type leafref {
            path "../../../endpoints/endpoint/state/destination";
          }
          description
            "Destination Value of OAM endpoint";
        }
        leaf source {
          type leafref {
            path "../../../endpoints/endpoint/state/source";
          }
          description
            "Source Value of OAM endpoint";
        }
        uses oam-endpoint-history-stats;
      }
    }
  }

  grouping oam-stats {
    leaf total-number-of-endpoints {
      type yang:counter32;
      description
        "total number of endpoints being monitored";
    }
    leaf eligible-endpoints {
      type yang:counter32;
      description
        "number of endpoints in eligible or healthy state as per the profile";
    }
    leaf ineligible-endpoints {
      type yang:counter32;
      description
        "number of endpoints in ineligible or unhealthy state as per the profile";
    }
  }

  grouping oam-profile-state {
    description
      "grouping for oam-profile state";
    leaf enabled {
      type boolean;
      description
        "State Enabled/Disabled.";
    }
      leaf probe-interval {
        type uint16;
        description
          "monitor interval value in seconds";
      }
  }

  grouping oam-profile-config {
    description
      "grouping for oam-profile config";

      leaf name {
        type string;
        description
         "Name of oam-profile";
      }
      leaf enable {
        type boolean;
        default true;
        description
          "Enables the OAM profile.";
      }
      leaf monitor-interval {
        type identityref {
          base arc-oam-types:OAM_MONITOR_INTERVAL_TYPE;
        }
        default arc-oam-types:OAM_MONITOR_INTERVAL_60s;
        description
          "monitor interval value in seconds";
      }
      leaf latency {
        type decimal64 {
          fraction-digits 1;
        }
        description
          "Maximum tolerable measured latency value in milli-seconds";
      }
      leaf latency-threshold {
        type decimal64 {
          fraction-digits 1;
        }
        default 15;
        description
          "This metric indicates maximum tolerated ratio of latency(small_window)/latency(long_window) in percentage.";
      }
      leaf baseline-latency-window-multiplier {
        type uint8;
        default 5;
        description
          "Long sliding window duration value as specified by multiples of monitoring interval. This interval will be used to create
          a running average of latency for the “long latency” statistics.";
      }
      leaf pkt-loss-percent {
        type decimal64 {
          fraction-digits 1;
          range "0.1..100";
        }
        description
          "Maximum tolerable measured packet loss as percentage";
      }
      leaf dampening-multiplier {
        type uint8;
        default 3;
        description
          "number of probe intervals in affected state before flagging and notifying the clients";
      }
      leaf maximum-consecutive-pkt-loss {
        type uint16;
        description
          "maximum number of consecutive packet loss tolerated.";
      }
  }

  grouping oam-client-state {
    leaf name {
      type identityref {
        base oc-pol-types:INSTALL_PROTOCOL_TYPE;
      }
      description
        "Name of oam-profile client";
    }
    uses oam-stats;
  }

  grouping oam-client-top {
    container clients {
      config false;
      list client {
        key "name";
        description
          "The list of OAM profile clients.";

        leaf name {
          type leafref {
            path "../state/name";
          }
          description
            "Name of OAM profile client";
        }
        container state {
          uses oam-client-state;
        }
      }
   }
 }

  grouping oam-profile-top {
    container profiles {
      description
        "OAM profile related config";
        list profile {
          key "name";
          leaf name {
            type leafref {
              path "../config/name";
            }
            description
              "Name of OAM profile";
            }
            container config {
              uses oam-profile-config;
            }

            container state {
              config false;
              uses oam-profile-config;
              uses oam-profile-state;
              uses oam-stats;
            }
        }
    }
  }

  grouping oam-monitor-top {
    container monitor {
      description
        "Monitor specific endpoint.";
      action start {
        description
          "Monitor endpoint";

        input {
          leaf network-instance {
            type leafref {
              path "/oc-netinst:network-instances/oc-netinst:network-instance" +
                "/oc-netinst:name";
            }
            description
              "OAM-endpoint ni";
          }
          leaf endpoint {
            type string;
            description
            "Endpoint destination value.";
          }
          leaf from {
            type string;
            description
            "Endpoint source value.";
          }
          leaf profile {
            type leafref {
              path "/arc-oam:oam/arc-oam:profiles/arc-oam:profile/arc-oam:name";
            }
            description
            "Associated profile for this endpoint monitoring.";
          }
        }
        output {
          leaf result {
            type string;
            description
              "The status of the operation";
          }
        }
      }
      action stop {
        description
          "Monitor endpoint";

        input {
          leaf network-instance {
            type leafref {
              path "/oc-netinst:network-instances/oc-netinst:network-instance" +
                "/oc-netinst:name";
            }
            description
              "OAM-endpoint ni";
          }
          leaf endpoint {
            type string;
            description
            "Endpoint value.";
          }
          leaf from {
            type string;
            description
            "Endpoint source value.";
          }
        }
        output {
          leaf result {
            type string;
            description
              "The status of the operation";
          }
        }
      }
    }
  }
  grouping oam-config {
    description
      "Global configuration data for OAMs";
  }

  container oam {
      description
        "Top level enclosing container for OAM model config
        and operational state data";

      container config {
        description
          "Global config data for OAM config";

        uses oam-config;
      }

      container state {
        config false;
        leaf num-profiles {
          type yang:counter32;
          description
            "number of profiles";
          }
          uses oam-stats;
          uses oam-client-top;
      }
      uses oam-profile-top;
      uses oam-endpoint-top;
      uses oam-endpoint-history-top;
      uses oam-monitor-top;
  }


  container oam-clear {
    action all {
      description
        "Clear all endpoint state and history";

      output {
        leaf result {
          type string;
          description
            "The status of the operation";
        }
      }
    }
    action state {
      description
        "Clear all endpoint state";

      input {
        leaf endpoint {
          type string;
            description
            "The endpoint whose state is to be cleared.";
          }
        leaf all {
          type boolean;
            description
            "if all endpoint state is to be cleared.";
        }
      }

      output {
        leaf result {
          type string;
          description
            "The status of the operation";
        }
      }
    }
    action history {
      description
        "Clear all endpoint history";

      input {
        leaf endpoint {
          type string;
            description
            "The endpoint whose history is to be cleared";
        }
        leaf all {
          type boolean;
            description
            "if all endpoint state is to be cleared.";
        }
      }

      output {
        leaf result {
          type string;
          description
            "The status of the operation";
        }
      }
    }
  }
 }
