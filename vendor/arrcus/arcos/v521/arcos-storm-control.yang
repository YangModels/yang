module arcos-storm-control {
  yang-version 1.1;
  namespace "http://yang.arrcus.com/arcos/storm-control";
  prefix arc-strm-ctl;

  import iana-if-type {
    prefix ianaift;
  }

  import openconfig-interfaces {
    prefix oc-if;
  }

  import openconfig-yang-types {
    prefix oc-yang;
  }

  import openconfig-if-ethernet {
    prefix oc-eth;
  }

  import openconfig-if-aggregate {
    prefix oc-lag;
  }

  organization
    "Arrcus, Inc.";

  contact
    "Arrcus, Inc.
     2077 Gateway Place
     Suite 400
     San Jose, CA 95110

     E-mail: yang-support@arrcus.com";

  description
    "This module contains definitions for the storm control feature in ArcOS

     Copyright (c) 2016-2023 by Arrcus, Inc.
     All rights reserved.";


  revision 2023-01-09 {
    description "Add option to configure rates in kbps";
  }

  revision 2022-11-02 {
    description "Update min value configurable for broadcast-level,
                 multicast-level and unknown-unicast-level";
  }

  grouping storm-control-top {
    description
      "Top-level grouping for layer 2 storm control feature";

    container storm-control {
      description
        "Storm control feature for a port";
      leaf broadcast-level {
        type decimal64 {
          fraction-digits 2;
          range "0.01..100";
        }
        description "broadcast traffic rate limit as percentage of port speed";
      }
      leaf multicast-level {
        type decimal64 {
          fraction-digits 2;
          range "0.01..100";
        }
        description "multicast traffic rate limit as percentage of port speed";
      }
      leaf unknown-unicast-level {
        type decimal64 {
          fraction-digits 2;
          range "0.01..100";
        }
        description "unknown-unicast traffic rate limit as percentage of port speed";
      }
      leaf broadcast-kbps {
        type uint32 {
          range "1..4294967295";
         }
        units "kilobits per second";
        description "broadcast traffic rate limit in kilobits per second";
      }
      leaf multicast-kbps {
        type uint32 {
          range "1..4294967295";
         }
        units "kilobits per second";
        description "multicast traffic rate limit in kilobits per second";
      }
      leaf unknown-unicast-kbps {
        type uint32 {
          range "1..4294967295";
         }
        units "kilobits per second";
        description "unknown-unicast traffic rate limit in kilobits per second";
      }

      must "not(broadcast-level and broadcast-kbps)" {
        error-message "Configure only one of either broadcast-level or broadcast-kbps";
      }
      must "not(multicast-level and multicast-kbps)" {
        error-message "Configure only one of either multicast-level or multicast-kbps";
      }
      must "not(unknown-unicast-level and unknown-unicast-kbps)" {
        error-message "Configure one of either unknown-unicast-level or unknown-unicast-kbps";
      }
      container state {
        config false;
        leaf bcast-Kbps {
          type uint32;
          description "broadcast rate limit in Kbps";
        }
        leaf mcast-Kbps {
          type uint32;
          description "multicast rate limit in Kbps";
        }
        leaf uucast-Kbps {
          type uint32;
          description "unknown unicast rate limit in Kbps";
        }
      }
    }
  }

  augment "/oc-if:interfaces/oc-if:interface" {
    uses storm-control-top {
      when "(current()/oc-if:name != 'ma1' and " +
           "(((current()/oc-if:config/oc-if:type = 'ianaift:ethernetCsmacd') or " +
           "(current()/oc-if:config/oc-if:type = 'ianaift:ieee8023adLag')) and " +
           "(boolean(current()/oc-eth:ethernet/oc-eth:config/oc-lag:aggregate-id) != 'true')))";
    }
  }
}
