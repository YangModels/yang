module arcos-openconfig-routing-policy-sr-augments {
  yang-version 1.1;
  namespace "http://yang.arrcus.com/arcos/openconfig/routing-policy-sr/augments";
  prefix arc-oc-rpol-sr-aug;

  import openconfig-routing-policy {
    prefix oc-rpol;
  }

  import ietf-inet-types {
    prefix inet;
  }

  grouping match-sr-policy-config {
    description
      "Configuration data for match conditions on SR policy";
    leaf color {
      type uint32;
      description
        "Match color for the SR policy";
    }
    leaf endpoint {
      type inet:ip-address;
      description
        "Match endpoint for the SR policy";
    }
  }

  grouping match-sr-policy-state {
    description
      "Operational state data for match conditions on SR policy";
  }

  grouping match-sr-policy-top {
    description
      "Top-level grouping for match SR policy";
    container match-sr-policy {
      description
        "Top-level container for match conditions for SR policy.";
      container config {
        description
          "Configuration data for match conditions on SR policy";
        uses match-sr-policy-config;
      }
      container state {
        config false;
        description
          "Operational state data ";
        uses match-sr-policy-config;
        uses match-sr-policy-state;
      }
    }
  }

  grouping set-sr-policy-config {
    description
      "Configuration data for set actions on SR policy";
    leaf binding-sid {
      type inet:ipv6-address;
      description
        "Set binding SID for the SR policy";
    }
    leaf-list sid-list {
      type inet:ipv6-address;
      description
        "Set SID list for the SR policy";
      max-elements 1;
    }
  }

  grouping set-sr-policy-state {
    description
      "Operational state data for set actions on SR policy";
  }

  grouping set-sr-policy-top {
    description
      "Top-level grouping for set SR policy";
    container set-sr-policy {
      description
        "Top-level container for set actions for SR policy.";
      container config {
        description
          "Configuration data for set actions on SR policy";
        uses set-sr-policy-config;
      }
      container state {
        config false;
        description
          "Operational state data ";
        uses set-sr-policy-config;
        uses set-sr-policy-state;
      }
    }
  }

  augment "/oc-rpol:routing-policy" +
          "/oc-rpol:policy-definitions/oc-rpol:policy-definition" +
          "/oc-rpol:statements/oc-rpol:statement" +
          "/oc-rpol:conditions" {
    description
      "Adds SR policy match to conditions";
    uses match-sr-policy-top;
  }

  augment "/oc-rpol:routing-policy" +
          "/oc-rpol:policy-definitions/oc-rpol:policy-definition" +
          "/oc-rpol:statements/oc-rpol:statement" +
          "/oc-rpol:actions" {
    description
      "Adds SR policy set to actions";
    uses set-sr-policy-top;
  }
}
