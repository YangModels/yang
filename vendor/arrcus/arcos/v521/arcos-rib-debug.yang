module arcos-rib-debug {
  yang-version 1.1;
  namespace "http://yang.arrcus.com/arcos/rib/debug";
  prefix arc-rib-dbg;

  typedef rib-debug-state {
    type enumeration { 
      enum on {
        description
          "Enable debug";
      }
      enum off {
        description
          "Disable debug";
      }
    }
  }

  typedef rib-debug-type {
    type enumeration { 
      enum route {
        description
          "Control route/prefix debugs";
      }
      enum path {
        description
          "Control path debugs";
      }
      enum rnh {
        description
          "Control rnh core debugs";
      }
      enum err {
        description
          "Control error debugs";
      }
      enum ds {
        description
          "Control DS API debugs";
      }
      enum rnh-ds {
        description
          "Control DS RNH API debugs";
      }
      enum mpsc {
        description
          "Control MPSC interaction debugs";
      }
      enum ptrack-event {
        description
          "Control prefix tracker event debugs";
      }
      enum ptrack-client {
        description
          "Control prefix tracker client debugs";
      }
      enum client {
        description
          "Control client event debugs";
      }
      enum oper {
        description
          "Control Oper command debugs";
      }
      enum all {
        description
          "Control All debugs";
      }
    }
  }

  container rib-debug {
    description
      "RIB debug control";
    action ipv4 {
      input {
        leaf debug {
        type rib-debug-type;
        mandatory true;
          description
          "Debug to be controlled";
        }
        leaf op {
        type rib-debug-state;
        mandatory true;
          description
          "turn on/off operation";
        }
      }
      output {
        leaf result {
        type string;
          description
          "The status of operation"; 
        }
      }
    }
    action ipv6 {
      input {
        leaf debug {
        type rib-debug-type;
        mandatory true;
          description
          "Debug to be controlled";
        }
        leaf op {
        type rib-debug-state;
        mandatory true;
          description
          "turn on/off debug";
        }
      }
      output {
        leaf result {
        type string;
          description
          "The status of operation"; 
        }
      }
    }
  }
}
