module arcos-l3fm-debug {
  yang-version 1.1;
  namespace "http://yang.arrcus.com/arcos/l3fm/debug";
  prefix arc-l3fm-dbg;

  organization
    "Arrcus, Inc.";

  contact
    "Arrcus, Inc.
     2077 Gateway Place
     Suite 400
     San Jose, CA 95110

     E-mail: yang-support@arrcus.com";

  description
    "This module contains definitions for the
     native ArcOS L3FM Debug domain.

     Note: This module is under deprecation and
     will be migrated to another module.

     Copyright (c) 2016-2019 by Arrcus, Inc.
     All rights reserved.";

  revision 2019-10-31 {
    description "Initial version";
  }

  typedef l3fm-debug-state {
    type enumeration {
      enum off {
        description
          "Disable debug";
      }
      enum on {
        description
          "Enable debug";
      }
    }
  }

  typedef l3fm-debug-type {
    type enumeration {
      enum all {
        description
          "L3FM All debugs";
      }
      enum event {
        description
          "L3FM Event debugs";
      }
      enum ui {
        description
          "L3FM UI debugs";
      }
    }
  }

  container l3fm-debug {
    description
      "L3FM debug control";
    action process {
      input {
        leaf debug {
        type l3fm-debug-type;
        mandatory true;
          description
          "Debug to be controlled";
        }
        leaf op {
        type l3fm-debug-state;
        mandatory true;
          description
          "turn on/off operation";
        }
      }
      output {
        leaf result {
        type string;
          description
          "The status of operation";
        }
      }
    }
  }
}
