module arcos-ospf-policy {
  yang-version "1.1";
  namespace "http://yang.arrcus.com/arcos/ospf/policy";
  prefix "arc-ospf-pol";
  import openconfig-routing-policy { prefix "oc-rpol"; }
  import openconfig-extensions { prefix "oc-ext"; }
  import arcos-ospf-types { prefix "arc-ospf-types"; }
  description
    "This module defines extensions to the OpenConfig policy
    model to add extensions for OSPF. This module is intended
    to be generic for both OSPFv2 and OSPFv3.";
  // OpenConfig specific extensions for module metadata.
  oc-ext:regexp-posix;  
  grouping ospf-match-config {
    description
      "Configuration parameters for OSPF match conditions";
    leaf area-eq {
      type arc-ospf-types:ospf-area-identifier;
      description
        "Match prefixes which are within a particular OSPF area";
    }
  }
  grouping ospf-match-conditions {
    description
      "Match conditions that are added by OSPF";
    container ospf-conditions {
      description
        "Match conditions specific to OSPF";
      container config {
        description
          "Configuration parameters relating to OSPF match conditions";
      }
      container state {
        config false;
        description
          "Operational state parameters relating to OSPF match conditions";
        uses ospf-match-config;
      }
    }
  }
  grouping ospf-actions-config {
    description
      "Configuration parameters for OSPF policy actions";
    leaf set-area {
      type arc-ospf-types:ospf-area-identifier;
      description
        "Set the area for the matched route. This action is typically
        used when importing prefixes into OSPF, such that a route can
        be imported into a specific area within the instance.";
    }
  }
  grouping ospf-actions-set-metric-config {
    description
      "Configuration parameters relating to setting the OSPF metric";
    leaf metric-type {
     type arc-ospf-types:ospf-metric-type; 
     default "TYPE_2_METRIC";
      description
        "Specify the type of metric which is to be set by the policy";

    }
    leaf metric {
      type uint32 {
        range 1..16777215;
      }
      description
        "Set the metric of the routes matching the policy to the value
        specified by this leaf.";
    }
  }
  grouping ospf-actions {
    description
      "Actions that are added by OSPF to the action framework";
    container ospf-actions {
      description
        "Actions specific to OSPF";
      container config {
        description
          "Configuration parameters for OSPF actions";
      }
      container state {
        config false;
        description
          "Operational state parameters for OSPF actions";
      }
      container set-metric {
        description
          "Configuration and state parameters relating to manipulating
          the OSPF metric";
        container config {
          description
            "Configuration parameters relating to setting the OSPF metric";
          uses ospf-actions-set-metric-config;
        }
        container state {
          config false;
          description
            "Operational state parameters relating to setting the OSPF
            metric";
          uses ospf-actions-set-metric-config;
        }
      }
    }
  }
  // augment the groupings into the routing policy model
  // TODO: discuss whether igp-actions should be used or whether this should
  // be removed.
  augment "/oc-rpol:routing-policy/oc-rpol:policy-definitions/" +
          "oc-rpol:policy-definition/oc-rpol:statements/oc-rpol:statement/" +
          "oc-rpol:conditions" {
    description
      "Add OSPF specific match conditions to the routing policy model";
    uses ospf-match-conditions;
  }
  augment "/oc-rpol:routing-policy/oc-rpol:policy-definitions/" +
          "oc-rpol:policy-definition/oc-rpol:statements/oc-rpol:statement/" +
          "oc-rpol:actions" {
    description
      "Add OSPF specific actions to the routing policy model";
    uses ospf-actions;
  }
}
