module arcos-openconfig-network-instance-deviations {
  yang-version 1.1;
  namespace "http://yang.arrcus.com/arcos/openconfig/network-instance/deviations";
  prefix arc-oc-netinst-dev;

  import openconfig-isis-types {
    prefix oc-isis-types;
  }
  import openconfig-local-routing {
    prefix oc-loc-rt;
  }
  import openconfig-network-instance {
    prefix oc-netinst;
  }
  import openconfig-network-instance-types {
    prefix oc-ni-types;
  }
  import arcos-openconfig-network-instance-types {
    prefix arc-oc-ni-types;
  }
  import openconfig-if-ip {
    prefix oc-ip;
  }
  import openconfig-policy-types {
    prefix oc-pol-types;
  }
  import openconfig-types {
    prefix oc-types;
  }
  import ietf-inet-types {
    prefix inet;
  }
  import arcos-isis-types {
    prefix arc-isis-types;
  }
  import openconfig-ospf-types {
    prefix oc-ospf-types;
  }
  import arcos-openconfig-bgp-types {
    prefix arc-oc-bgp-types;
  }
  import arcos-system-types {
    prefix arc-sys-types;
  }

  organization
    "Arrcus, Inc";

  contact
    "Arrcus, Inc.
    2077 Gateway Place,
    San Jose, CA 95110
    Tel: +1 (408) 884-1965
    E-mail: yang-support@arrcus.com";
  
  description
    "This module defines deviate statements for Arrcus
    implemention of the openconfig network-instance module.
    Copyright (c) 2016-2023 by Arrcus, Inc.
    All rights reserved.";

  revision 2023-04-27 {
    description
      "Remove must statment that restricts interface to one network-instance";
  }

  revision 2023-03-31 {
    description
      "Limit the network-instance name length to 15";
  }
  revision 2022-10-28 {
    description
      "Change LDP authentication keys to be encrypted strings.";
  }

  revision 2022-09-26 {
    description
      "Remove the deviate not-supported of mac-table entry subinterface";
  }
  
  revision 2022-06-20 {
    description
      "Replaced Static route next-hop must statement with validation point";
  }

  deviation "/oc-netinst:network-instances/oc-netinst:network-instance" +
            "/oc-netinst:config/oc-netinst:name" {
    deviate replace {
      type string {
        length 1..15;
      }
    }
  }
  deviation "/oc-netinst:network-instances/oc-netinst:network-instance" +
            "/oc-netinst:protocols/oc-netinst:protocol/oc-netinst:ospfv2" {
    deviate not-supported;
    description
      "Not supported in this release.";
  }

  deviation "/oc-netinst:network-instances/oc-netinst:network-instance" +
            "/oc-netinst:config/oc-netinst:route-distinguisher" {
    deviate not-supported;
    description
      "Not supported in this release.";
  }

  deviation "/oc-netinst:network-instances/oc-netinst:network-instance" +
            "/oc-netinst:state/oc-netinst:route-distinguisher" {
    deviate not-supported;
    description
      "Not supported in this release.";
  }

  deviation "/oc-netinst:network-instances/oc-netinst:network-instance" +
            "/oc-netinst:config/oc-netinst:enabled" {
    deviate not-supported;
    description
      "Not supported in this release.";
  }

  deviation "/oc-netinst:network-instances/oc-netinst:network-instance" +
            "/oc-netinst:state/oc-netinst:enabled" {
    deviate not-supported;
    description
      "Not supported in this release.";
  }

  deviation "/oc-netinst:network-instances/oc-netinst:network-instance" +
            "/oc-netinst:protocols/oc-netinst:protocol" +
            "/oc-netinst:config/oc-netinst:enabled" {
    deviate not-supported;
    description
      "Not supported in this release.";
  }

  deviation "/oc-netinst:network-instances/oc-netinst:network-instance/oc-netinst:state" {
    deviate not-supported;
    description
      "Not supported in this release.";
  }

  deviation "/oc-netinst:network-instances/oc-netinst:network-instance/oc-netinst:protocols"
          + "/oc-netinst:protocol/oc-netinst:state/oc-netinst:enabled" {
    deviate not-supported;
    description
      "Not supported in this release.";
  }

  deviation "/oc-netinst:network-instances/oc-netinst:network-instance/oc-netinst:interfaces"
          + "/oc-netinst:interface" {
    deviate add {
      max-elements 1024;
    }
    description
      "Restrict L2 sub interface to a single network instance";
  }

  deviation "/oc-netinst:network-instances/oc-netinst:network-instance/oc-netinst:interfaces"
          + "/oc-netinst:interface/oc-netinst:state/oc-netinst:associated-address-families" {
    deviate not-supported;
    description
      "Not supported in this release.";
  }

  deviation "/oc-netinst:network-instances/oc-netinst:network-instance/oc-netinst:interfaces"
          + "/oc-netinst:interface/oc-netinst:config/oc-netinst:associated-address-families" {
    deviate not-supported;
    description
      "Not supported in this release.";
  }

  deviation "/oc-netinst:network-instances/oc-netinst:network-instance/oc-netinst:config/oc-netinst:router-id" {
    deviate not-supported;
    description
      "Not supported in this release.";
  }

  deviation "/oc-netinst:network-instances/oc-netinst:network-instance/oc-netinst:state/oc-netinst:router-id" {
    deviate not-supported;
    description
      "Not supported in this release.";
  }

  deviation "/oc-netinst:network-instances/oc-netinst:network-instance/oc-netinst:inter-instance-policies" {
    deviate not-supported;
    description
      "Not supported in this release.";
  }

  deviation "/oc-netinst:network-instances/oc-netinst:network-instance/oc-netinst:connection-points" {
    deviate not-supported;
    description
      "Not supported in this release.";
  }

  deviation "/oc-netinst:network-instances/oc-netinst:network-instance"
          + "/oc-netinst:table-connections/oc-netinst:table-connection"
          + "/oc-netinst:config/oc-netinst:src-protocol" {
    deviate replace {
      type identityref {
        base oc-pol-types:INSTALL_PROTOCOL_TYPE;
      }
    }
    deviate add {
      must "current() != 'oc-pol-types:LOCAL_AGGREGATE'" {
        error-message "src-protocol not supported yet";
      }
    }
    description
      "Do not go through network-instance/table.";
  }

  deviation "/oc-netinst:network-instances/oc-netinst:network-instance"
          + "/oc-netinst:table-connections/oc-netinst:table-connection"
          + "/oc-netinst:config/oc-netinst:address-family" {
    deviate replace {
      type identityref {
        base oc-types:ADDRESS_FAMILY;
      }
    }
    deviate add {
      must "current() = 'oc-types:IPV4' or "
         + "current() = 'oc-types:IPV6'" {
        error-message "address-family not supported yet";
      }
    }
    description
      "Do not go through network-instance/table.";
  }

  deviation "/oc-netinst:network-instances/oc-netinst:network-instance"
          + "/oc-netinst:table-connections/oc-netinst:table-connection"
          + "/oc-netinst:config/oc-netinst:dst-protocol" {
    deviate replace {
      type identityref {
        base oc-pol-types:INSTALL_PROTOCOL_TYPE;
      }
    }
    deviate add {
      must "current() = 'oc-pol-types:BGP' or "
         + "current() = 'oc-pol-types:ISIS' or "
         + "current() = 'oc-pol-types:OSPF' or "
         + "current() = 'oc-pol-types:OSPF3'" {
        error-message "dest-protocol not supported yet";
      }
      must 'current() != ../oc-netinst:src-protocol' {
        error-message "dest-protocol must be different then src-protocol";
      }
    }
    description
      "Do not go through network-instance/table.";
  }

  deviation "/oc-netinst:network-instances/oc-netinst:network-instance"
          + "/oc-netinst:table-connections/oc-netinst:table-connection"
          + "/oc-netinst:config/oc-netinst:import-policy" {
    deviate add {
      max-elements 1;
    }
    description
      "Only support one policy in this release.";
  }

  deviation "/oc-netinst:network-instances/oc-netinst:network-instance"
          + "/oc-netinst:table-connections/oc-netinst:table-connection"
          + "/oc-netinst:config/oc-netinst:default-import-policy" {
    deviate not-supported;
    description
      "Not supported in this release.";
  }

  deviation "/oc-netinst:network-instances/oc-netinst:network-instance"
          + "/oc-netinst:table-connections/oc-netinst:table-connection"
          + "/oc-netinst:state/oc-netinst:default-import-policy" {
    deviate not-supported;
    description
      "Not supported in this release.";
  }

  deviation "/oc-netinst:network-instances/oc-netinst:network-instance/oc-netinst:encapsulation" {
    deviate not-supported;
    description
      "Not supported in this release.";
  }

  deviation "/oc-netinst:network-instances/oc-netinst:network-instance/oc-netinst:config/oc-netinst:type" {
    deviate add {
      must "current() = 'oc-ni-types:L2VLAN' or current() = 'oc-ni-types:L3VRF' or current() = 'arc-oc-ni-types:L2P2P_EVPN'" +
           "or current() = 'arc-oc-ni-types:L2VLAN_AWARE_BUNDLE'" {
        error-message "Unsupported network-instance type";
      }
    }
  }

  /*
   * Deviations for static routes
   */

  deviation "/oc-netinst:network-instances/oc-netinst:network-instance"
          + "/oc-netinst:protocols/oc-netinst:protocol/oc-netinst:local-aggregates" {
    deviate not-supported;
    description
      "Not supported in this release";
  }

  deviation "/oc-netinst:network-instances/oc-netinst:network-instance"
          + "/oc-netinst:protocols/oc-netinst:protocol/oc-netinst:static-routes"
          + "/oc-netinst:static/oc-netinst:next-hops/oc-netinst:next-hop"
          + "/oc-netinst:config/oc-netinst:recurse" {
    deviate not-supported;
    description
      "Resursive next-hop not supported in this release";
  }

  deviation "/oc-netinst:network-instances/oc-netinst:network-instance"
          + "/oc-netinst:protocols/oc-netinst:protocol/oc-netinst:static-routes"
          + "/oc-netinst:static/oc-netinst:state" {
    deviate not-supported;
    description
      "Not supported in this release";
  }

  deviation "/oc-netinst:network-instances/oc-netinst:network-instance"
          + "/oc-netinst:protocols/oc-netinst:protocol/oc-netinst:static-routes"
          + "/oc-netinst:static/oc-netinst:next-hops/oc-netinst:next-hop/oc-netinst:state" {
    deviate not-supported;
    description
      "Not supported in this release";
  }

  deviation "/oc-netinst:network-instances/oc-netinst:network-instance"
          + "/oc-netinst:protocols/oc-netinst:protocol/oc-netinst:static-routes"
          + "/oc-netinst:static/oc-netinst:next-hops/oc-netinst:next-hop"
          + "/oc-netinst:interface-ref/oc-netinst:state" {
    deviate not-supported;
    description
      "Not supported in this release";
  }

  deviation "/oc-netinst:network-instances/oc-netinst:network-instance"
          + "/oc-netinst:protocols/oc-netinst:protocol/oc-netinst:static-routes"
          + "/oc-netinst:static/oc-netinst:next-hops/oc-netinst:next-hop" {
    deviate add {
      must "(boolean(oc-netinst:interface-ref/config/interface) != 'true') or (boolean(oc-netinst:config/oc-netinst:next-hop) != 'true') or (oc-netinst:config/oc-netinst:next-hop != 'oc-loc-rt:DROP')" {
        error-message "Next-hop must not be DROP if interface is specified.";
      }
    }
  }
  deviation "/oc-netinst:network-instances/oc-netinst:network-instance"
          + "/oc-netinst:protocols/oc-netinst:protocol/oc-netinst:static-routes"
          + "/oc-netinst:static/oc-netinst:next-hops" {
    deviate add {
      must 'boolean(oc-netinst:next-hop)' {
        error-message "Static route has no path/next-hop.";
      }
      must "(count(oc-netinst:next-hop[oc-netinst:config/oc-netinst:next-hop = 'oc-loc-rt:DROP']) < 2)" {
        error-message "Only one next-hop can be configured to DROP.";
      }
      must "(count(oc-netinst:next-hop[oc-netinst:interface-ref/config/interface]) = 0) or " +
           "((count(oc-netinst:next-hop[oc-netinst:interface-ref/config/interface]) + " +
           "count(oc-netinst:next-hop[oc-netinst:config/oc-netinst:next-hop = 'oc-loc-rt:DROP'])) = " +
           "count(oc-netinst:next-hop))" {
        error-message "All paths must be configured with interface / next-hop as DROP, or without interface.";
      }
    }
  }

  /*
   * Add this deviation of "unique" statement to enfornce unique
   * protocol identifiers per network-instance. This is needed
   * for single-instance protocol components including STATIC and
   * BGP. A separate solution is under investigation in order to
   * allow multiple instances per network-instance for IGPs like
   * IS-IS and OSPF.
   */
  deviation "/oc-netinst:network-instances/oc-netinst:network-instance"
          + "/oc-netinst:protocols/oc-netinst:protocol" {
    deviate add {
      unique "oc-netinst:identifier";
    }
  }

  deviation "/oc-netinst:network-instances/oc-netinst:network-instance"
          + "/oc-netinst:afts/oc-netinst:ipv4-unicast/oc-netinst:ipv4-entry"
          + "/oc-netinst:state" {
    deviate not-supported;
    description
      "Not supported in this release";
  }

  deviation "/oc-netinst:network-instances/oc-netinst:network-instance"
          + "/oc-netinst:afts/oc-netinst:ipv6-unicast/oc-netinst:ipv6-entry"
          + "/oc-netinst:state" {
    deviate not-supported;
    description
      "Not supported in this release";
  }

  deviation "/oc-netinst:network-instances/oc-netinst:network-instance"
          + "/oc-netinst:afts/oc-netinst:mpls/oc-netinst:label-entry"
          + "/oc-netinst:state" {
    deviate not-supported;
    description
      "Not supported in this release";
  }

  deviation "/oc-netinst:network-instances/oc-netinst:network-instance"
          + "/oc-netinst:afts/oc-netinst:policy-forwarding" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:state/oc-netinst:index" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:state/oc-netinst:weight" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:state/oc-netinst:decapsulate-header" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:state/oc-netinst:encapsulate-header" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:state/oc-netinst:popped-mpls-label-stack" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:state/oc-netinst:origin-protocol" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:interface-ref"
          + "/oc-netinst:config" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:state/oc-netinst:index" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:state/oc-netinst:weight" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:state/oc-netinst:decapsulate-header" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:state/oc-netinst:encapsulate-header" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:state/oc-netinst:popped-mpls-label-stack" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:state/oc-netinst:origin-protocol" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:interface-ref"
          + "/oc-netinst:config" {
    deviate not-supported;
    description
      "Not supported in this release";
  }

  deviation "/oc-netinst:network-instances/oc-netinst:network-instance"
          + "/oc-netinst:afts/oc-netinst:mpls/oc-netinst:label-entry"
          + "/oc-netinst:next-hops/oc-netinst:next-hop/oc-netinst:state/oc-netinst:index" {
    deviate not-supported;
    description
      "Not supported in this release";
  }

  deviation "/oc-netinst:network-instances/oc-netinst:network-instance"
          + "/oc-netinst:afts/oc-netinst:mpls/oc-netinst:label-entry"
          + "/oc-netinst:next-hops/oc-netinst:next-hop/oc-netinst:state/oc-netinst:weight" {
    deviate not-supported;
    description
      "Not supported in this release";
  }

  deviation "/oc-netinst:network-instances/oc-netinst:network-instance"
          + "/oc-netinst:afts/oc-netinst:mpls/oc-netinst:label-entry"
          + "/oc-netinst:next-hops/oc-netinst:next-hop/oc-netinst:state/oc-netinst:decapsulate-header" {
    deviate not-supported;
    description
      "Not supported in this release";
  }

  deviation "/oc-netinst:network-instances/oc-netinst:network-instance"
          + "/oc-netinst:afts/oc-netinst:mpls/oc-netinst:label-entry"
          + "/oc-netinst:next-hops/oc-netinst:next-hop/oc-netinst:state/oc-netinst:encapsulate-header" {
    deviate not-supported;
    description
      "Not supported in this release";
  }

  deviation "/oc-netinst:network-instances/oc-netinst:network-instance"
          + "/oc-netinst:afts/oc-netinst:mpls/oc-netinst:label-entry"
          + "/oc-netinst:next-hops/oc-netinst:next-hop/oc-netinst:state/oc-netinst:origin-protocol" {
    deviate not-supported;
    description
      "Not supported in this release";
  }

  deviation "/oc-netinst:network-instances/oc-netinst:network-instance"
          + "/oc-netinst:afts/oc-netinst:mpls/oc-netinst:label-entry"
          + "/oc-netinst:next-hops/oc-netinst:next-hop/oc-netinst:interface-ref"
          + "/oc-netinst:config" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:state" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:state" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:state" {
    deviate not-supported;
    description
      "Not supported in this release";
  }

  deviation "/oc-netinst:network-instances/oc-netinst:network-instance"
          + "/oc-netinst:afts-units/oc-netinst:aft-unit-entry"
          + "/oc-netinst:afts/oc-netinst:policy-forwarding" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:state/oc-netinst:index" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:state/oc-netinst:weight" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:state/oc-netinst:decapsulate-header" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:state/oc-netinst:encapsulate-header" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:state/oc-netinst:popped-mpls-label-stack" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:state/oc-netinst:origin-protocol" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:interface-ref"
          + "/oc-netinst:config" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:state/oc-netinst:index" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:state/oc-netinst:weight" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:state/oc-netinst:decapsulate-header" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:state/oc-netinst:encapsulate-header" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:state/oc-netinst:popped-mpls-label-stack" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:state/oc-netinst:origin-protocol" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:interface-ref"
          + "/oc-netinst:config" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:next-hops/oc-netinst:next-hop/oc-netinst:state/oc-netinst:index" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:next-hops/oc-netinst:next-hop/oc-netinst:state/oc-netinst:weight" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:next-hops/oc-netinst:next-hop/oc-netinst:state/oc-netinst:decapsulate-header" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:next-hops/oc-netinst:next-hop/oc-netinst:state/oc-netinst:encapsulate-header" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:next-hops/oc-netinst:next-hop/oc-netinst:state/oc-netinst:origin-protocol" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:next-hops/oc-netinst:next-hop/oc-netinst:interface-ref"
          + "/oc-netinst:config" {
    deviate not-supported;
    description
      "Not supported in this release";
  }

  /*
   * Deviation for ISIS.
   */

  deviation "/oc-netinst:network-instances/oc-netinst:network-instance"
          + "/oc-netinst:protocols/oc-netinst:protocol/oc-netinst:isis/oc-netinst:global"
          + "/oc-netinst:config/oc-netinst:authentication-check" {
    deviate not-supported;
    description
      "Not supported in this release";
  }

  deviation "/oc-netinst:network-instances/oc-netinst:network-instance"
          + "/oc-netinst:protocols/oc-netinst:protocol/oc-netinst:isis/oc-netinst:global"
          + "/oc-netinst:state/oc-netinst:authentication-check" {
    deviate not-supported;
    description
      "Not supported in this release";
  }

  deviation "/oc-netinst:network-instances/oc-netinst:network-instance"
          + "/oc-netinst:protocols/oc-netinst:protocol/oc-netinst:isis/oc-netinst:global"
          + "/oc-netinst:config/oc-netinst:instance" {
    deviate not-supported;
    description
      "Not supported in this release";
  }

  deviation "/oc-netinst:network-instances/oc-netinst:network-instance"
          + "/oc-netinst:protocols/oc-netinst:protocol/oc-netinst:isis/oc-netinst:global"
          + "/oc-netinst:config/oc-netinst:net" {
    deviate add {
      max-elements 3;
    }
    description
      "Only suppport three area-address in this release";
  }

  deviation "/oc-netinst:network-instances/oc-netinst:network-instance"
          + "/oc-netinst:protocols/oc-netinst:protocol/oc-netinst:isis/oc-netinst:global"
          + "/oc-netinst:config/oc-netinst:maximum-area-addresses" {
    deviate not-supported;
    description
      "Not supported in this release";
  }

  deviation "/oc-netinst:network-instances/oc-netinst:network-instance"
          + "/oc-netinst:protocols/oc-netinst:protocol/oc-netinst:isis/oc-netinst:global"
          + "/oc-netinst:config/oc-netinst:poi-tlv" {
    deviate not-supported;
    description
      "Not supported in this release";
  }

  deviation "/oc-netinst:network-instances/oc-netinst:network-instance"
          + "/oc-netinst:protocols/oc-netinst:protocol/oc-netinst:isis/oc-netinst:global"
          + "/oc-netinst:config/oc-netinst:iid-tlv" {
    deviate not-supported;
    description
      "Not supported in this release";
  }

  deviation "/oc-netinst:network-instances/oc-netinst:network-instance"
          + "/oc-netinst:protocols/oc-netinst:protocol/oc-netinst:isis/oc-netinst:global"
          + "/oc-netinst:config/oc-netinst:fast-flooding" {
    deviate not-supported;
    description
      "Not supported in this release";
  }

  deviation "/oc-netinst:network-instances/oc-netinst:network-instance"
          + "/oc-netinst:protocols/oc-netinst:protocol/oc-netinst:isis/oc-netinst:global"
          + "/oc-netinst:lsp-bit/oc-netinst:overload-bit/oc-netinst:reset-triggers"
          + "/oc-netinst:reset-trigger/oc-netinst:config/oc-netinst:reset-trigger" {
    deviate add {
      must "(not (current() = 'oc-isis-types:WAIT_FOR_SYSTEM'))" {
        error-message "WAIT_FOR_SYSTEM not supported yet";
      }
    }
    description
      "Not supported in this release";
  }

  deviation "/oc-netinst:network-instances/oc-netinst:network-instance"
          + "/oc-netinst:protocols/oc-netinst:protocol/oc-netinst:isis/oc-netinst:global"
          + "/oc-netinst:timers/oc-netinst:lsp-generation" {
    deviate not-supported;
    description
      "Not supported in this release";
  }

  deviation "/oc-netinst:network-instances/oc-netinst:network-instance"
          + "/oc-netinst:protocols/oc-netinst:protocol/oc-netinst:isis/oc-netinst:global"
          + "/oc-netinst:inter-level-propagation-policies"
          + "/oc-netinst:level1-to-level2"
          + "/oc-netinst:config/oc-netinst:import-policy" {
    deviate add {
      max-elements 1;
    }
    description
      "Only support one policy in this release.";
  }

  deviation "/oc-netinst:network-instances/oc-netinst:network-instance"
          + "/oc-netinst:protocols/oc-netinst:protocol/oc-netinst:isis/oc-netinst:global"
          + "/oc-netinst:inter-level-propagation-policies"
          + "/oc-netinst:level2-to-level1"
          + "/oc-netinst:config/oc-netinst:import-policy" {
    deviate add {
      max-elements 1;
    }
    description
      "Only support one policy in this release.";
  }

  deviation "/oc-netinst:network-instances/oc-netinst:network-instance"
          + "/oc-netinst:protocols/oc-netinst:protocol/oc-netinst:isis/oc-netinst:global"
          + "/oc-netinst:inter-level-propagation-policies"
          + "/oc-netinst:level1-to-level2"
          + "/oc-netinst:config/oc-netinst:default-import-policy" {
    deviate not-supported;
    description
      "Not supported in this release.";
  }

  deviation "/oc-netinst:network-instances/oc-netinst:network-instance"
          + "/oc-netinst:protocols/oc-netinst:protocol/oc-netinst:isis/oc-netinst:global"
          + "/oc-netinst:inter-level-propagation-policies"
          + "/oc-netinst:level2-to-level1"
          + "/oc-netinst:config/oc-netinst:default-import-policy" {
    deviate not-supported;
    description
      "Not supported in this release.";
  }

  deviation "/oc-netinst:network-instances/oc-netinst:network-instance"
          + "/oc-netinst:protocols/oc-netinst:protocol/oc-netinst:isis/oc-netinst:global"
          + "/oc-netinst:nsr" {
    deviate not-supported;
    description
      "Not supported in this release";
  }

  deviation "/oc-netinst:network-instances/oc-netinst:network-instance"
          + "/oc-netinst:protocols/oc-netinst:protocol/oc-netinst:isis/oc-netinst:global"
          + "/oc-netinst:mpls/oc-netinst:igp-ldp-sync/oc-netinst:config"
          + "/oc-netinst:post-session-up-delay" {
    deviate not-supported;
    description
      "Not supported in this release";
  }

  deviation "/oc-netinst:network-instances/oc-netinst:network-instance"
          + "/oc-netinst:protocols/oc-netinst:protocol/oc-netinst:isis/oc-netinst:global"
          + "/oc-netinst:mpls/oc-netinst:igp-ldp-sync/oc-netinst:config"
          + "/oc-netinst:enabled" {
    deviate replace {
      default false;
    }
  }

  deviation "/oc-netinst:network-instances/oc-netinst:network-instance"
          + "/oc-netinst:protocols/oc-netinst:protocol/oc-netinst:isis/oc-netinst:global"
          + "/oc-netinst:igp-shortcuts" {
    deviate not-supported;
    description
      "Not supported in this release";
  }

  deviation "/oc-netinst:network-instances/oc-netinst:network-instance"
          + "/oc-netinst:protocols/oc-netinst:protocol/oc-netinst:isis/oc-netinst:global"
          + "/oc-netinst:afi-safi/oc-netinst:af/oc-netinst:config/oc-netinst:metric" {
    deviate not-supported;
    description
      "Not supported in this release";
  }

  deviation "/oc-netinst:network-instances/oc-netinst:network-instance"
          + "/oc-netinst:protocols/oc-netinst:protocol/oc-netinst:isis/oc-netinst:global"
          + "/oc-netinst:afi-safi/oc-netinst:af/oc-netinst:state/oc-netinst:metric" {
    deviate not-supported;
    description
      "Not supported in this release";
  }

  deviation "/oc-netinst:network-instances/oc-netinst:network-instance"
          + "/oc-netinst:protocols/oc-netinst:protocol/oc-netinst:isis/oc-netinst:global"
          + "/oc-netinst:afi-safi/oc-netinst:af/oc-netinst:config/oc-netinst:safi-name" {
    deviate add {
      must "current() = 'oc-isis-types:UNICAST'" {
        error-message "SAFI not supported yet";
      }
    }
    description
      "Do not support multicast SAFI in this release";
  }

  deviation "/oc-netinst:network-instances/oc-netinst:network-instance"
          + "/oc-netinst:protocols/oc-netinst:protocol/oc-netinst:isis/oc-netinst:global"
          + "/oc-netinst:afi-safi/oc-netinst:af/oc-netinst:multi-topology" {
    deviate not-supported;
    description
      "Not supported in this release";
  }

  deviation "/oc-netinst:network-instances/oc-netinst:network-instance"
          + "/oc-netinst:protocols/oc-netinst:protocol/oc-netinst:isis/oc-netinst:global"
          + "/oc-netinst:timers/oc-netinst:spf/oc-netinst:config"
          + "/oc-netinst:spf-hold-interval" {
    deviate replace {
      type uint64 {
        range "1..120000";
      }
    }
    description
      "Add range for spf-hold-interval limit";
  }

  deviation "/oc-netinst:network-instances/oc-netinst:network-instance"
          + "/oc-netinst:protocols/oc-netinst:protocol/oc-netinst:isis/oc-netinst:global"
          + "/oc-netinst:timers/oc-netinst:spf/oc-netinst:config"
          + "/oc-netinst:spf-first-interval" {
    deviate replace {
      type uint64 {
        range "1..120000";
      }
    }
    description
      "Add range and default for spf-first-interval limit";
  }

  deviation "/oc-netinst:network-instances/oc-netinst:network-instance"
          + "/oc-netinst:protocols/oc-netinst:protocol/oc-netinst:isis/oc-netinst:global"
          + "/oc-netinst:transport/oc-netinst:config/oc-netinst:lsp-mtu-size" {
    deviate replace {
      type uint16 {
        range "128..65535";
      }
    }
    description
      "Add range for lsp-mtu-size";
  }

  deviation "/oc-netinst:network-instances/oc-netinst:network-instance"
          + "/oc-netinst:protocols/oc-netinst:protocol/oc-netinst:isis/oc-netinst:global"
          + "/oc-netinst:timers/oc-netinst:spf/oc-netinst:config"
          + "/oc-netinst:spf-second-interval" {
    deviate replace {
      type uint64 {
        range "1..120000";
      }
    }
    description
      "Add range and default for spf-second-interval limit";
  }

  deviation "/oc-netinst:network-instances/oc-netinst:network-instance"
          + "/oc-netinst:protocols/oc-netinst:protocol/oc-netinst:isis/oc-netinst:global"
          + "/oc-netinst:reference-bandwidth/oc-netinst:config/oc-netinst:reference-bandwidth" {
    deviate replace {
      type uint32 {
        range "1..max";
      }
    }
    description
      "Add range for IS-IS reference-bandwidth";
  }

  deviation "/oc-netinst:network-instances/oc-netinst:network-instance"
          + "/oc-netinst:protocols/oc-netinst:protocol/oc-netinst:isis/oc-netinst:levels"
          + "/oc-netinst:level/oc-netinst:config/oc-netinst:authentication-check" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:state/oc-netinst:authentication-check" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:config/oc-netinst:metric-style" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:state/oc-netinst:lsp-id" {
    deviate replace {
      type arc-isis-types:lsp-name;
    }
    description
      "Support use of name";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv4-te-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv6-te-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:instance-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv4-srlg" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv6-srlg" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:purge-oi" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:is-reachability" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:state/oc-netinst:system-id" {
    deviate replace {
      type arc-isis-types:node-name;
    }
    description
      "Fix incorrect use of System-Id as the key and support use of name.";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor/oc-netinst:state/oc-netinst:system-id" {
    deviate replace {
      type arc-isis-types:node-name;
    }
    description
      "Fix incorrect use of System-Id as the key and support use of name.";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv4-internal-reachability" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv4-external-reachability" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:adjacency-sid" {
    deviate not-supported;
    description
      "Correct adjacency SID is implemented in augmentation.";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:admin-group" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:available-bandwidth" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:bandwidth-constraints" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:extended-admin-group" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:ipv4-interface-address" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:ipv4-neighbor-address" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:ipv6-interface-address" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:ipv6-neighbor-address" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:lan-adjacency-sid" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:link-attributes" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:link-delay" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:link-delay-variation" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:link-loss" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:link-protection-type" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:max-link-bandwidth" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:max-reservable-link-bandwidth" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:min-max-link-delay" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:residual-bandwidth" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:te-default-metric" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:unconstrained-lsp" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:unreserved-bandwidth" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs"
          + "/oc-netinst:subTLVs/oc-netinst:utilized-bandwidth" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:adjacency-sid" {
    deviate not-supported;
    description
      "Correct adjacency SID is implemented in augmentation.";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:admin-group" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:available-bandwidth" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:bandwidth-constraints" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:extended-admin-group" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:ipv4-interface-address" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:ipv4-neighbor-address" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:ipv6-interface-address" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:ipv6-neighbor-address" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:lan-adjacency-sid" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:link-attributes" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:link-delay" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:link-delay-variation" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:link-loss" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:link-protection-type" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:max-link-bandwidth" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:max-reservable-link-bandwidth" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:min-max-link-delay" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:residual-bandwidth" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:te-default-metric" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:unconstrained-lsp" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:unreserved-bandwidth" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn"
          + "/oc-netinst:neighbors/oc-netinst:neighbor"
          + "/oc-netinst:instances/oc-netinst:instance/oc-netinst:subTLVs"
          + "/oc-netinst:subTLVs/oc-netinst:utilized-bandwidth" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-ipv4-reachability"
          + "/oc-netinst:prefixes/oc-netinst:prefix/oc-netinst:subTLVs/oc-netinst:subTLVs"
          + "/oc-netinst:ipv4-source-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-ipv4-reachability"
          + "/oc-netinst:prefixes/oc-netinst:prefix/oc-netinst:subTLVs/oc-netinst:subTLVs"
          + "/oc-netinst:ipv6-source-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv6-reachability"
          + "/oc-netinst:prefixes/oc-netinst:prefix/oc-netinst:subTLVs/oc-netinst:subTLVs"
          + "/oc-netinst:ipv4-source-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv6-reachability"
          + "/oc-netinst:prefixes/oc-netinst:prefix/oc-netinst:subTLVs/oc-netinst:subTLVs"
          + "/oc-netinst:ipv6-source-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-ipv6-reachability"
          + "/oc-netinst:prefixes/oc-netinst:prefix/oc-netinst:subTLVs/oc-netinst:subTLVs"
          + "/oc-netinst:ipv4-source-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-ipv6-reachability"
          + "/oc-netinst:prefixes/oc-netinst:prefix/oc-netinst:subTLVs/oc-netinst:subTLVs"
          + "/oc-netinst:ipv6-source-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:isis-neighbor-attribute" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:isis-alias-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:multi-topology"
          + "/oc-netinst:topologies/oc-netinst:topology"
          + "/oc-netinst:state/oc-netinst:attributes" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:traffic-engineering" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:route-preference" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:afi-safi/oc-netinst:af/oc-netinst:safi-name" {
    deviate add {
      must "current() = 'oc-isis-types:UNICAST'" {
        error-message "SAFI not supported yet";
      }
    }
    description
      "Do not support multicast SAFI in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:afi-safi/oc-netinst:af/oc-netinst:config/oc-netinst:metric" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:afi-safi/oc-netinst:af/oc-netinst:state/oc-netinst:metric" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:afi-safi/oc-netinst:af/oc-netinst:segment-routing" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:afi-safi" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:config/oc-netinst:passive" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:state/oc-netinst:passive" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:packet-counters/oc-netinst:esh" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:packet-counters/oc-netinst:ish" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:config/oc-netinst:hello-padding" {
    deviate not-supported;
    description
      "Not supported in this release";
  }

  /*
   * Make circuit-type to be operation state only and change the
   * type to the level-bits which is more accurate based on protocol
   * specificiation.
   */

  deviation "/oc-netinst:network-instances/oc-netinst:network-instance"
          + "/oc-netinst:protocols/oc-netinst:protocol/oc-netinst:isis/oc-netinst:interfaces"
          + "/oc-netinst:interface/oc-netinst:config/oc-netinst:circuit-type" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:state/oc-netinst:circuit-type" {
    deviate replace {
      type identityref {
        base arc-isis-types:level-bits;
      }
    }
    description
      "Fix incorrect use of the term circuit-type.";
  }

  deviation "/oc-netinst:network-instances/oc-netinst:network-instance"
          + "/oc-netinst:fdb/oc-netinst:config" {
    deviate not-supported;
    description
      "Not supported in this release";
  }

  deviation "/oc-netinst:network-instances/oc-netinst:network-instance" +
    "/oc-netinst:fdb/oc-netinst:state" {
    deviate not-supported;
    description "Not supported in this release";
  }

  /* no support for per-mac vlan or multiple vlans in an l2ni */

  deviation "/oc-netinst:network-instances/oc-netinst:network-instance"
          + "/oc-netinst:fdb/oc-netinst:mac-table/oc-netinst:entries/oc-netinst:entry/oc-netinst:state"{
    deviate not-supported;
    description
      "Not supported in this release";
  }

  deviation "/oc-netinst:network-instances/oc-netinst:network-instance"
          + "/oc-netinst:fdb/oc-netinst:mac-table/oc-netinst:entries/oc-netinst:entry/oc-netinst:interface"
          + "/oc-netinst:interface-ref/oc-netinst:state" {
    deviate not-supported;
    description
      "Not supported in this release";
  }

  deviation "/oc-netinst:network-instances/oc-netinst:network-instance"
          + "/oc-netinst:fdb/oc-netinst:mac-table/oc-netinst:entries/oc-netinst:entry/oc-netinst:config"
          + "/oc-netinst:vlan" {
    deviate not-supported;
    description
      "Not supported in this release";
  }

  deviation "/oc-netinst:network-instances/oc-netinst:network-instance" +
    "/oc-netinst:fdb/oc-netinst:mac-table/oc-netinst:entries/oc-netinst:entry/oc-netinst:interface" +
    "/oc-netinst:interface-ref/oc-netinst:state/oc-netinst:subinterface" {
    deviate not-supported;
    description "Not supported in this release";
  }

  deviation "/oc-netinst:network-instances/oc-netinst:network-instance" +
    "/oc-netinst:fdb/oc-netinst:mac-table/oc-netinst:entries/oc-netinst:entry" +
    "/oc-netinst:state/oc-netinst:age" {
    deviate not-supported;
    description "Not supported in this release";
  }

  /* protocol and table-conn supported for L3VRF only */

  deviation "/oc-netinst:network-instances/oc-netinst:network-instance" +
            "/oc-netinst:protocols/oc-netinst:protocol" +
            "/oc-netinst:config/oc-netinst:identifier" {
    deviate add {
      must "(../../../../oc-netinst:config/oc-netinst:type = 'oc-ni-types:L3VRF') or " +
           "(../identifier = 'oc-pol-types:BGP' and " +
           "((../../../../oc-netinst:config/oc-netinst:type = 'oc-ni-types:L2VLAN') or " +
           "(../../../../oc-netinst:config/oc-netinst:type = 'arc-oc-ni-types:L2P2P_EVPN') or " +
           "(../../../../oc-netinst:config/oc-netinst:type = 'arc-oc-ni-types:L2VLAN_AWARE_BUNDLE')))" {
        error-message "Cannot configure protocol instance in this mode";
      }
    }
    description
      "protocol only supported on l3 network instance";
  }

  deviation "/oc-netinst:network-instances/oc-netinst:network-instance/oc-netinst:table-connections/oc-netinst:table-connection" {
    deviate add {
      must "../../oc-netinst:config/oc-netinst:type = 'oc-ni-types:L3VRF'" {
        error-message "table-connection may only be configured for default or mamagement L3VRF network instance type";
      }
    }
    description
      "table-connection only supported on l3 network instance";
  }

  deviation "/oc-netinst:network-instances/oc-netinst:network-instance"
          + "/oc-netinst:fdb/oc-netinst:mac-table/oc-netinst:entries/oc-netinst:entry" {
    deviate add {
      must "../../../../oc-netinst:config/oc-netinst:type = 'oc-ni-types:L2VLAN' and ../../../../oc-netinst:config/oc-netinst:vlan" {
        error-message "mac entry may only be configured in L2VLAN network instance with a valid vlan-id";
      }
    }
    description
      "mac entry may only be configured in L2VLAN network instance with a valid vlan-id";
  }

  deviation "/oc-netinst:network-instances/oc-netinst:network-instance/oc-netinst:config/oc-netinst:type" {
    deviate add {
      default "oc-ni-types:L3VRF";
    }
  }

  /*
   * We do not want RSVP
   */
  deviation "/oc-netinst:network-instances/oc-netinst:network-instance" +
    "/oc-netinst:mpls/oc-netinst:te-global-attributes" {
    deviate not-supported;
    description "Not supported in this release";
  }

  deviation "/oc-netinst:network-instances/oc-netinst:network-instance" +
    "/oc-netinst:mpls/oc-netinst:te-interface-attributes" {
    deviate not-supported;
    description "Not supported in this release";
  }

  deviation "/oc-netinst:network-instances/oc-netinst:network-instance" +
    "/oc-netinst:mpls/oc-netinst:signaling-protocols/oc-netinst:rsvp-te" {
    deviate not-supported;
    description "Not supported in this release";
  }

  /*
   * WE do not want lsps
   */
  deviation "/oc-netinst:network-instances/oc-netinst:network-instance" +
    "/oc-netinst:mpls/oc-netinst:lsps" {
    deviate not-supported;
    description "Not supported in this release";
    }

  /*
   * We do not want to have configured MPLS attributes per interface
   */
  deviation "/oc-netinst:network-instances/oc-netinst:network-instance" +
    "/oc-netinst:mpls/oc-netinst:global/oc-netinst:interface-attributes" {
    deviate not-supported;
    description "Not supported in this release";
  }

  /*
   * Limit the number of reserved blocks to 32
   * NOTE:
   * This number MUST match "LBLMGR_RESERVED_BLOCK_NUM_MAX"
   */
  deviation "/oc-netinst:network-instances/oc-netinst:network-instance" +
    "/oc-netinst:mpls/oc-netinst:global/oc-netinst:reserved-label-blocks" +
    "/oc-netinst:reserved-label-block" {
    deviate add {
      max-elements 32;
    }
    description "Only up to 32 reserved-blocks.";
  }


  /*
   * the yang model has segment routing as a signalling protocol
   * It has two things
   * - per SID (and even per EXP bits value) counter
   * - Some per interface counters for SIDs
   * - Some segment routing enablement per interface
   * We do not support per-route or per-label counters
   * We do not have per interface SR enable,ent
   * So I will deviate segment-routing as an MPLS signaling protocol
   */
  deviation "/oc-netinst:network-instances/oc-netinst:network-instance" +
    "/oc-netinst:mpls/oc-netinst:signaling-protocols/oc-netinst:segment-routing" {
    deviate not-supported;
    description "Not supported in this release";
  }

  /*
   * For this release, we will NOT support SRLB
   * If you add this deviation, make sure that you deviate
   * SRLB configuration and state under ISIS
   * If you only deviate config but not state or vice versa, you will
   * get a build error
   */
  /* deviation "/oc-netinst:network-instances/oc-netinst:network-instance" +
    "/oc-netinst:segment-routing/oc-netinst:srlbs" {
    deviate not-supported;
    description "Not supported in this release";
  } */

  /*
   * For this release we only support SR-MPLS
   */
  deviation "/oc-netinst:network-instances/oc-netinst:network-instance" +
    "/oc-netinst:segment-routing/oc-netinst:srgbs/oc-netinst:srgb/oc-netinst:config/oc-netinst:dataplane-type" {
    deviate add {
      must "current() = 'MPLS'" {
        error-message "MPLS dataplane-type is the only supported SR configuration in this release";
      }
    }
    description "Only supporting SR-MPLS in this release";
  }

  /*
   * Only support up to 28 reserved blocks per SRGB
   * The number 28 came from the SR-capability sub-TLV in ISIS. All
   * blocks used by an ISIS process MUST fit into a 255 byte sub-TLV
   */
  deviation "/oc-netinst:network-instances/oc-netinst:network-instance" +
    "/oc-netinst:segment-routing/oc-netinst:srgbs/oc-netinst:srgb/oc-netinst:config" +
    "/oc-netinst:mpls-label-blocks" {
    deviate add {
      max-elements 28;
    }
    description "Only support maximum of 28 blocks per SRGB.";
  }

  /*
   * Only support up to 8 SRGBs
   */
  deviation "/oc-netinst:network-instances/oc-netinst:network-instance" +
    "/oc-netinst:segment-routing/oc-netinst:srgbs/oc-netinst:srgb" {
    deviate add {
      max-elements 8;
    }
    description "Only support maximum of 8 SRGBs.";
  }

  /*
   * LDP supports only default VRF.
   */
  deviation "/oc-netinst:network-instances/oc-netinst:network-instance" +
    "/oc-netinst:mpls/oc-netinst:signaling-protocols/oc-netinst:ldp" +
    "/oc-netinst:global/oc-netinst:config/oc-netinst:lsr-id" {
    deviate add {
      must "../../../../../../oc-netinst:config/oc-netinst:type = 'oc-ni-types:L3VRF' and
            ../../../../../../oc-netinst:config/oc-netinst:name = 'default'" {
        error-message "MPLS LDP signaling-protocols configuration is only valid with the default network instance.";
      }
    }
    deviate replace {
      type inet:ip-address;
    }
    description "MPLS LDP signaling-protocols configuration is only valid with the default network instance.";
  }

  deviation "/oc-netinst:network-instances/oc-netinst:network-instance" +
    "/oc-netinst:mpls/oc-netinst:signaling-protocols/oc-netinst:ldp/oc-netinst:global/oc-netinst:authentication/oc-netinst:config/oc-netinst:enable" {
    deviate add {
      must "../../../../../../../oc-netinst:config/oc-netinst:type = 'oc-ni-types:L3VRF' and
            ../../../../../../../oc-netinst:config/oc-netinst:name = 'default'" {
        error-message "MPLS LDP signaling-protocols configuration is only valid with the default network instance.";
      }
    }
    description "MPLS LDP signaling-protocols configuration is only valid with the default network instance.";
  }

  deviation "/oc-netinst:network-instances/oc-netinst:network-instance" +
    "/oc-netinst:mpls/oc-netinst:signaling-protocols/oc-netinst:ldp/oc-netinst:global/oc-netinst:authentication/oc-netinst:config/oc-netinst:authentication-key" {
    deviate add {
      must "../../../../../../../oc-netinst:config/oc-netinst:type = 'oc-ni-types:L3VRF' and
            ../../../../../../../oc-netinst:config/oc-netinst:name = 'default'" {
        error-message "MPLS LDP signaling-protocols configuration is only valid with the default network instance.";
      }
    }
    description "MPLS LDP signaling-protocols configuration is only valid with the default network instance.";
  }

  deviation "/oc-netinst:network-instances/oc-netinst:network-instance" +
    "/oc-netinst:mpls/oc-netinst:signaling-protocols/oc-netinst:ldp/oc-netinst:global/oc-netinst:attributes/oc-netinst:config/oc-netinst:php-type" {
    deviate add {
      must "../../../../../../../oc-netinst:config/oc-netinst:type = 'oc-ni-types:L3VRF' and
            ../../../../../../../oc-netinst:config/oc-netinst:name = 'default'" {
        error-message "MPLS LDP signaling-protocols configuration is only valid with the default network instance.";
      }
    }
    description "MPLS LDP signaling-protocols configuration is only valid with the default network instance.";
  }

  deviation "/oc-netinst:network-instances/oc-netinst:network-instance" +
    "/oc-netinst:mpls/oc-netinst:signaling-protocols/oc-netinst:ldp/oc-netinst:global/oc-netinst:attributes/oc-netinst:config/oc-netinst:php-enable" {
    deviate add {
      must "../../../../../../../oc-netinst:config/oc-netinst:type = 'oc-ni-types:L3VRF' and
            ../../../../../../../oc-netinst:config/oc-netinst:name = 'default'" {
        error-message "MPLS LDP signaling-protocols configuration is only valid with the default network instance.";
      }
    }
    description "MPLS LDP signaling-protocols configuration is only valid with the default network instance.";
  }

  deviation "/oc-netinst:network-instances/oc-netinst:network-instance" +
    "/oc-netinst:mpls/oc-netinst:signaling-protocols/oc-netinst:ldp/oc-netinst:global/oc-netinst:attributes/oc-netinst:config/oc-netinst:label-distribution-mode" {
    deviate add {
      must "../../../../../../../oc-netinst:config/oc-netinst:type = 'oc-ni-types:L3VRF' and
            ../../../../../../../oc-netinst:config/oc-netinst:name = 'default'" {
        error-message "MPLS LDP signaling-protocols configuration is only valid with the default network instance.";
      }
    }
    description "MPLS LDP signaling-protocols configuration is only valid with the default network instance.";
  }

  deviation "/oc-netinst:network-instances/oc-netinst:network-instance" +
    "/oc-netinst:mpls/oc-netinst:signaling-protocols/oc-netinst:ldp/oc-netinst:interface-attributes/oc-netinst:config/oc-netinst:hello-holdtime" {
    deviate add {
      must "../../../../../../oc-netinst:config/oc-netinst:type = 'oc-ni-types:L3VRF' and
            ../../../../../../oc-netinst:config/oc-netinst:name = 'default'" {
        error-message "MPLS LDP signaling-protocols configuration is only valid with the default network instance.";
      }
    }
    description "MPLS LDP signaling-protocols configuration is only valid with the default network instance.";
  }

  deviation "/oc-netinst:network-instances/oc-netinst:network-instance" +
    "/oc-netinst:mpls/oc-netinst:signaling-protocols/oc-netinst:ldp/oc-netinst:interface-attributes/oc-netinst:config/oc-netinst:hello-interval" {
    deviate add {
      must "../../../../../../oc-netinst:config/oc-netinst:type = 'oc-ni-types:L3VRF' and
            ../../../../../../oc-netinst:config/oc-netinst:name = 'default'" {
        error-message "MPLS LDP signaling-protocols configuration is only valid with the default network instance.";
      }
    }
    description "MPLS LDP signaling-protocols configuration is only valid with the default network instance.";
  }

  deviation "/oc-netinst:network-instances/oc-netinst:network-instance" +
    "/oc-netinst:mpls/oc-netinst:signaling-protocols/oc-netinst:ldp/oc-netinst:interface-attributes/oc-netinst:config/oc-netinst:link-hello" {
    deviate add {
      must "../../../../../../oc-netinst:config/oc-netinst:type = 'oc-ni-types:L3VRF' and
            ../../../../../../oc-netinst:config/oc-netinst:name = 'default'" {
        error-message "MPLS LDP signaling-protocols configuration is only valid with the default network instance.";
      }
    }
    description "MPLS LDP signaling-protocols configuration is only valid with the default network instance.";
  }

  deviation "/oc-netinst:network-instances/oc-netinst:network-instance" +
    "/oc-netinst:mpls/oc-netinst:signaling-protocols/oc-netinst:ldp/oc-netinst:interface-attributes/oc-netinst:interfaces/oc-netinst:interface" {
    deviate add {
      must "../../../../../../oc-netinst:config/oc-netinst:type = 'oc-ni-types:L3VRF' and
            ../../../../../../oc-netinst:config/oc-netinst:name = 'default'" {
        error-message "MPLS LDP signaling-protocols configuration is only valid with the default network instance.";
      }
    }
    description "MPLS LDP signaling-protocols configuration is only valid with the default network instance.";
  }

  deviation "/oc-netinst:network-instances/oc-netinst:network-instance" +
    "/oc-netinst:mpls/oc-netinst:signaling-protocols/oc-netinst:ldp/oc-netinst:neighbors/oc-netinst:neighbor" {
    deviate add {
      must "../../../../../oc-netinst:config/oc-netinst:type = 'oc-ni-types:L3VRF' and
            ../../../../../oc-netinst:config/oc-netinst:name = 'default'" {
        error-message "MPLS LDP signaling-protocols configuration is only valid with the default network instance.";
      }
    }
    description "MPLS LDP signaling-protocols configuration is only valid with the default network instance.";
  }

/*
  deviation "/oc-netinst:network-instances/oc-netinst:network-instance" +
    "/oc-netinst:mpls/oc-netinst:signaling-protocols/oc-netinst:ldp"+
    "/oc-netinst:neighbors/oc-netinst:neighbor/oc-netinst:config/oc-netinst:lsr-id" {
    deviate add {
      must "../../../../../../../oc-netinst:config/oc-netinst:type = 'oc-ni-types:L3VRF' and
            ../../../../../../../oc-netinst:config/oc-netinst:name = 'default'" {
        error-message "MPLS LDP signaling-protocols configuration is only valid with the default network instance.";
      }
    }
    description "MPLS LDP signaling-protocols configuration is only valid with the default network instance.";
  }

  deviation "/oc-netinst:network-instances/oc-netinst:network-instance" +
    "/oc-netinst:mpls/oc-netinst:signaling-protocols/oc-netinst:ldp" +
    "/oc-netinst:neighbors/oc-netinst:neighbor/oc-netinst:config/oc-netinst:label-space-id" {
    deviate add {
      must "../../../../../../../oc-netinst:config/oc-netinst:type = 'oc-ni-types:L3VRF' and
            ../../../../../../../oc-netinst:config/oc-netinst:name = 'default'" {
        error-message "MPLS LDP signaling-protocols configuration is only valid with the default network instance.";
      }
    }
    description "MPLS LDP signaling-protocols configuration is only valid with the default network instance.";
  }

  deviation "/oc-netinst:network-instances/oc-netinst:network-instance" +
    "/oc-netinst:mpls/oc-netinst:signaling-protocols/oc-netinst:ldp/oc-netinst:neighbors/oc-netinst:neighbor/oc-netinst:authentication/oc-netinst:config/oc-netinst:enable" {
    deviate add {
      must "../../../../../../../../oc-netinst:config/oc-netinst:type = 'oc-ni-types:L3VRF' and
            ../../../../../../../../oc-netinst:config/oc-netinst:name = 'default'" {
        error-message "MPLS LDP signaling-protocols configuration is only valid with the default network instance.";
      }
    }
    description "MPLS LDP signaling-protocols configuration is only valid with the default network instance.";
  }

  deviation "/oc-netinst:network-instances/oc-netinst:network-instance" +
    "/oc-netinst:mpls/oc-netinst:signaling-protocols/oc-netinst:ldp/oc-netinst:neighbors/oc-netinst:neighbor/oc-netinst:authentication/oc-netinst:config/oc-netinst:authentication-key" {
    deviate add {
      must "../../../../../../../../oc-netinst:config/oc-netinst:type = 'oc-ni-types:L3VRF' and
            ../../../../../../../../oc-netinst:config/oc-netinst:name = 'default'" {
        error-message "MPLS LDP signaling-protocols configuration is only valid with the default network instance.";
      }
    }
    description "MPLS LDP signaling-protocols configuration is only valid with the default network instance.";
  }
*/

/*
  deviation "/oc-netinst:network-instances/oc-netinst:network-instance" +
    "/oc-netinst:mpls" {
    deviate add {
      must "../oc-netinst:config/oc-netinst:name = 'default'" {
        error-message "MPLS configuration is only valid with the default network instance.";
      }
    }
    description "MPLS configuration is only valid with the default network instance.";
  }

  deviation "/oc-netinst:network-instances/oc-netinst:network-instance" +
    "/oc-netinst:segment-routing" {
    deviate add {
      must "../oc-netinst:config/oc-netinst:name = 'default'" {
        error-message "Segment routing configuration is only valid with the default network instance.";
      }
    }
    description "Segment routing configuration is only valid with the default network instance.";
  }
*/

  /**********************
   * Deviations for BGP *
   **********************/
  // Global BGP Commands modified.
  deviation "/oc-netinst:network-instances/oc-netinst:network-instance" +
            "/oc-netinst:protocols/oc-netinst:protocol" +
            "/oc-netinst:bgp" +
            "/oc-netinst:global/oc-netinst:config/oc-netinst:as" {
    //    deviate replace {
    //      mandatory false;
    //    }
    deviate add {
      must "../../../../../../oc-netinst:name = 'default'" {
        error-message "BGP global AS number must be configured in network-instance default only.";
      }
    }
  }

  deviation "/oc-netinst:network-instances/oc-netinst:network-instance" +
            "/oc-netinst:protocols/oc-netinst:protocol/oc-netinst:config" +
            "/oc-netinst:default-metric" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:ebgp-multihop/oc-netinst:config/oc-netinst:enabled" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:apply-policy" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:as-path-options/oc-netinst:config" +
            "/oc-netinst:replace-peer-as" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:as-path-options/oc-netinst:config" +
            "/oc-netinst:disable-peer-as-filter" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:as-path-options/oc-netinst:state" +
            "/oc-netinst:replace-peer-as" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:as-path-options/oc-netinst:state" +
            "/oc-netinst:disable-peer-as-filter" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:config/oc-netinst:local-as" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:apply-policy/oc-netinst:config/oc-netinst:import-policy" {
    deviate add {
      max-elements 8;
    }
    description "Only support eight policies in this release.";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:apply-policy/oc-netinst:config" +
            "/oc-netinst:default-import-policy" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:apply-policy/oc-netinst:state" +
            "/oc-netinst:default-import-policy" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:apply-policy/oc-netinst:config/oc-netinst:export-policy" {
    deviate add {
      max-elements 8;
    }
    description "Only support eight policies in this release.";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:apply-policy/oc-netinst:config" +
            "/oc-netinst:default-export-policy" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:apply-policy/oc-netinst:state" +
            "/oc-netinst:default-export-policy" {
    deviate not-supported;
    description "not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:ebgp-multihop/oc-netinst:config/oc-netinst:multihop-ttl" {
    deviate add {
      must ". > 0" {
        error-message "TTL cannot be set to 0";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:config/oc-netinst:afi-safi-name" {
    deviate add {
      must "(boolean(/oc-netinst:network-instances" +
                    "/oc-netinst:network-instance[name=current()/../../../../../../../../../config/name]" +
                    "/oc-netinst:protocols/oc-netinst:protocol" +
                    "/oc-netinst:bgp/oc-netinst:global/oc-netinst:afi-safis" +
                    "/oc-netinst:afi-safi[afi-safi-name=current()]/oc-netinst:config/oc-netinst:afi-safi-name))" {
        error-message "BGP global AF must be configured first.";
      }
    }
    description "Not supported in this release";
  }

  // Global BGP Commands not supported.
  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" +
            "/oc-netinst:config/oc-netinst:receive" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" +
            "/oc-netinst:config/oc-netinst:send" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" +
            "/oc-netinst:config/oc-netinst:send-max" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" +
            "/oc-netinst:state/oc-netinst:receive" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" +
            "/oc-netinst:state/oc-netinst:send" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" +
            "/oc-netinst:state/oc-netinst:send-max" {
    deviate not-supported;
    description "Not supported in this release";
  }

  deviation "/oc-netinst:network-instances/oc-netinst:network-instance" +
            "/oc-netinst:protocols/oc-netinst:protocol" +
            "/oc-netinst:bgp" +
            "/oc-netinst:global/oc-netinst:confederation" {
    deviate not-supported;
    description "Not supported in this release";
  }

  deviation "/oc-netinst:network-instances/oc-netinst:network-instance" +
            "/oc-netinst:protocols/oc-netinst:protocol" +
            "/oc-netinst:bgp" +
            "/oc-netinst:global/oc-netinst:use-multiple-paths" {
    deviate not-supported;
    description "Not supported in this release";
  }

  deviation "/oc-netinst:network-instances/oc-netinst:network-instance" +
            "/oc-netinst:protocols/oc-netinst:protocol" +
            "/oc-netinst:bgp" +
            "/oc-netinst:global/oc-netinst:default-route-distance" {
    deviate not-supported;
    description "Not supported in this release";
  }

  deviation "/oc-netinst:network-instances/oc-netinst:network-instance" +
            "/oc-netinst:protocols/oc-netinst:protocol" +
            "/oc-netinst:bgp" +
            "/oc-netinst:global/oc-netinst:dynamic-neighbor-prefixes" {
    deviate not-supported;
    description "Not supported in this release";
  }

  // Global route-selection knobs not supported
  deviation "/oc-netinst:network-instances/oc-netinst:network-instance" +
            "/oc-netinst:protocols/oc-netinst:protocol" +
            "/oc-netinst:bgp" +
            "/oc-netinst:global/oc-netinst:route-selection-options" +
            "/oc-netinst:config/oc-netinst:always-compare-med" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:state/oc-netinst:always-compare-med" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:config/oc-netinst:ignore-as-path-length" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:state/oc-netinst:ignore-as-path-length" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:config/oc-netinst:external-compare-router-id" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:state/oc-netinst:external-compare-router-id" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:config/oc-netinst:advertise-inactive-routes" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:state/oc-netinst:advertise-inactive-routes" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:config/oc-netinst:enable-aigp" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:state/oc-netinst:enable-aigp" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:route-selection-options" {
    deviate not-supported;
    description "Not supported in this release";
  }

  // Global BGP AF Commands not supported.
  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:config/oc-netinst:enabled" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:use-multiple-paths" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:ipv4-unicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:ipv4-unicast/oc-netinst:config/oc-netinst:send-default-route" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:ipv6-unicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:ipv6-unicast/oc-netinst:config/oc-netinst:send-default-route" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:ipv4-labeled-unicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:ipv6-labeled-unicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:l3vpn-ipv4-unicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:l3vpn-ipv6-unicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:l3vpn-ipv4-multicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:l3vpn-ipv6-multicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:l2vpn-vpls/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:l2vpn-evpn/oc-netinst:prefix-limit" {
    deviate not-supported;
    description "Not supported in this release";
  }

  // Global BGP Neighbor Commands not supported.
  deviation "/oc-netinst:network-instances/oc-netinst:network-instance" +
            "/oc-netinst:protocols/oc-netinst:protocol" +
            "/oc-netinst:bgp" +
            "/oc-netinst:neighbors/oc-netinst:neighbor/oc-netinst:config" +
            "/oc-netinst:enabled" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:state" +
            "/oc-netinst:session-state" {
    deviate replace {
      type arc-oc-bgp-types:session-state-type;
    }
    description "BGP session state with updated types";
  }

  deviation "/oc-netinst:network-instances/oc-netinst:network-instance" +
            "/oc-netinst:protocols/oc-netinst:protocol" +
            "/oc-netinst:bgp" +
            "/oc-netinst:neighbors/oc-netinst:neighbor/oc-netinst:config" +
            "/oc-netinst:peer-type" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:config" +
            "/oc-netinst:route-flap-damping" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:state" +
            "/oc-netinst:route-flap-damping" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:config" +
            "/oc-netinst:send-community" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:timers" +
            "/oc-netinst:config/oc-netinst:minimum-advertisement-interval" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:timers" +
            "/oc-netinst:config/oc-netinst:hold-time" {
    deviate replace { default 180; }
  }

  deviation "/oc-netinst:network-instances/oc-netinst:network-instance" +
            "/oc-netinst:protocols/oc-netinst:protocol" +
            "/oc-netinst:bgp" +
            "/oc-netinst:neighbors/oc-netinst:neighbor/oc-netinst:timers" +
            "/oc-netinst:config/oc-netinst:keepalive-interval" {
    deviate replace { default 60; }
  }

  deviation "/oc-netinst:network-instances/oc-netinst:network-instance" +
            "/oc-netinst:protocols/oc-netinst:protocol" +
            "/oc-netinst:bgp" +
            "/oc-netinst:neighbors/oc-netinst:neighbor/oc-netinst:transport" +
            "/oc-netinst:config/oc-netinst:tcp-mss" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:transport" +
            "/oc-netinst:config/oc-netinst:mtu-discovery" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:error-handling" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:graceful-restart/oc-netinst:config" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:logging-options" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:route-reflector/oc-netinst:state" +
            "/oc-netinst:route-reflector-cluster-id" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:route-reflector/oc-netinst:config" +
            "/oc-netinst:route-reflector-cluster-id" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:use-multiple-paths" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:afi-safis" +
            "/oc-netinst:afi-safi/oc-netinst:config/oc-netinst:enabled" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:graceful-restart/oc-netinst:config" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:afi-safis" +
            "/oc-netinst:afi-safi/oc-netinst:ipv4-unicast/oc-netinst:config" +
            "/oc-netinst:send-default-route" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:afi-safis" +
            "/oc-netinst:afi-safi/oc-netinst:ipv6-unicast/oc-netinst:config" +
            "/oc-netinst:send-default-route" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:use-multiple-paths" {
    deviate not-supported;
    description "Not supported in this release";
  }

  // Global BGP Commands modified.
  deviation "/oc-netinst:network-instances/oc-netinst:network-instance" +
            "/oc-netinst:protocols/oc-netinst:protocol" +
            "/oc-netinst:bgp" {
    deviate add {
       must "boolean(/oc-netinst:network-instances/oc-netinst:network-instance[name='default']" +
                    "/oc-netinst:protocols/oc-netinst:protocol/oc-netinst:bgp)" {
           error-message "BGP is not allowed in non-default network-instance without " +
                         "BGP configured in the default network-instance.";
       }
    }
    description "Do not allow BGP configured in non-default network-instances only";
  }

  deviation "/oc-netinst:network-instances/oc-netinst:network-instance" +
            "/oc-netinst:protocols/oc-netinst:protocol" +
            "/oc-netinst:bgp" +
            "/oc-netinst:global/oc-netinst:afi-safis/oc-netinst:afi-safi/oc-netinst:config/oc-netinst:afi-safi-name" {
    deviate add {
       must "boolean(/oc-netinst:network-instances/oc-netinst:network-instance[name='default']" +
                    "/oc-netinst:protocols/oc-netinst:protocol" +
                    "/oc-netinst:bgp/oc-netinst:global/oc-netinst:config/oc-netinst:as) and " +
            "boolean(/oc-netinst:network-instances/oc-netinst:network-instance[name='default']" +
                    "/oc-netinst:protocols/oc-netinst:protocol" +
                    "/oc-netinst:bgp/oc-netinst:global/oc-netinst:config/oc-netinst:router-id)" {
           error-message "Local-AS and Router-ID must be configured.";
       }
    }
    description "Confd workaround";
  }

  deviation "/oc-netinst:network-instances/oc-netinst:network-instance" +
            "/oc-netinst:protocols/oc-netinst:protocol" +
            "/oc-netinst:bgp" +
            "/oc-netinst:neighbors/oc-netinst:neighbor/oc-netinst:config/oc-netinst:neighbor-address" {
    deviate add {
       must "boolean(/oc-netinst:network-instances/oc-netinst:network-instance[name='default']" +
                    "/oc-netinst:protocols/oc-netinst:protocol" +
                    "/oc-netinst:bgp/oc-netinst:global/oc-netinst:config/oc-netinst:as) and " +
            "boolean(/oc-netinst:network-instances/oc-netinst:network-instance[name='default']" +
                    "/oc-netinst:protocols/oc-netinst:protocol" +
                    "/oc-netinst:bgp/oc-netinst:global/oc-netinst:config/oc-netinst:router-id)" {
           error-message "Local-AS and Router-ID must be configured.";
       }
    }
    description "Confd workaround";
  }

  // Graceful-restart related deviations
  deviation "/oc-netinst:network-instances/oc-netinst:network-instance" +
            "/oc-netinst:protocols/oc-netinst:protocol" +
            "/oc-netinst:bgp" +
            "/oc-netinst:global/oc-netinst:graceful-restart" +
            "/oc-netinst:config/oc-netinst:enabled" {
    deviate add {
      default true;
    }
    description "Global graceful-restart enabled default value added";
  }

  deviation "/oc-netinst:network-instances/oc-netinst:network-instance" +
            "/oc-netinst:protocols/oc-netinst:protocol" +
            "/oc-netinst:bgp" +
            "/oc-netinst:global/oc-netinst:graceful-restart" +
            "/oc-netinst:config/oc-netinst:stale-routes-time" {
    deviate replace {
      type uint16;
    }
    description "Global graceful-restart stale-time type changed";
  }

  deviation "/oc-netinst:network-instances/oc-netinst:network-instance" +
            "/oc-netinst:protocols/oc-netinst:protocol" +
            "/oc-netinst:bgp" +
            "/oc-netinst:global/oc-netinst:graceful-restart/oc-netinst:state" +
            "/oc-netinst:stale-routes-time" {
    deviate replace {
      type uint16;
    }
    description "Global graceful-restart stale-time type changed";
  }

  deviation "/oc-netinst:network-instances/oc-netinst:network-instance" +
            "/oc-netinst:protocols/oc-netinst:protocol" +
            "/oc-netinst:bgp" +
            "/oc-netinst:global/oc-netinst:graceful-restart" +
            "/oc-netinst:config/oc-netinst:stale-routes-time" {
    deviate add {
      default 300;
    }
    description "Global graceful-restart stale-time default value added";
  }

  deviation "/oc-netinst:network-instances/oc-netinst:network-instance" +
            "/oc-netinst:protocols/oc-netinst:protocol" +
            "/oc-netinst:bgp" +
            "/oc-netinst:global/oc-netinst:graceful-restart" +
            "/oc-netinst:config/oc-netinst:restart-time" {
    deviate add {
      default 120;
    }
    description "Global graceful-restart restart-time default value added";
  }

  deviation "/oc-netinst:network-instances/oc-netinst:network-instance" +
            "/oc-netinst:protocols/oc-netinst:protocol" +
            "/oc-netinst:bgp" +
            "/oc-netinst:neighbors/oc-netinst:neighbor" +
            "/oc-netinst:graceful-restart/oc-netinst:state/oc-netinst:stale-routes-time" {
    deviate replace {
      type uint16;
    }
    description "Neighbor graceful-restart stale-time type changed";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:graceful-restart/oc-netinst:config/oc-netinst:enabled" {
    deviate delete {
      default false;
    }
    description "Global AF graceful-restart enabled default value deleted";
  }

  // end graceful-restart related deviations

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:state" +
            "/oc-netinst:prefixes/oc-netinst:installed" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:state" +
            "/oc-netinst:prefixes/oc-netinst:received-pre-policy" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv4-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv4-labeled-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv6-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv6-labeled-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l3vpn-ipv4-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l3vpn-ipv6-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l2vpn-evpn" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv4-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv6-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv4-labeled-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv6-labeled-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l3vpn-ipv4-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l3vpn-ipv6-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l2vpn-evpn" +
            "/oc-netinst:prefix-limit/oc-netinst:config/oc-netinst:prevent-teardown" {
    deviate delete {
      default false;
    }
    description "Remove the unnecessary default value";
  }

  /*
   * Make "max-prefixes" mandatory for "prefix-limit" config.
   */
  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv4-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv6-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv4-labeled-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv6-labeled-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l3vpn-ipv4-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l3vpn-ipv6-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l2vpn-evpn" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  /*
   * Deviations for peer-group under BGP
   */
  // Global BGP Commands modified.
  deviation "/oc-netinst:network-instances/oc-netinst:network-instance" +
            "/oc-netinst:protocols/oc-netinst:protocol" +
            "/oc-netinst:bgp" +
            "/oc-netinst:peer-groups/oc-netinst:peer-group" +
            "/oc-netinst:apply-policy" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:as-path-options/oc-netinst:config" +
            "/oc-netinst:replace-peer-as" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:as-path-options/oc-netinst:config" +
            "/oc-netinst:disable-peer-as-filter" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:as-path-options/oc-netinst:state" +
            "/oc-netinst:replace-peer-as" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:as-path-options/oc-netinst:state" +
            "/oc-netinst:disable-peer-as-filter" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:config/oc-netinst:local-as" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi" +
            "/oc-netinst:apply-policy/oc-netinst:config/oc-netinst:import-policy" {
    deviate add {
      max-elements 1;
    }
    description "Only support one policy in this release.";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi" +
            "/oc-netinst:apply-policy/oc-netinst:config" +
            "/oc-netinst:default-import-policy" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi" +
            "/oc-netinst:apply-policy/oc-netinst:config/oc-netinst:export-policy" {
    deviate add {
      max-elements 8;
    }
    description "Only support eight policies in this release.";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi" +
            "/oc-netinst:apply-policy/oc-netinst:config" +
            "/oc-netinst:default-export-policy" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:config" +
            "/oc-netinst:afi-safi-name" {
    deviate add {
      must "(boolean(/oc-netinst:network-instances" +
           "/oc-netinst:network-instance[name=current()/../../../../../../../../../config/name]" +
           "/oc-netinst:protocols/oc-netinst:protocol" +
           "/oc-netinst:bgp" +
           "/oc-netinst:global/oc-netinst:afi-safis" +
           "/oc-netinst:afi-safi[afi-safi-name=current()/../afi-safi-name]))" {
        error-message "BGP global AF must be configured first.";
      }
    }
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:config" +
            "/oc-netinst:peer-type" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:config" +
            "/oc-netinst:route-flap-damping" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:state" +
            "/oc-netinst:route-flap-damping" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:config" +
            "/oc-netinst:send-community" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:state" +
            "/oc-netinst:send-community" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:state" +
            "/oc-netinst:total-paths" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:state" +
            "/oc-netinst:total-prefixes" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:timers" +
            "/oc-netinst:config/oc-netinst:minimum-advertisement-interval" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:timers" +
            "/oc-netinst:config/oc-netinst:hold-time" {
    deviate replace { default 180; }
  }

  deviation "/oc-netinst:network-instances/oc-netinst:network-instance" +
            "/oc-netinst:protocols/oc-netinst:protocol" +
            "/oc-netinst:bgp" +
            "/oc-netinst:peer-groups/oc-netinst:peer-group/oc-netinst:timers" +
            "/oc-netinst:config/oc-netinst:keepalive-interval" {
    deviate replace { default 60; }
  }

  deviation "/oc-netinst:network-instances/oc-netinst:network-instance" +
            "/oc-netinst:protocols/oc-netinst:protocol" +
            "/oc-netinst:bgp" +
            "/oc-netinst:peer-groups/oc-netinst:peer-group" +
            "/oc-netinst:transport/oc-netinst:config/oc-netinst:tcp-mss" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:transport/oc-netinst:config/oc-netinst:mtu-discovery" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:error-handling" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:graceful-restart/oc-netinst:config" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:logging-options" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:route-reflector/oc-netinst:state" +
            "/oc-netinst:route-reflector-cluster-id" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:route-reflector/oc-netinst:config" +
            "/oc-netinst:route-reflector-cluster-id" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:use-multiple-paths" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:config/oc-netinst:enabled" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi" +
            "/oc-netinst:graceful-restart/oc-netinst:config" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-unicast" +
            "/oc-netinst:config/oc-netinst:send-default-route" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-unicast" +
            "/oc-netinst:config/oc-netinst:send-default-route" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:use-multiple-paths" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:transport/oc-netinst:config/oc-netinst:local-address" {
    deviate replace {
      type union {
        type inet:ip-address;
        type string;
      }
    }
    description "Replacement of type due to OpenConfig non-compliance with
                 YANG 1.0/1.1 pattern statement:
                 option 1: IP address
                 option 2: String representing interface name (swp1, swp1.1, loopback0 etc.)";
  }

  deviation "/oc-netinst:network-instances/oc-netinst:network-instance" +
            "/oc-netinst:protocols/oc-netinst:protocol" +
            "/oc-netinst:bgp" +
            "/oc-netinst:peer-groups/oc-netinst:peer-group" +
            "/oc-netinst:transport/oc-netinst:state/oc-netinst:local-address" {
    deviate replace {
      type union {
        type inet:ip-address;
        type string;
      }
    }

    description "Replacement of type due to OpenConfig non-compliance with
                 YANG 1.0/1.1 pattern statement:
                 option 1: IP address
                 option 2: String representing interface name (swp1, swp1.1, loopback0 etc.)";
  }

  deviation "/oc-netinst:network-instances/oc-netinst:network-instance" +
            "/oc-netinst:protocols/oc-netinst:protocol" +
            "/oc-netinst:bgp" +
            "/oc-netinst:peer-groups/oc-netinst:peer-group" +
            "/oc-netinst:graceful-restart/oc-netinst:config/oc-netinst:stale-routes-time" {
    deviate replace {
      type uint16;
    }
    description "Neighbor graceful-restart stale-time type changed";
  }

  deviation "/oc-netinst:network-instances/oc-netinst:network-instance" +
            "/oc-netinst:protocols/oc-netinst:protocol" +
            "/oc-netinst:bgp" +
            "/oc-netinst:peer-groups/oc-netinst:peer-group" +
            "/oc-netinst:graceful-restart/oc-netinst:state/oc-netinst:stale-routes-time" {
    deviate replace {
      type uint16;
    }
    description "Neighbor graceful-restart stale-time type changed";
  }

  deviation "/oc-netinst:network-instances/oc-netinst:network-instance" +
            "/oc-netinst:protocols/oc-netinst:protocol" +
            "/oc-netinst:bgp" +
            "/oc-netinst:peer-groups/oc-netinst:peer-group" +
            "/oc-netinst:graceful-restart/oc-netinst:config/oc-netinst:stale-routes-time" {
    deviate add {
      default 300;
    }
    description "Neighbor graceful-restart stale-time default value added";
  }

  deviation "/oc-netinst:network-instances/oc-netinst:network-instance" +
            "/oc-netinst:protocols/oc-netinst:protocol" +
            "/oc-netinst:bgp" +
            "/oc-netinst:peer-groups/oc-netinst:peer-group" +
            "/oc-netinst:graceful-restart/oc-netinst:config/oc-netinst:restart-time" {
    deviate add {
      default 120;
    }
    description "Neighbor graceful-restart stale-time default value added";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-labeled-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-labeled-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l3vpn-ipv4-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l3vpn-ipv6-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l2vpn-evpn" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-labeled-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-labeled-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l3vpn-ipv4-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l3vpn-ipv6-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l2vpn-evpn" +
            "/oc-netinst:prefix-limit/oc-netinst:config/oc-netinst:prevent-teardown" {
    deviate delete {
      default false;
    }
    description "Remove the unnecessary default value";
  }

  /*
   * Make "max-prefixes" mandatory for "prefix-limit" config.
   */
  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-labeled-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-labeled-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l3vpn-ipv4-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l3vpn-ipv6-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l2vpn-evpn" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group/oc-netinst:config" {
    deviate add {
       must "boolean(/oc-netinst:network-instances/oc-netinst:network-instance" +
                    "/oc-netinst:protocols/oc-netinst:protocol" +
                    "/oc-netinst:bgp" +
                    "/oc-netinst:global/oc-netinst:config/oc-netinst:as) and " +
             "boolean(/oc-netinst:network-instances/oc-netinst:network-instance" +
                    "/oc-netinst:protocols/oc-netinst:protocol" +
                    "/oc-netinst:bgp" +
                    "/oc-netinst:global/oc-netinst:config/oc-netinst:router-id)" {
           error-message "Local-AS and Router-ID must be configured.";
       }
    }
    description "Confd workaround";
  }

  deviation "/oc-netinst:network-instances/oc-netinst:network-instance" +
            "/oc-netinst:protocols/oc-netinst:protocol" +
            "/oc-netinst:bgp" +
            "/oc-netinst:peer-groups/oc-netinst:peer-group" +
            "/oc-netinst:ebgp-multihop/oc-netinst:config/oc-netinst:enabled" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:ebgp-multihop/oc-netinst:state/oc-netinst:enabled" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:ebgp-multihop/oc-netinst:config/oc-netinst:multihop-ttl" {
    deviate add {
      must ". > 0" {
        error-message "TTL cannot be set to 0";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:apply-policy" +
            "/oc-netinst:state/oc-netinst:default-import-policy" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:apply-policy" +
            "/oc-netinst:state/oc-netinst:default-export-policy" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:add-paths" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi" +
            "/oc-netinst:add-paths" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:transport/oc-netinst:config/oc-netinst:local-address" {
    deviate replace {
      type union {
        type inet:ip-address;
        type string;
      }
    }
    description "Replacement of type due to OpenConfig non-compliance with
                 YANG 1.0/1.1 pattern statement:
                 option 1: IP address
                 option 2: String representing interface name (swp1, swp1.1, loopback0 etc.)";
  }

  deviation "/oc-netinst:network-instances/oc-netinst:network-instance" +
            "/oc-netinst:protocols/oc-netinst:protocol" +
            "/oc-netinst:bgp" +
            "/oc-netinst:neighbors/oc-netinst:neighbor" +
            "/oc-netinst:transport/oc-netinst:state/oc-netinst:local-address" {
    deviate replace {
      type union {
        type inet:ip-address;
        type string;
      }
    }
    description "Replacement of type due to OpenConfig non-compliance with
                 YANG 1.0/1.1 pattern statement:
                 option 1: IP address
                 option 2: String representing interface name (swp1, swp1.1, loopback0 etc.)";
  }

  deviation "/oc-netinst:network-instances/oc-netinst:network-instance" +
            "/oc-netinst:protocols/oc-netinst:protocol" +
            "/oc-netinst:bgp" +
            "/oc-netinst:neighbors/oc-netinst:neighbor" +
            "/oc-netinst:transport/oc-netinst:state/oc-netinst:remote-address" {
    deviate replace {
      type inet:ip-address;
    }
    description "Replacement of type due to OpenConfig non-compliance with
                 YANG 1.0/1.1 pattern statement";
  }

  /*
   * TODO
   * Currently, type leafref in unions are not validated,
   * and treated as a string internally. Making leafref a part of a union
   * in a deviation throws an error - "The type leafref cannot be part of a union".
   * Once confd supports it, change "string" to "leafref" pointing to
   * interface name in openconfig-interfaces.
   */
  deviation "/oc-netinst:network-instances/oc-netinst:network-instance" +
            "/oc-netinst:protocols/oc-netinst:protocol" +
            "/oc-netinst:bgp" +
            "/oc-netinst:neighbors/oc-netinst:neighbor/oc-netinst:config" +
            "/oc-netinst:neighbor-address" {
    deviate replace {
      type union {
        type inet:ip-address;
        type string;
      }
    }
    description "Replacement of type due to OpenConfig non-compliance with
                 YANG 1.0/1.1 pattern statement:
                 option 1: IP address
                 option 2: String representing local interface name (swp1, swp1.1 etc.)";
  }

  deviation "/oc-netinst:network-instances/oc-netinst:network-instance" +
            "/oc-netinst:protocols/oc-netinst:protocol" +
            "/oc-netinst:bgp" +
            "/oc-netinst:neighbors/oc-netinst:neighbor/oc-netinst:state" +
            "/oc-netinst:neighbor-address" {
    deviate replace {
      type union {
        type inet:ip-address;
        type string;
      }
    }
    description "Replacement of type due to OpenConfig non-compliance with
                 YANG 1.0/1.1 pattern statement:
                 option 1: IP address
                 option 2: String representing local interface name (swp1, swp1.1 etc.)";
  }

  deviation "/oc-netinst:network-instances/oc-netinst:network-instance" +
            "/oc-netinst:protocols/oc-netinst:protocol" +
            "/oc-netinst:bgp" +
            "/oc-netinst:neighbors/oc-netinst:neighbor/oc-netinst:state" +
            "/oc-netinst:last-established" {
    deviate replace {
      type string;
    }
    description "Change last established state to a human readable format";
  }

  /**************************
   * Deviations for BGP-RIB *
   **************************/
  deviation "/oc-netinst:network-instances/oc-netinst:network-instance" +
            "/oc-netinst:protocols/oc-netinst:protocol" +
            "/oc-netinst:bgp/oc-netinst:rib" +
            "/oc-netinst:attr-sets/oc-netinst:attr-set" +
            "/oc-netinst:state/oc-netinst:next-hop" {
    deviate not-supported;
    description "Not supported in this release";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv4-unicast" +
            "/oc-netinst:neighbors/oc-netinst:neighbor" +
            "/oc-netinst:adj-rib-out-pre" {
    deviate not-supported;
    description "Not supported in this release";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv4-unicast" +
            "/oc-netinst:neighbors/oc-netinst:neighbor" +
            "/oc-netinst:adj-rib-out-post" {
    deviate not-supported;
    description "Not supported in this release";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv6-unicast" +
            "/oc-netinst:neighbors/oc-netinst:neighbor" +
            "/oc-netinst:adj-rib-out-pre" {
    deviate not-supported;
    description "Not supported in this release";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv6-unicast" +
            "/oc-netinst:neighbors/oc-netinst:neighbor" +
            "/oc-netinst:adj-rib-out-post" {
    deviate not-supported;
    description "Not supported in this release";
  }

  deviation "/oc-netinst:network-instances/oc-netinst:network-instance" +
            "/oc-netinst:protocols/oc-netinst:protocol" +
            "/oc-netinst:bgp/oc-netinst:rib" +
            "/oc-netinst:afi-safis/oc-netinst:afi-safi" +
            "/oc-netinst:ipv4-unicast/oc-netinst:neighbors" +
            "/oc-netinst:neighbor/oc-netinst:state" +
            "/oc-netinst:neighbor-address" {
    deviate replace {
      type leafref {
        path "/oc-netinst:network-instances/oc-netinst:network-instance" +
             "/oc-netinst:protocols/oc-netinst:protocol" +
             "/oc-netinst:bgp/oc-netinst:neighbors/oc-netinst:neighbor" +
             "/oc-netinst:neighbor-address";
      }
    }
    description "Change neighbor-address type to leafref";
  }

  deviation "/oc-netinst:network-instances/oc-netinst:network-instance" +
            "/oc-netinst:protocols/oc-netinst:protocol" +
            "/oc-netinst:bgp/oc-netinst:rib" +
            "/oc-netinst:afi-safis/oc-netinst:afi-safi" +
            "/oc-netinst:ipv6-unicast/oc-netinst:neighbors" +
            "/oc-netinst:neighbor/oc-netinst:state" +
            "/oc-netinst:neighbor-address" {
    deviate replace {
      type leafref {
        path "/oc-netinst:network-instances/oc-netinst:network-instance" +
             "/oc-netinst:protocols/oc-netinst:protocol" +
             "/oc-netinst:bgp/oc-netinst:neighbors/oc-netinst:neighbor" +
             "/oc-netinst:neighbor-address";
      }
    }
    description "Change neighbor-address type to leafref";
  }

  deviation "/oc-netinst:network-instances/oc-netinst:network-instance" +
            "/oc-netinst:protocols/oc-netinst:protocol" +
            "/oc-netinst:bgp/oc-netinst:rib" +
            "/oc-netinst:attr-sets/oc-netinst:attr-set" +
            "/oc-netinst:tunnel-encapsulation" {
    deviate not-supported;
    description "Not supported in this release";
  }

  // deviation "/oc-netinst:network-instances/oc-netinst:network-instance" +
  //           "/oc-netinst:protocols/oc-netinst:protocol" +
  //           "/oc-netinst:bgp/oc-netinst:rib" +
  //           "/oc-netinst:afi-safis" +
  //           "/oc-netinst:afi-safi/oc-netinst:ipv4-srte-policy" {
  //    deviate not-supported;
  //    description "Not supported in this release";
  // }

  // deviation "/oc-netinst:network-instances/oc-netinst:network-instance" +
  //           "/oc-netinst:protocols/oc-netinst:protocol" +
  //           "/oc-netinst:bgp/oc-netinst:rib" +
  //           "/oc-netinst:afi-safis" +
  //           "/oc-netinst:afi-safi/oc-netinst:ipv6-srte-policy" {
  //    deviate not-supported;
  //    description "Not supported in this release";
  // }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv4-unicast" +
            "/oc-netinst:loc-rib/oc-netinst:routes/oc-netinst:route" +
            "/oc-netinst:state/oc-netinst:origin" {
    deviate replace {
      type union {
        type inet:ip-address;
        type string;
        type identityref {
          base oc-pol-types:INSTALL_PROTOCOL_TYPE;
        }
      }
    }
    description "Change origin type to handle interface name for neighbor";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv4-unicast" +
            "/oc-netinst:loc-rib/oc-netinst:routes/oc-netinst:route" +
            "/oc-netinst:state/oc-netinst:path-id" {
    deviate replace {
      type uint64;
    }
    description "Change path-id type to handle 64-bit internal ID";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv4-unicast" +
            "/oc-netinst:neighbors/oc-netinst:neighbor" +
            "/oc-netinst:adj-rib-in-pre/oc-netinst:routes/oc-netinst:route" +
            "/oc-netinst:state/oc-netinst:path-id" {
    deviate replace {
      type uint64;
    }
    description "Change path-id type to handle 64-bit internal ID";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv4-unicast" +
            "/oc-netinst:neighbors/oc-netinst:neighbor" +
            "/oc-netinst:adj-rib-in-post/oc-netinst:routes/oc-netinst:route" +
            "/oc-netinst:state/oc-netinst:path-id" {
    deviate replace {
      type uint64;
    }
    description "Change path-id type to handle 64-bit internal ID";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv6-unicast" +
            "/oc-netinst:loc-rib/oc-netinst:routes/oc-netinst:route" +
            "/oc-netinst:state/oc-netinst:origin" {
    deviate replace {
      type union {
        type inet:ip-address;
        type string;
        type identityref {
          base oc-pol-types:INSTALL_PROTOCOL_TYPE;
        }
      }
    }
    description "Change origin type to handle interface name for neighbor";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv6-unicast" +
            "/oc-netinst:loc-rib/oc-netinst:routes/oc-netinst:route" +
            "/oc-netinst:state/oc-netinst:path-id" {
    deviate replace {
      type uint64;
    }
    description "Change path-id type to handle 64-bit internal path ID";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv6-unicast" +
            "/oc-netinst:neighbors/oc-netinst:neighbor" +
            "/oc-netinst:adj-rib-in-pre/oc-netinst:routes/oc-netinst:route" +
            "/oc-netinst:state/oc-netinst:path-id" {
    deviate replace {
      type uint64;
    }
    description "Change path-id type to handle 64-bit internal ID";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv6-unicast" +
            "/oc-netinst:neighbors/oc-netinst:neighbor" +
            "/oc-netinst:adj-rib-in-post/oc-netinst:routes/oc-netinst:route" +
            "/oc-netinst:state/oc-netinst:path-id" {
    deviate replace {
      type uint64;
    }
    description "Change path-id type to handle 64-bit internal ID";
  }

  deviation "/oc-netinst:network-instances/oc-netinst:network-instance" +
            "/oc-netinst:protocols/oc-netinst:protocol/oc-netinst:isis" +
            "/oc-netinst:levels/oc-netinst:level/oc-netinst:authentication" +
            "/oc-netinst:key/oc-netinst:config/oc-netinst:auth-password" {

    deviate replace {
      type arc-sys-types:encrypted-string;
    }

    description "Prevent storage of clear-text strings in the configuration database";
  }

  deviation "/oc-netinst:network-instances/oc-netinst:network-instance" +
            "/oc-netinst:protocols/oc-netinst:protocol/oc-netinst:isis" +
            "/oc-netinst:interfaces/oc-netinst:interface/oc-netinst:authentication" +
            "/oc-netinst:key/oc-netinst:config/oc-netinst:auth-password" {

    deviate replace {
      type arc-sys-types:encrypted-string;
    }

    description "Prevent storage of clear-text strings in the configuration database";
  }

  deviation "/oc-netinst:network-instances/oc-netinst:network-instance" +
            "/oc-netinst:protocols/oc-netinst:protocol/oc-netinst:isis" +
            "/oc-netinst:interfaces/oc-netinst:interface" +
            "/oc-netinst:levels/oc-netinst:level/oc-netinst:hello-authentication" +
            "/oc-netinst:key/oc-netinst:config/oc-netinst:auth-password" {

    deviate replace {
      type arc-sys-types:encrypted-string;
    }

    description "Prevent storage of clear-text strings in the configuration database";
  }

  deviation "/oc-netinst:network-instances/oc-netinst:network-instance" +
            "/oc-netinst:protocols/oc-netinst:protocol/oc-netinst:isis" +
            "/oc-netinst:interfaces/oc-netinst:interface/oc-netinst:levels" +
            "/oc-netinst:level/oc-netinst:adjacencies/oc-netinst:adjacency" +
            "/oc-netinst:state/oc-netinst:system-id" {
    deviate replace {
      type arc-isis-types:system-name;
    }

    description "Support use of name";
  }

  deviation "/oc-netinst:network-instances/oc-netinst:network-instance/oc-netinst:protocols" +
            "/oc-netinst:protocol/oc-netinst:bgp/oc-netinst:neighbors/oc-netinst:neighbor" +
            "/oc-netinst:config/oc-netinst:auth-password" {

    deviate replace {
      type arc-sys-types:encrypted-string;
    }

    description "Prevent storage of clear-text strings in the configuration database";
  }

  deviation "/oc-netinst:network-instances/oc-netinst:network-instance/oc-netinst:protocols" +
            "/oc-netinst:protocol/oc-netinst:bgp/oc-netinst:peer-groups/oc-netinst:peer-group" +
            "/oc-netinst:config/oc-netinst:auth-password" {

    deviate replace {
      type arc-sys-types:encrypted-string;
    }

    description "Prevent storage of clear-text strings in the configuration database";
  }

  deviation "/oc-netinst:network-instances/oc-netinst:network-instance" +
            "/oc-netinst:mpls/oc-netinst:signaling-protocols/oc-netinst:ldp" +
            "/oc-netinst:global/oc-netinst:config/oc-netinst:lsr-id" {
    deviate replace {
      type inet:ip-address;
    }
  }

  deviation "/oc-netinst:network-instances/oc-netinst:network-instance" +
            "/oc-netinst:mpls/oc-netinst:signaling-protocols/oc-netinst:ldp" +
            "/oc-netinst:neighbors/oc-netinst:neighbor/oc-netinst:config/oc-netinst:lsr-id" {
    deviate replace {
      type inet:ip-address;
    }
  }

  deviation "/oc-netinst:network-instances/oc-netinst:network-instance" +
            "/oc-netinst:mpls/oc-netinst:signaling-protocols/oc-netinst:ldp" +
            "/oc-netinst:global/oc-netinst:state/oc-netinst:lsr-id" {
    deviate replace {
      type inet:ip-address;
    }
  }

  deviation "/oc-netinst:network-instances/oc-netinst:network-instance" +
            "/oc-netinst:mpls/oc-netinst:signaling-protocols/oc-netinst:ldp" +
            "/oc-netinst:neighbors/oc-netinst:neighbor/oc-netinst:state/oc-netinst:lsr-id" {
    deviate replace {
      type inet:ip-address;
    }
  }

  deviation "/oc-netinst:network-instances/oc-netinst:network-instance" +
            "/oc-netinst:mpls/oc-netinst:signaling-protocols/oc-netinst:ldp" +
            "/oc-netinst:global/oc-netinst:authentication/oc-netinst:config" +
            "/oc-netinst:authentication-key" {
    deviate replace {
      type arc-sys-types:encrypted-string;
    }

    description "Prevent storage of clear-text strings in the configuration database";
  }

  deviation "/oc-netinst:network-instances/oc-netinst:network-instance" +
            "/oc-netinst:mpls/oc-netinst:signaling-protocols/oc-netinst:ldp" +
            "/oc-netinst:neighbors/oc-netinst:neighbor/oc-netinst:authentication" +
            "/oc-netinst:config/oc-netinst:authentication-key" {
    deviate replace {
      type arc-sys-types:encrypted-string;
    }

    description "Prevent storage of clear-text strings in the configuration database";
  }

  deviation "/oc-netinst:network-instances/oc-netinst:network-instance/oc-netinst:mpls/oc-netinst:signaling-protocols" +
            "/oc-netinst:ldp/oc-netinst:interface-attributes/oc-netinst:config/oc-netinst:link-hello" {
    deviate not-supported;
    description
      "Not supported in this release.";
  }

  deviation "/oc-netinst:network-instances/oc-netinst:network-instance/oc-netinst:mpls/oc-netinst:signaling-protocols" +
            "/oc-netinst:ldp/oc-netinst:interface-attributes/oc-netinst:state/oc-netinst:link-hello" {
    deviate not-supported;
    description
      "Not supported in this release.";
  }

  /*
   * check if local-id is configured for reserved label block
   * Maximum length of local-id cannot exceed 63
   */
  deviation "/oc-netinst:network-instances/oc-netinst:network-instance" +
            "/oc-netinst:mpls/oc-netinst:global" +
            "/oc-netinst:reserved-label-blocks/oc-netinst:reserved-label-block" +
            "/oc-netinst:config/oc-netinst:local-id" {
    deviate add {
      mandatory true;
    }
    deviate replace {
      type string {
        length "1..63" {
          error-message "Length of local-id should be less-than 63 characters";
        }
      }
    }
  }

  /*
   * check if lower-bound is configured for reserved label block
   */
  deviation "/oc-netinst:network-instances/oc-netinst:network-instance" +
            "/oc-netinst:mpls/oc-netinst:global" +
            "/oc-netinst:reserved-label-blocks/oc-netinst:reserved-label-block" +
            "/oc-netinst:config/oc-netinst:lower-bound" {
    deviate add {
      mandatory true;
    }
  }

  /*
   * check if upper-bound is configured for reserved label block
   */
  deviation "/oc-netinst:network-instances/oc-netinst:network-instance" +
            "/oc-netinst:mpls/oc-netinst:global" +
            "/oc-netinst:reserved-label-blocks/oc-netinst:reserved-label-block" +
            "/oc-netinst:config/oc-netinst:upper-bound" {
    deviate add {
      mandatory true;
      must ". >= ../oc-netinst:lower-bound" {
        error-message "upper bound is less than lower bound";
      }
    }
  }

  /*
   * check if local-id is configured for srgb label block
   * Maximum length of local-id cannot exceed 63
   */
  deviation "/oc-netinst:network-instances/oc-netinst:network-instance" +
            "/oc-netinst:segment-routing/oc-netinst:srgbs" +
            "/oc-netinst:srgb/oc-netinst:config/oc-netinst:local-id" {
    deviate add {
      mandatory true;
    }
    deviate replace {
      type string {
        length "1..63" {
          error-message "Length of local-id should be less-than 63 characters";
        }
      }
    }
  }

  /*
   * check if local-id is configured for srlb label block
   * Maximum length of local-id cannot exceed 63
   */
  deviation "/oc-netinst:network-instances/oc-netinst:network-instance" +
            "/oc-netinst:segment-routing/oc-netinst:srlbs" +
            "/oc-netinst:srlb/oc-netinst:config/oc-netinst:local-id" {
    deviate add {
      mandatory true;
    }
    deviate replace {
      type string {
        length "1..63" {
          error-message "Length of local-id should be less-than 63 characters";
        }
      }
    }
  }

  deviation "/oc-netinst:network-instances/oc-netinst:network-instance" +
            "/oc-netinst:protocols/oc-netinst:protocol/oc-netinst:isis" +
            "/oc-netinst:levels/oc-netinst:level/oc-netinst:link-state-database" +
            "/oc-netinst:lsp/oc-netinst:tlvs/oc-netinst:tlv/oc-netinst:router-capabilities" +
            "/oc-netinst:capability/oc-netinst:subtlvs/oc-netinst:subtlvs" +
            "/oc-netinst:segment-routing-algorithms/oc-netinst:state" +
            "/oc-netinst:algorithm" {
    deviate replace {
      type union {
        type uint8 {
          range "128..255";
        }
        type enumeration {
          enum SPF {
                    value 0;
                    description
                    "Shortest Path First (SPF) algorithm
                              based on link metric.  This is the
                              well-known shortest path algorithm as
                              computed by the IS-IS Decision process.
                              Consistent with the deployed practice
                              for link-state protocols, algorithm 0
                              permits any node to overwrite the SPF
                              path with a different path based on
                              local policy.";
          }
          enum STRICT_SPF {
                           value 1;
                           description
                           "Strict Shortest Path First (SPF)
                              algorithm based on link metric. The
                              algorithm is identical to algorithm 0
                              but algorithm 1 requires that all nodes
                              along the path will honor the SPF
                              routing decision. Local policy MUST NOT
                              alter the forwarding decision computed
                              by algorithm 1 at the node claiming to
                              support algorithm 1.";
          }
        }
      }
    }
  }
}
