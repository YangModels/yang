module arcos-mpls-ldp {

  yang-version "1.1";

  // namespace
  namespace "http://yang.arrcus.com/arcos/mpls/ldp";

  prefix "arc-mpls-ldp";

  // import some basic types
  import ietf-inet-types { prefix "inet"; }
  import openconfig-routing-policy { prefix "oc-rpol"; }
  import openconfig-interfaces { prefix "oc-if"; }
  import openconfig-mpls-ldp {prefix "oc-ldp"; }
  import arcos-common-types { prefix arc-common-types; }
  import ietf-yang-types {
    prefix "yang";
  }

  organization "Arrcus, Inc";

  contact
    "Email: eng@arrcus.com";

  description
    "This module lists the ldp related information";

  revision 2022-09-16 {
    description
      "Add reset count to hello adjacency and session state";
  }

  revision 2022-09-14 {
    description
      "Add uptime to hello adjacency and session state";
  }

  revision "2019-08-21" {
    description
      "Initial version";
  }

  grouping mpls-ldp-max-local-binding-config {
    description
      "Grouping containing maximum number of local binding configuration";

    container max-local-binding {
      description
        "Maximum number of local binding";

      container config {
        description
          "Configuration for maximum number of local binding";

        uses mpls-ldp-max-local-binding;
      }

      container state {
        config false;
        description
          "Operation data for the maximum number of local binding";

        uses mpls-ldp-max-local-binding;
      }
    }
  }

  grouping mpls-ldp-max-local-binding {
    description
      "Grouping containing maximum number of local binding";

    leaf maximum-local-binding {
      type uint32 {
        range "0..max";
      }
      description
        "Define the maximum number of local binding";
    }
  }

  grouping mpls-ldp-max-remote-binding-config {
    description
      "Grouping containing maximum number of remote binding configuration";

    container max-remote-binding {
      description
        "Maximum number of remote binding";

      container config {
        description
          "Configuration for maximum number of remote binding";

        uses mpls-ldp-max-remote-binding;
      }

      container state {
        config false;
        description
          "Operation data for the maximum number of remote binding";

        uses mpls-ldp-max-remote-binding;
      }
    }
  }

  grouping mpls-ldp-max-remote-binding {
    description
      "Grouping containing maximum number of remote binding";

    leaf maximum-remote-binding {
      type uint32 {
        range "0..max";
      }
      description
        "Define the maximum number of remote binding";
    }
  }

  grouping mpls-ldp-transport-address-config {
    description
      "Grouping containing interface-related attributes
       that can be configured for LDP.";

    container transport-address {
      description
        "Transport address configuration.";

      container config {
        description
          "Configuration for the transport address";

        uses mpls-ldp-transport-addresses;
      }

      container state {
        config false;
        description
          "Operation data for the tranport address.";

        uses mpls-ldp-transport-addresses;
      }
    }
  }

  grouping mpls-ldp-transport-addresses {
    description
      "Grouping containing transport address configuration.";

    leaf ipv4 {
      type inet:ip-address;
      description
        "Defines the transport address for Hello message and session
         on this interface.";
    }

    leaf ipv6 {
       type inet:ipv6-address;
       description
         "Defines the transport ipv6 address for Hello message and session
          on this interface.";
     }
  }

  grouping mpls-ldp-fec-filter {
    description
      "LDP FEC filtering";

    container fec-filter {
      description
        "LDP FEC filtering";

      container config {
        description
          "Configuration for FEC filtering";

        uses oc-rpol:apply-policy-export-config;
      }

      container state {
        config false;
        description
          "Operation data for FEC filtering";
        uses oc-rpol:apply-policy-export-config;
      }
    }
  }

  grouping mpls-ldp-sessions {
    description
      "LDP session information";

    container sessions {
      description
        "LDP Sessions";

      container ipv4 {
        config false;
        description
          "IPv4 LDP session information";

        uses mpls-ldp-sessions-v4;
      }

      container ipv6 {
        config false;
        description
          "IPv6 LDP session information";

        uses mpls-ldp-sessions-v6;
      }
    }
  }

  grouping mpls-ldp-sessions-v4 {
    description
      "IPv4 LDP session information";

    list session {
      config false;
      key "peer-address";

      description
        "List of IPv4 LDP sessions";

      leaf peer-address {
        type leafref {
          path "../state/peer-address";
        }
        description
          "reference to the peer-address data";
      }

      container state {
        description
          "Operational data for LDP session";

        uses mpls-ldp-session-state;
      }
    }
  }

  grouping mpls-ldp-sessions-v6 {
    description
      "IPv6 LDP session information";

    list session {
      config false;
      key "peer-address";

      description
        "List of IPv6 LDP sessions";

      leaf peer-address {
        type leafref {
          path "../state/peer-address";
        }
        description
          "reference to the peer-address data";
      }

      container state {
        description
          "Operational data for LDP session";

        uses mpls-ldp-session-state-v6;
      }
    }
  }

  grouping mpls-ldp-label-mapping {
    description
      "LDP Label Mapping";

    container label-mappings {
      description
        "LDP Label Mapping";

      container ipv4 {
        config false;
        description
          "IPv4 LDP Label Mapping";

        uses mpls-ldp-label-mapping-v4;
      }

      container ipv6 {
        config false;
        description
          "IPv6 LDP Label Mapping";

        uses mpls-ldp-label-mapping-v6;
      }
    }
  }

  grouping mpls-ldp-label-mapping-v4 {
    description
      "LDP Label Mapping";

    list label-mapping {
      config false;
      key "peer-address fec";

      description
        "List of Label Mapping";

      leaf peer-address {
        type leafref {
          path "../state/peer-address";
        }
        description
          "reference to the peer-address data";
      }

      leaf fec {
        type leafref {
          path "../state/fec";
        }
        description
          "reference to the fec data";
      }

      container state {
        description
          "Operational data of Label Mapping";

        uses mpls-ldp-label-mapping-state;
      }
    }
  }

  grouping mpls-ldp-label-mapping-v6 {
    description
      "LDP Label Mapping";

    list label-mapping {
      config false;
      key "peer-address fec";

      description
        "List of Label Mapping";

      leaf peer-address {
        type leafref {
          path "../state/peer-address";
        }
        description
          "reference to the peer-address data";
      }

      leaf fec {
        type leafref {
          path "../state/fec";
        }
        description
          "reference to the fec data";
      }

      container state {
        description
          "Operational data of Label Mapping";

        uses mpls-ldp-label-mapping-state-v6;
      }
    }
  }

  grouping mpls-ldp-hello-adjacency {
    description
      "LDP Hello Adjacency";

    container hello-adjacencies {
      description
        "LDP Hello Adjacency";

      container ipv4 {
        config false;
        description
          "IPv4 LDP hHello Adjacency";

        uses mpls-ldp-hello-adjacency-v4;
      }

      container ipv6 {
        config false;
        description
          "IPv6 LDP hHello Adjacency";

        uses mpls-ldp-hello-adjacency-v6;
      }
    }
  }

  grouping mpls-ldp-hello-adjacency-v4 {
    description
      "LDP Hello Adjacency";

    list hello-adjacency {
      config false;
      key "peer-address";

      description
        "list of Hello Adjacency";

      leaf peer-address {
        type leafref {
          path "../state/peer-address";
        }
        description
          "reference to the peer-address data";
      }

      container state {
        description
          "Operational Data of Hello Adjacency";

        uses mpls-ldp-hello-adjacency-state;
      }
    }
  }

  grouping mpls-ldp-hello-adjacency-v6 {
    description
      "LDP Hello Adjacency";

    list hello-adjacency {
      config false;
      key "peer-address";

      description
        "list of Hello Adjacency";

      leaf peer-address {
        type leafref {
          path "../state/peer-address";
        }
        description
          "reference to the peer-address data";
      }

      container state {
        description
          "Operational Data of Hello Adjacency";

        uses mpls-ldp-hello-adjacency-state-v6;
      }
    }
  }

  grouping mpls-ldp-session-state {
    description
      "Set of LDP session related state attribute";

    leaf peer-address {
      description
        "Peer address for a particular LDP session";
      type inet:ip-address;
    }

    leaf local-address {
      description
        "Local address for a particular LDP session";
      type inet:ip-address;
    }

    leaf session-state {
      description
        "Current state for a particular LDP session";
      type string;
    }

    leaf session-role {
      description
        "Session role for a particular LDP session";
      type string;
    }

    leaf keepalive-timeout {
      description
        "Keepalive timeout for a particular LDP session";
      type uint16;
    }

    leaf keepalive-interval {
      description
        "Keepalive interval for a particular LDP session";
      type uint16;
    }

    leaf local-lsr-id {
      description
        "Local LSR-ID for a particular LDP session";
      type inet:ip-address;
    }

    leaf local-label-space-id {
      description
        "Local Label Space ID for a particular LDP session";
      type uint16;
    }

    leaf remote-lsr-id {
      description
        "Remote LSR-ID for a particular LDP session";
      type inet:ip-address;
    }

    leaf remote-label-space-id {
      description
        "Remote Label Space ID for a particular LDP session";
      type uint16;
    }

    leaf uptime {
      type string;
      description
        "Length of time since a particular session was established in " +
        "ddd:hh:mm:ss format";
    }

    leaf reset-count {
      type yang:zero-based-counter32;
      description
        "Number of times a particular session has transitioned from an " +
        "established state to the non existent state";
    }
  }

  grouping mpls-ldp-session-state-v6 {
    description
      "Set of LDP session related state attribute";

    leaf peer-address {
      description
        "Peer address for a particular LDP session";
      type inet:ipv6-address;
    }

    leaf local-address {
      description
        "Local address for a particular LDP session";
      type inet:ipv6-address;
    }

    leaf session-state {
      description
        "Current state for a particular LDP session";
      type string;
    }

    leaf session-role {
      description
        "Session role for a particular LDP session";
      type string;
    }

    leaf keepalive-timeout {
      description
        "Keepalive timeout for a particular LDP session";
      type uint16;
    }

    leaf keepalive-interval {
      description
        "Keepalive interval for a particular LDP session";
      type uint16;
    }

    leaf local-lsr-id {
      description
        "Local LSR-ID for a particular LDP session";
      type inet:ip-address;
    }

    leaf local-label-space-id {
      description
        "Local Label Space ID for a particular LDP session";
      type uint16;
    }

    leaf remote-lsr-id {
      description
        "Remote LSR-ID for a particular LDP session";
      type inet:ip-address;
    }

    leaf remote-label-space-id {
      description
        "Remote Label Space ID for a particular LDP session";
      type uint16;
    }

    leaf uptime {
      type string;
      description
        "Length of time since a particular session was established in " +
        "ddd:hh:mm:ss format";
    }

    leaf reset-count {
      type yang:zero-based-counter32;
      description
        "Number of times a particular session has transitioned from an " +
        "established state to the non existent state";
    }
  }

  grouping mpls-ldp-label-mapping-state {
    description
      "Set of LDP Label Mapping related state attribute";

    leaf peer-address {
      description
        "Peer address for a particular LDP session";
      type inet:ip-address;
    }

    leaf fec {
      description
        "FEC";
      type inet:ip-prefix;
    }

    leaf upstream-binding {
      description 
        "Upstream label binding for a particular FEC";
      type uint32;
    }

    leaf downstream-binding {
      description
        "Downstream label binding for a particular FEC";
      type uint32;
    }
  }

  grouping mpls-ldp-label-mapping-state-v6 {
    description
      "Set of LDP Label Mapping related state attribute";

    leaf peer-address {
      description
        "Peer address for a particular LDP session";
      type inet:ipv6-address;
    }

    leaf fec {
      description
        "FEC";
      type inet:ipv6-prefix;
    }

    leaf upstream-binding {
      description 
        "Upstream label binding for a particular FEC";
      type uint32;
    }

    leaf downstream-binding {
      description
        "Downstream label binding for a particular FEC";
      type uint32;
    }
  }

  grouping mpls-ldp-hello-adjacency-state {
    description
      "Set of hello-adjacency related state attribute";

    leaf peer-address {
      description
        "LDP Peer address";
      type inet:ip-address;
    }

    leaf version {
      description
        "LDP version";
      type uint16;
    }

    leaf lsr-id {
      description
        "LDP Peer LSR ID";
      type inet:ip-address;
    }

    leaf label-space-id {
      description
        "LDP Peer Label Space ID";
      type uint16;
    }

    leaf transport-address {
      description
        "LDP Hello Transport Address";
      type inet:ip-address;
    }

    leaf source-address {
      description
        "LDP Hello Srouce Address";
      type inet:ip-address;
    }

    leaf holdtime {
      description
        "LDP Hello Holdtime";
      type uint32;
    }

    leaf interface {
      description
        "Interface on this hello adjacency";
      type string;
    }

    leaf uptime {
      type string;
      description
        "Length of time since the hello adjacency was established in " +
        "ddd:hh:mm:ss format";
    }

    leaf reset-count {
      type yang:zero-based-counter32;
      description
        "Number of times this hello adjacency has been recreated after " +
        "initial discovery";
    }
  }

  grouping mpls-ldp-hello-adjacency-state-v6 {
    description
      "Set of hello-adjacency related state attribute";

    leaf peer-address {
      description
        "LDP Peer address";
      type inet:ipv6-address;
    }

    leaf version {
      description
        "LDP version";
      type uint16;
    }

    leaf lsr-id {
      description
        "LDP Peer LSR ID";
      type inet:ip-address;
    }

    leaf label-space-id {
      description
        "LDP Peer Label Space ID";
      type uint16;
    }

    leaf transport-address {
      description
        "LDP Hello Transport Address";
      type inet:ipv6-address;
    }

    leaf source-address {
      description
        "LDP Hello Srouce Address";
      type inet:ipv6-address;
    }

    leaf holdtime {
      description
        "LDP Hello Holdtime";
      type uint32;
    }

    leaf interface {
      description
        "Interface on this hello adjacency";
      type string;
    }

    leaf uptime {
      type string;
      description
        "Length of time since the hello adjacency was established in " +
        "ddd:hh:mm:ss format";
    }

    leaf reset-count {
      type yang:zero-based-counter32;
      description
        "Number of times this hello adjacency has been recreated after " +
        "initial discovery";
    }
  }

  rpc clear-ldp-neighbor {
    description
      "Clear one or all LDP sessions.";

    input {
      leaf address-family {
        mandatory true;
        description
          "Address family";

        type oc-ldp:mpls-ldp-afi;
      }

      leaf address {
        mandatory true;
        description
          "All LDP sessions or the address of one LDP session.";
        type union {
          type enumeration {
            enum ALL {
              description
                "All LDP sessions";
            }
          }
          type inet:ip-address;
        }
      }
    }
  }

  rpc clear-ldp-adjacency {
    description
      "Clear one or all LDP adjacencies.";

    input {
      leaf interface {
        mandatory true;
        description
          "LDP adjacencies on all interfaces  or LDP adjacency on a specific interface.";
        type union {
          type enumeration {
            enum ALL {
              description
                "All LDP adjacencies";
            }
          }
          type oc-if:interface-id;
        }
      }
    }
  }

}
