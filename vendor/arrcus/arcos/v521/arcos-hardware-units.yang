submodule arcos-hardware-units {
  yang-version 1.1;

  belongs-to arcos-hardware {
    prefix arc-hw;
  }

  import ietf-yang-types {
    prefix yang;
  }

  grouping hardware-units {
    description
      "View hardware resources";

    list unit-entry {
      config false;
      description
        "List of forwarding units";

      key "unit-id";

      leaf unit-id {
        type uint32;
        description "Forwarding unit id";
      }

      leaf unit-descr {
        type string;
        description "Forwarding unit description";
      }

      container resources {
        config false;
        description
          "List of resources in a forwarding init. A resource has
           a maximum number of entries and may be shared by one or
           more features";

        list resource-entry {
          description
            "A resource entry";
          key "name";

          leaf name {
            type string;
            description "Name of the resource";
          }

          leaf raw-used {
            type uint64;
            description "Number of raw resource entries in use";
          }

          leaf raw-free {
            type uint64;
            description "Number of raw resource entries free";
          }

          container feature {
            list feature-entry {
              key "name";

              leaf name {
                type string;
                description "Feature name";
              }

              leaf objects-allocated {
                type uint64;
                description "Number of objects allocated by this feature.
                  An object may use one or more raw resource
                  entries. For some features this is a best effort estimate";
              }

              leaf objects-failed {
                type yang:zero-based-counter64;
                description "Number of objects that have failed due to
                  unavailable hardware resources. An object may use one or more
                  hardware resource entry.";
              }

              leaf high-watermark {
                type uint64;
                description "High watermark of the number of objects allocated
                  by this feature";
              }

              leaf high-watermark-time {
                type yang:date-and-time;
                description "Date and time the high watermark was hit";
              }

              leaf estimated-free {
                type uint64;
                description "Number of objects that can be allocated by this
                  feature until it runs out of resources. In the case where the
                  the resource is shared between one or more features, this
                  number may go up or down if another feature uses up resource
                  entries. For some features this is a best effort estimate";
              }

              leaf errors {
                type uint64;
                description "Count of the number of times that the feature
                  failed to allocate a logical entry";
              }
            }
          }
        }
      }

      container indexers {
        config false;
        list indexer-entry {
          config false;

          key "name";

          leaf name {
            type string;
            description "Indexer name";
          }

          leaf type {
            type string;
            description "Type of the indexer";
          }

          leaf start-index {
            type uint32;
            description "Starting index";
          }

          leaf count {
            type uint32;
            description "Maximum number of entries ";
          }

          leaf used {
            type uint32;
            description "Number of entries in use";
          }

          leaf hold-count {
            type uint32;
            description "Hold count";
          }
        }
      }
    }
  }
}
