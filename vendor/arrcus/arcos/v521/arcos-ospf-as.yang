submodule arcos-ospf-as {

  yang-version "1.1";

  belongs-to arcos-ospf {
    prefix "arc-ospf";
  }

  import ietf-yang-types { prefix "yang"; }
  import arcos-ospf-types { prefix "arc-ospf-types"; }

  // Include submodules
  include arcos-ospf-common;
  include arcos-ospf-statistics;
  include arcos-ospf-spf;

  description
    "This submodule provides OSPF configuration and operational
    state parameters that have Autonomous System scope";

  grouping ospf-as-scope-structure {
    description
      "Top level structural grouping for OSPF AS scope parameters";

    container as-scope {
      description
        "Configuration and operational state parameters for settings
        that are AS scope in the OSPF instance";

      container spf {
        description
          "This container defines AS scope SPF state.";

        container state {
          config false;
          description
            "Operational state of AS scope SPF computation";

          uses ospf-spf-state;
        }

        container last-spf-computation {
          config false;
          description
            "Operational state of the most recent AS scope SPF computation";

          uses ospf-spf-comp-state;
        }
      }

      container statistics {
        config false;
        description
          "AS scope statistics";

        uses ospf-as-scope-lsa-statistics-structure;
        uses ospf-comp-spf-statistics-structure;
      }
    }
  }
}
