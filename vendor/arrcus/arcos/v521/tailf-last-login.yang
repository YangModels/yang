module tailf-last-login {
  namespace "http://tail-f.com/yang/last-login";
  prefix last;

  tailf:ignore-if-no-cdb-oper;

  import ietf-inet-types         { prefix inet;  }
  import ietf-yang-types         { prefix yang;  }
  import tailf-common            { prefix tailf; }
  import ietf-netconf-monitoring { prefix ncm;   }

  organization "Tail-f Systems";

  description
    "This module defines a list representing the last logged in users.

     Copyright 2019 Cisco Systems, Inc.
     All rights reserved.
     Permission is hereby granted to redistribute this file without
     modification.";

  revision 2019-11-21 {
    description
      "Initial revision.

       Released as part of ConfD-7.4 and NSO-5.4.";
  }


  grouping login-data {

    leaf login-time {
      type yang:date-and-time;
      description
        "Time at the server at which the session was established.";
    }

    leaf authenticating-host {
      type inet:host;
      description
        "Host identifier of the authenticating host.
         The value returned is implementation specific (e.g., hostname,
         IPv4 address, IPv6 address)";
    }

    leaf client-host {
      type inet:host;
      description
        "Host identifier of the client. The value
         returned is implementation specific (e.g., hostname,
         IPv4 address, IPv6 address)";
    }

    leaf transport {
      type identityref {
        base ncm:transport;
      }
      description
        "Identifies the transport for each session, e.g.,
         'netconf-ssh', 'restconf', 'cli', etc.";
    }

  } // end grouping login-data


  grouping login-data-and-failed {

    uses login-data;

    leaf num-of-failed-logins {
      type uint32;
      description
        "Number of failed login attempts since the last successful login.";
    }

  } // end grouping login-data-and-failed


  container last-logins {
    config false;
    tailf:info "Display last logged in users";
    description
      "The last-logins container is the root of the last-login data model.

       The list contains the last time a user was successfully authenticated,
       the name of the authenticating host, the name or address of the
       location from which the user last received service, and the type
       of service used.

       A representative message might be:

           User jblow last logged in 2008-Dec-13, to foo.cisco.com,
              from bar.cisco.com using netconf-ssh

       The list also keeps track of the number of failed login attempts
       since the last successful login, together with the information
       normally given for a successful attempt.
       Examples of how this could be presented are:

           User jblow failed to log in 5 times!

           Most recent failure 2008-Dec-13, to foo.cisco.com,
             from bar.cisco.com using HTTPS

      ";

    list user {
      key name;
      description
        "All users that has successfully logged into the system are
         reported in this list.";

      leaf name  {
        type string;
        description
          "The name of the user is the client identity.";
      }

      list login {
        ordered-by user;
        key login-time;

        uses login-data-and-failed;

        container last-failed {
          presence "last-failed";
          description
            "Login data for the last failed login.

             This container only exist if the 'num-of-failed-logins' > 0.
            ";
          uses login-data;
        }
      }
    }
  }
}
