module tailf-netconf-rollback {
  yang-version 1.1;
  namespace "http://tail-f.com/ns/netconf/rollback";
  prefix netconf-rollback;

  import ietf-netconf {
    prefix nc;
  }
  import tailf-netconf-transactions {
    prefix tr;
  }

  organization "Tail-f Systems";

  description
    "Extends the NETCONF server with rollback specific meta data.

     Copyright 2018 Cisco Systems, Inc.
     All rights reserved.
     Permission is hereby granted to redistribute this file without
     modification.";

  revision 2018-01-12 {
    description
      "Initial revision.";
  }

  grouping rollback-meta-data {
    leaf rollback-label {
      type string;
    }
    leaf rollback-comment {
      type string;
    }
  }

  augment "/nc:edit-config/nc:input" {
    when "nc:target/nc:running";
    uses rollback-meta-data;
  }

  augment "/nc:commit/nc:input" {
    if-feature nc:candidate;
    uses rollback-meta-data;
  }

  augment "/tr:prepare-transaction/tr:input" {
    uses rollback-meta-data;
  }
}
