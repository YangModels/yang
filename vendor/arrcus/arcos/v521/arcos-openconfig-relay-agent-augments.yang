module arcos-openconfig-relay-agent-augments {
  yang-version 1.1;
  namespace "http://yang.arrcus.com/arcos/openconfig/relay-agent/augments";
  prefix arc-oc-relay-aug;

  import ietf-inet-types {
    prefix inet;
  }

  import ietf-yang-types {
    prefix yang;
  }

  import openconfig-yang-types {
    prefix oc-yang;
  }

  import openconfig-relay-agent {
    prefix oc-relay;
  }

  import openconfig-interfaces {
    prefix oc-if;
  }

  organization
    "Arrcus, Inc.";

  contact
    "Arrcus, Inc.
     2077 Gateway Place
     Suite 400
     San Jose, CA 95110

     E-mail: yang-support@arrcus.com";

  description
    "This module defines ArcOS augments to the
     OpenConfig relay-agent module.

     Copyright (c) 2022 by Arrcus, Inc.
     All rights reserved.";

  revision 2022-07-21 {
    description
      "Added Option-82 Circuit ID format support";
  }

  grouping relay-agent-ipv6-helper-config {
    description
      "DHCPv6 server configuration for relay";

    container servers {
      description
        "Enclosing container for list of DHCPv6 servers";

      list server {
        key "name";
        unique "helper-address helper-interface";
        max-elements 64;
        description
          "DHCPv6 server to relay towards";

        leaf name {
          type string {
            length "1..64";
          }
          description "Name of this server entry";
        }

        leaf helper-address {
          mandatory true;
          type inet:ipv6-address;
          description "IPv6 address of DHCPv6 server to relay requests towards";
        }

        leaf helper-interface {
          mandatory true;
          type oc-if:base-interface-ref;
          description
            "The interface name to forward DHCPv6 requests out to reach this server";
        }
      }
    }
  }

  grouping relay-agent-dhcp-global-counters {
    description
      "DHCP relay agent global counters grouping";

    container counters {
      description
        "DHCP relay agent global counters";

      config false;
      container state {

        leaf received-requests {
          type oc-yang:counter64;
          description
            "Number of DHCP Requests received from a client";
        }
        leaf received-responses {
          type oc-yang:counter64;
          description
            "Number of DHCP Responses received from a server";
        }
        leaf relayed-requests {
          type oc-yang:counter64;
          description
            "Number of DHCP Requests relayed to a server";
        }
        leaf relayed-responses {
          type oc-yang:counter64;
          description
            "Number of DHCP Responses relayed to a client";
        }
        leaf total-drops {
          type oc-yang:counter64;
          description
            "Total Number of DHCP packets dropped";
        }
        leaf last-clear {
          type yang:date-and-time;
          description
            "Indicates the last time the counters were
             cleared.";
        }
      }
    }
  }


  grouping relay-agent-dhcp-global-drop-counters {
    description
      "DHCP relay agent global drop counters grouping";

    container drop-counters {
      description
        "DHCP relay agent global drop counters";

      config false;
      container state {

        leaf bad-giaddr {
          type oc-yang:counter64;
          description
            "Number of DHCP Responses with a giaddr that doesn't
             match any DHCP relay enabled interface";
        }
        leaf request-send-failure {
          type oc-yang:counter64;
          description
            "Number of DHCP Requests that failed to be sent to
             a server";
        }
        leaf response-send-failure {
          type oc-yang:counter64;
          description
            "Number of DHCP Responses that failed to be sent to
             a client";
        }
        leaf agent-option-missing {
          type oc-yang:counter64;
          description
            "Number of DHCP Responses received without an agent
             option, when requests are sent with one";
        }
        leaf agent-option-corrupt {
          type oc-yang:counter64;
          description
            "Number of DHCP Responses received with a corrupt agent
             option, when requests are sent with an agent option";
        }
        leaf circuit-id-missing {
          type oc-yang:counter64;
          description
            "Number of DHCP Responses with a an agent option that
             doesn't contain a circuit ID suboption, when requests
             are sent with an agent option";
        }
        leaf no-circuit-id-match {
          type oc-yang:counter64;
          description
            "Number of DHCP Responses with an agent option circuit
             ID that doesn't match any DHCP relay enabled
             interface's circuit ID";
        }
        leaf agent-option-add-error {
          type oc-yang:counter64;
          description
            "Number of DHCP Requests for which the agent option
             could not be added due to length";
        }
        leaf circuit-id-exists {
          type oc-yang:counter64;
          description
            "Number of DHCP Requests received that already contain
             an agent option with a circuit ID";
        }
        leaf parse-error {
          type oc-yang:counter64;
          description
            "Error in parsing. For example, options exceed the
             length of the packet";
        }
      }
    }
  }
 
  grouping relay-agent-dhcp-interface-counters {
    description
      "DHCP relay agent per interface counters grouping";

    container counters {
      description
        "DHCP relay agent per interface counters";

      config false;

      container state {

        leaf received-requests {
          type oc-yang:counter64;
          description
            "Number of DHCP Requests received from a client on
             the interface";
        }
        leaf relayed-requests {
          type oc-yang:counter64;
          description
            "Number of DHCP Requests from the interface that were
             relayed to a server";
        }
        leaf relayed-responses {
          type oc-yang:counter64;
          description
            "Number of DHCP Responses relayed to a client on the
             interface";
        }
        leaf drops {
          type oc-yang:counter64;
          description
            "Number of DHCP Requests from the interface that were
             dropped";
        }
        leaf last-clear {
          type yang:date-and-time;
          description
            "Indicates the last time the counters were
             cleared.";
        }
      }
    }
  }

  typedef circuit-id-formats {
    type enumeration {
      enum HOSTNAME_PORT {
        description
          "Generate the Circuit ID based on the relay agent's hostname
          and port the request arrived on";
      }
      enum PORT_VLAN {
        description
          "Generate the Circuit ID based on the port and VLAN ID
          the request arrived on";
      }
    }
    description
      "Format of the Agent Information option Circuit-ID generated";
  }

  grouping agent-information-ipv4-interface-config-ext {
    description
      "Extended configuration data for DCHP relay agent information option
      on IPv4 interfaces";

    leaf circuit-id-format {
      type circuit-id-formats;
      must "not(../oc-relay:circuit-id)" {
        error-message "Only one of circuit-id or circuit-id-format may be configured";
      }
      description
        "When configured for an interface, the Circuit ID of relayed packets
        will contain the chosen format";
    }
  }

  grouping agent-information-ipv4-common-config-ext {
    description
      "Extended common configuration data for IPv4 DCHP relay agent
      information option";

    leaf circuit-id-format {
      type circuit-id-formats;
      description
        "When configured the Circuit ID of relayed packets will contain the
        chosen format, unless overridden at the interface level";
    }
  }

  augment "/oc-relay:relay-agent/oc-relay:dhcp/oc-relay:config" {
    leaf-list helper-address {
      max-elements 16;
      type inet:ip-address;
      description
        "IPv4 address of DHCP server to relay requests towards";
    }
  }

  augment "/oc-relay:relay-agent/oc-relay:dhcp/oc-relay:state" {
    leaf-list helper-address {
      type inet:ip-address;
      description
        "IPv4 address of DHCP server to relay requests towards";
    }
  }

  augment "/oc-relay:relay-agent/oc-relay:dhcp" {

    uses relay-agent-dhcp-global-counters;
    uses relay-agent-dhcp-global-drop-counters;
  }

  augment "/oc-relay:relay-agent/oc-relay:dhcpv6/oc-relay:config" {
    uses relay-agent-ipv6-helper-config;
  }

  augment "/oc-relay:relay-agent/oc-relay:dhcpv6/oc-relay:state" {
    uses relay-agent-ipv6-helper-config;
  }

  augment "/oc-relay:relay-agent/oc-relay:dhcp/oc-relay:interfaces" +
          "/oc-relay:interface" {
    uses relay-agent-dhcp-interface-counters;
  }
  
  augment "/oc-relay:relay-agent/oc-relay:dhcp/oc-relay:interfaces" +
          "/oc-relay:interface/oc-relay:agent-information-option" +
          "/oc-relay:config" {
    uses agent-information-ipv4-interface-config-ext;
  }

  augment "/oc-relay:relay-agent/oc-relay:dhcp/oc-relay:interfaces" +
          "/oc-relay:interface/oc-relay:agent-information-option" +
          "/oc-relay:state" {
    uses agent-information-ipv4-interface-config-ext;
  }

  augment "/oc-relay:relay-agent/oc-relay:dhcp" +
          "/oc-relay:agent-information-option/oc-relay:config" {
    uses agent-information-ipv4-common-config-ext;
  }

  augment "/oc-relay:relay-agent/oc-relay:dhcp" +
          "/oc-relay:agent-information-option/oc-relay:state" {
    uses agent-information-ipv4-common-config-ext;
  }

}
