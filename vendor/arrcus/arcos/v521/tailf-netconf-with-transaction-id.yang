module tailf-netconf-with-transaction-id {
  yang-version 1.1;
  namespace "http://tail-f.com/ns/netconf/with-transaction-id";
  prefix wtxid;

  import ietf-netconf {
    prefix nc;
  }

  import tailf-netconf-transactions {
    prefix tr;
  }

  description
    "This module adds a parameter 'with-transaction-id' to the
     following rpcs:

       o  edit-config
       o  copy-config
       o  commit
       o  commit-transaction

     This parameter lets the client request that the datastore's
     transaction id is returned in the reply to the request.

     This can be used to avoid a round-trip, which is otherwise needed
     to get the transaction id from

       /netconf-state/datastores/datastore/transaction-id

     The transaction id is only availabe for the running configuration
     datastore.

     Copyright 2018 Cisco Systems, Inc.
     All rights reserved.
     Permission is hereby granted to redistribute this file without
     modification.";

  revision 2018-11-23 {
    description
      "Initial revision.";
  }

  grouping with-transaction-id-params {
    leaf with-transaction-id {
      type empty;
    }
  }
  grouping with-transaction-id-reply {
    leaf transaction-id {
      type string;
    }
  }

  /*
   * RPC augmentations
   */
  augment '/nc:edit-config/nc:input' {
    uses with-transaction-id-params;
  }
  augment '/nc:edit-config/nc:output' {
    uses with-transaction-id-reply;
  }

  augment '/nc:copy-config/nc:input' {
    uses with-transaction-id-params;
  }
  augment '/nc:copy-config/nc:output' {
    uses with-transaction-id-reply;
  }

  augment '/nc:commit/nc:input' {
    uses with-transaction-id-params;
  }
  augment '/nc:commit/nc:output' {
    uses with-transaction-id-reply;
  }

  augment '/tr:commit-transaction/tr:input' {
    uses with-transaction-id-params;
  }
  augment '/tr:commit-transaction/tr:output' {
    uses with-transaction-id-reply;
  }
}
