module arcos-hardware-platform-types {
  yang-version 1.1;
  namespace "http://yang.arrcus.com/arcos/hardware/platform/types";
  prefix arc-hw-platform-types;

  typedef MMU_QUEUE_ALPHA_VALUE {
    type enumeration {
      enum 1/128;
      enum 1/64;
      enum 1/32;
      enum 1/16;
      enum 1/8;
      enum 1/4;
      enum 1/2;
      enum 1;
      enum 2;
      enum 4;
      enum 8;
    }
  }

  identity SWITCH_FORWARDING_MODE {
    description "Base type for switch forwarding modes";
  }

  identity STORE_AND_FORWARD {
    base SWITCH_FORWARDING_MODE;
    description "Store and forward mode";
  }

  identity CUT_THROUGH {
    base SWITCH_FORWARDING_MODE;
    description "Cut through forwarding mode";
  }

  identity BUFFER_STATS_MODE {
    description "Base type for buffer stats modes";
  }

  identity BUFFER_STATS_MODE_NONE {
    base BUFFER_STATS_MODE;
    description "Buffer stats collection is disabled";
  }

  identity BUFFER_STATS_MODE_PEAK {
    base BUFFER_STATS_MODE;
    description "Buffer stats collected reflect peak usage";
  }

  identity BUFFER_STATS_MODE_PEAK_RESET {
    base BUFFER_STATS_MODE;
    description "Buffer stats collected reflect peak usage and reset the stats after every show";
  }

  typedef ECMP_MODE {
    type enumeration {
      enum RESILIENT_MODE {
        value 1;
      }
      enum DLB_MODE {
        value 2;
      }
    }
  }

  typedef  inact-int-uint32 {
    type uint32 {
      range "16..32767";
     }
  }
}
