module arcos-openconfig-defined-sets-deviations {
  yang-version 1.1;
  namespace "http://yang.arrcus.com/arcos/openconfig/defined-sets/deviations";
  prefix arc-oc-sets-dev;

  import openconfig-defined-sets {
    prefix oc-sets;
  }

  import ietf-inet-types {
    prefix ietf-inet;
  } 

  deviation "/oc-sets:defined-sets/oc-sets:ipv4-prefix-sets/oc-sets:ipv4-prefix-set" + 
            "/oc-sets:config/oc-sets:prefix" {
    deviate replace {
      type ietf-inet:ipv4-prefix;
    }
    description "Use ietf-inet types instead of oc-inet";
  }

  deviation "/oc-sets:defined-sets/oc-sets:ipv4-prefix-sets/oc-sets:ipv4-prefix-set" + 
            "/oc-sets:state/oc-sets:prefix" {
    deviate replace {
      type ietf-inet:ipv4-prefix;
    }
    description "Use ietf-inet types instead of oc-inet";
  }

  deviation "/oc-sets:defined-sets/oc-sets:ipv6-prefix-sets/oc-sets:ipv6-prefix-set" + 
            "/oc-sets:config/oc-sets:prefix" {
    deviate replace {
      type ietf-inet:ipv6-prefix;
    }
    description "Use ietf-inet types instead of oc-inet";
  }

  deviation "/oc-sets:defined-sets/oc-sets:ipv6-prefix-sets/oc-sets:ipv6-prefix-set" + 
            "/oc-sets:state/oc-sets:prefix" {
    deviate replace {
      type ietf-inet:ipv6-prefix;
    }
    description "Use ietf-inet types instead of oc-inet";
  }
}
