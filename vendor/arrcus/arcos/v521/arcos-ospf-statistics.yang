submodule arcos-ospf-statistics {

  yang-version "1.1";

  belongs-to arcos-ospf {
    prefix "arc-ospf";
  }

  import ietf-yang-types { prefix "yang"; }
  import openconfig-types { prefix "oc-types"; }
  import arcos-ospf-types { prefix "arc-ospf-types"; }
  import arcos-system-types { prefix arc-sys-types; }

  description
    "This submodule provides OSPF statistics related to LSA, SPF,
    RIB and packets.";


  /*
   * Packet Statistics
   */
  grouping ospf-pkt-tx-common-statistics {
    description
      "This grouping defines common packet transmit statistics";

    leaf total {
      type uint64;
      description
        "Total number of packets sent";
    }

    leaf errors {
      type uint64;
      description
        "Number of errors during packet send";
    }
  }

  grouping ospf-pkt-tx-type-statistics {
    description
      "This grouping defines per-type packet transmit statistics";

    leaf total {
      type uint64;
      description
        "Total number of packets sent";
    }

    leaf retransmits {
      type uint64;
      description
        "Number of retransmits";
    }

    leaf errors {
      type uint64;
      description
        "Number of errors during packet send";
    }

    leaf errors-socket {
      type uint64;
      description
        "Number of socket write errors";
    }

    leaf lsas {
      type uint64;
      description
        "Number of LSAs sent";
    }

    leaf retransmits-lsas {
      type uint64;
      description
        "Number of LSAs sent in retransmit packets";
    }
  }

  grouping ospf-pkt-tx-statistics {
    description
      "This grouping defines packet transmit statistics";

    container send {
      description
        "Packet send statistics";

      container cumulative {
        description
          "Total number of packets sent";

        uses ospf-pkt-tx-common-statistics;
      }

      container hello {
        description
          "Total number of HELLO packets sent";

        uses ospf-pkt-tx-type-statistics;
      }

      container dd {
        description
          "Total number of DD packets sent";

        uses ospf-pkt-tx-type-statistics;
      }

      container ls-req {
        description
          "Total number of LS-REQ packets sent";

        uses ospf-pkt-tx-type-statistics;
      }

      container ls-upd {
        description
          "Total number of LS-UPD packets sent";

        uses ospf-pkt-tx-type-statistics;

        leaf lsas-in-maintenance {
          type uint64;
          description
            "Number of in-maintenance LSAs sent";
        }

        leaf retransmits-lsas-in-maintenance {
          type uint64;
          description
            "Number of in-maintenance LSAs sent in retransmit packets";
        }
      }

      container ls-ack {
        description
          "Total number of LS-ACK packets sent";

        uses ospf-pkt-tx-type-statistics;
      }
    }
  }

  grouping ospf-pkt-rx-common-statistics {
    description
      "This grouping defines common packet receive statistics";

    leaf total {
      type uint64;
      description
        "Total number of packets received";
    }

    leaf drops {
      type uint64;
      description
        "Number of non-error packets dropped";
    }

    leaf errors {
      type uint64;
      description
        "Number of packets that encountered errors";
    }

    leaf errors-memory {
      type uint64;
      description
        "Number of packets that encountered memory allocation errors";
    }

    leaf errors-header {
      type uint64;
      description
        "Number of packets that encountered packet header errors";
    }

    leaf errors-auth {
      type uint64;
      description
        "Number of packets that encountered authentication errors";
    }
  }

  grouping ospf-pkt-rx-type-statistics {
    description
      "This grouping defines per-type packet receive statistics";

    leaf total {
      type uint64;
      description
        "Total number of packets received";
    }

    leaf drops {
      type uint64;
      description
        "Number of non-error packets dropped";
    }

    leaf errors {
      type uint64;
      description
        "Number of packets that encountered errors";
    }

    leaf lsas {
      type uint64;
      description
        "Number of LSAs received";
    }

    leaf lsas-ignored {
      type uint64;
      description
        "Number of LSAs received that were ignored";
    }

    leaf lsas-errors {
      type uint64;
      description
        "Number of LSAs received that encountered errors";
    }
  }

  grouping ospf-pkt-rx-statistics {
    description
      "This grouping defines packet receive statistics";

    container receive {
      description
        "Packet receive statistics";

      container cumulative {
        description
          "Total number of packets received";

        uses ospf-pkt-rx-common-statistics;
      }

      container hello {
        description
          "Total number of HELLO packets received";

        uses ospf-pkt-rx-type-statistics;
      }

      container dd {
        description
          "Total number of DD packets received";

        uses ospf-pkt-rx-type-statistics;

        leaf duplicates {
          type uint64;
          description
            "Number of duplicate DD packets";
        }
      }

      container ls-req {
        description
          "Total number of LS-REQ packets received";

        uses ospf-pkt-rx-type-statistics;
      }

      container ls-upd {
        description
          "Total number of LS-UPD packets received";

        uses ospf-pkt-rx-type-statistics;

        leaf lsas-ignored-limit {
          type uint64;
          description
            "Number of LSAs received that were ignored due to max-lsa limit";
        }

        leaf errors-memory {
          type uint64;
          description
            "Number of memory allocation errors";
        }
      }

      container ls-ack {
        description
          "Total number of LS-ACK packets received";

        uses ospf-pkt-rx-type-statistics;
      }
    }
  }

  grouping ospf-pkt-statistics-structure {
    description
      "This grouping defines packet statistics";

    container packet {
      description
        "Packet statistics";

      uses ospf-pkt-tx-statistics;
      uses ospf-pkt-rx-statistics;
    }
  }


  /*
   * OSPF LSA Statistics
   */
  grouping ospf-lsa-type-statistics {
    description
      "This grouping defines statistics related to one or all LSA Types.";

    leaf lsas {
      type uint32;
      description
        "Number of LSAs";
    }

    leaf lsas-in-maintenance {
      type uint32;
      description
        "Number of LSAs in maintenance-mode";
    }

    leaf creations {
      type uint64;
      description
        "Number of LSA creations";
    }

    leaf updates {
      type uint64;
      description
        "Number of LSA updates";
    }

    leaf maxage {
      type uint64;
      description
        "Number of LSA maxagings";
    }

    leaf deletions {
      type uint64;
      description
        "Number of LSA deletions";
    }

    leaf origination-changes {
      type uint64;
      description
        "Number of LSAs that changed origination between self and remote";
    }

    leaf errors {
      type uint64;
      description
        "Number of errors encountered";
    }

    leaf errors-memory {
      type uint64;
      description
        "Number of LSA memory allocation errors";
    }
  }

  grouping ospf-interface-lsa-type-statistics {
    description
      "This grouping defines statistics related to Interface LSDB.";

    container cumulative {
      description
        "LSA statistics across types";

      leaf lsas {
        type uint32;
        description
          "Number of LSAs of all types";
      }

      leaf lsas-in-maintenance {
        type uint32;
        description
          "Number of LSAs in maintenance-mode";
      }
    }

    container link-lsa {
      description
        "Link LSA statistics";

      uses ospf-lsa-type-statistics;
    }
  }

  grouping ospf-interface-lsa-statistics-structure {
    description
      "This grouping defines statistics related to Interface LSDB.";

    container lsa {
      description
        "Interface LSA statistics";

      container self {
        description
          "Self LSA statistics";

        uses ospf-interface-lsa-type-statistics;
      }

      container remote {
        description
          "Remote LSA statistics";

        uses ospf-interface-lsa-type-statistics;
      }
    }
  }

  grouping ospf-area-lsa-type-statistics {
    description
      "This grouping defines statistics related to Area LSDB.";

    container cumulative {
      description
        "LSA statistics across types";

      uses ospf-lsa-type-statistics;
    }

    container router-lsa {
      description
        "Router LSA statistics";

      uses ospf-lsa-type-statistics;
    }

    container network-lsa {
      description
        "Network LSA statistics";

      uses ospf-lsa-type-statistics;
    }

    container summary-prefix-lsa {
      description
        "Summary Prefix LSA statistics";

      uses ospf-lsa-type-statistics;
    }

    container summary-asbr-lsa {
      description
        "Summary ASBR LSA statistics";

      uses ospf-lsa-type-statistics;
    }

    container intra-area-prefix-lsa {
      description
        "Intra-Area-Prefix LSA statistics";

      uses ospf-lsa-type-statistics;
    }
  }

  grouping ospf-area-lsa-statistics-structure {
    description
      "This grouping defines statistics related to Area LSDB.";

    container lsa {
      description
        "Area LSA statistics";

      container self {
        description
          "Self LSA statistics";

        uses ospf-area-lsa-type-statistics;
      }

      container remote {
        description
          "Remote LSA statistics";

        uses ospf-area-lsa-type-statistics;
      }
    }
  }

  grouping ospf-as-scope-lsa-type-statistics {
    description
      "This grouping defines statistics related to AS scope LSDB.";

    container cumulative {
      description
        "LSA statistics across types";

      leaf lsas {
        type uint32;
        description
          "Number of LSAs of all types";
      }

      leaf lsas-in-maintenance {
        type uint32;
        description
          "Number of LSAs in maintenance-mode";
      }
    }

    container as-external-lsa {
      description
        "External LSA statistics";

      uses ospf-lsa-type-statistics;
    }
  }

  grouping ospf-as-scope-lsa-statistics-structure {
    description
      "This grouping defines statistics related to AS scope LSDB.";

    container lsa {
      description
        "AS scope LSA statistics";

      container self {
        description
          "Self LSA statistics";

        uses ospf-as-scope-lsa-type-statistics;
      }

      container remote {
        description
          "Remote LSA statistics";

        uses ospf-as-scope-lsa-type-statistics;
      }
    }
  }

  grouping ospf-global-lsa-type-statistics {
    description
      "This grouping defines statistics across all LSDBs of this instance.";

    container cumulative {
      description
        "LSA statistics across types";

      uses ospf-lsa-type-statistics;
    }

    container router-lsa {
      description
        "Router LSA statistics";

      uses ospf-lsa-type-statistics;
    }

    container network-lsa {
      description
        "Network LSA statistics";

      uses ospf-lsa-type-statistics;
    }

    container summary-prefix-lsa {
      description
        "Summary Prefix LSA statistics";

      uses ospf-lsa-type-statistics;
    }

    container summary-asbr-lsa {
        description
        "Summary ASBR LSA statistics";

      uses ospf-lsa-type-statistics;
    }

    container as-external-lsa {
      description
        "ASB External LSA statistics";

      uses ospf-lsa-type-statistics;
    }

    container link-lsa {
      description
        "Link LSA statistics";

      uses ospf-lsa-type-statistics;
    }

    container intra-area-prefix-lsa {
      description
        "Intra-Area-Prefix LSA statistics";

      uses ospf-lsa-type-statistics;
    }
  }

  grouping ospf-global-lsa-statistics-structure {
    description
      "This grouping defines statistics across all LSDBs of this instance";

    container lsa {
      description
        "Global LSA statistics";

      container self {
        description
          "Self LSA statistics";

        uses ospf-global-lsa-type-statistics;
      }

      container remote {
        description
          "Remote LSA statistics";

        uses ospf-global-lsa-type-statistics;
      }
    }
  }


  /*
   * SPF Statistics
   */
  grouping ospf-spf-sm-statistics {
    description
      "This grouping defines SPF Delay SM statistics.";

    leaf spf-delay-sm-event-count {
      type uint64;
      description
        "The total number of SPF Delay state-machine events generated.";
    }

    leaf spf-delay-sm-transition-count {
      type uint64;
      description
        "The total number of SPF Delay state-machine transitions generated.";
    }
  }

  grouping ospf-spf-common-statistics {
    description
      "This grouping defines SPF computation statistics.";

    leaf spf-trigger-count {
      type uint64;
      description
        "Number of total SPF triggers that have occured till now";
    }

    leaf spf-computation-count {
      type uint64;
      description
        "The total number of SPF computations performed.";
    }

    leaf full-spf-computation-count {
      type uint64;
      description
        "The total number of full SPF computations performed.";
    }

    leaf spf-duration {
      type uint64;
      units microseconds;
      description
        "The total time taken for completing all SPF computations.";
    }

    leaf spt-duration {
      type uint64;
      units microseconds;
      description
        "The time taken for computing all SPF SPT results.";
    }
  }

  grouping ospf-comp-spf-statistics-structure {
    description
      "This grouping defines SPF computation statistics.";

    container spf {
      description
        "This container defines SPF computation statistics.";

      uses ospf-spf-sm-statistics;
      uses ospf-spf-common-statistics;
    }
  }

  grouping ospf-global-spf-statistics-structure {
    description
      "This grouping defines SPF global statistics.";

    container spf {
      description
        "This container defines SPF computation statistics.";

      uses ospf-spf-common-statistics;
    }
  }


  /*
   * RIB Statistics
   */
  grouping ospf-rib-table-statistics {
    description
      "This grouping defines statistics related to a RIB table.";

    container routes {
      description
        "This container describes routes statistics.";

      leaf total {
        type uint32;
        description
          "Total number of routes";
      }

      leaf unreachable {
        type uint32;
        description
          "Number of unreachable routes";
      }

      leaf intra-area {
        type uint32;
        description
          "Number of intra-area routes";
      }

      leaf interface-connected {
        type uint32;
        description
          "Number of interface connected routes";
      }

      leaf inter-area {
        type uint32;
        description
          "Number of inter-area routes";
      }

      leaf external-type1 {
        type uint32;
        description
          "Number of external type-1 routes";
      }

      leaf external-type2 {
        type uint32;
        description
          "Number of external type-2 routes";
      }

      leaf errors-memory {
        type uint64;
        description
          "Number of memory allocation errors";
      }
    }

    container paths {
      description
        "This container describes paths statistics.";

      leaf total {
        type uint32;
        description
          "Total number of paths";
      }

      leaf intra-area {
        type uint32;
        description
          "Number of intra-area paths";
      }

      leaf interface-connected {
        type uint32;
        description
          "Number of interface connected paths";
      }

      leaf inter-area {
        type uint32;
        description
          "Number of inter-area paths";
      }

      leaf external {
        type uint32;
        description
          "Number of external paths";
      }

      leaf errors-memory {
        type uint64;
        description
          "Number of memory allocation errors";
      }
    }
  }

  grouping ospf-rib-redist-statistics {
    description
      "This grouping defines statistics related to RIB redistribution.";

    container redistributed-routes {
      description
        "This container describes redistributed routes statistics.";

      leaf connected {
        type uint32;
        description
          "Total number of Connected routes";
      }

      leaf static {
        type uint32;
        description
          "Total number of Static routes";
      }

      leaf isis {
        type uint32;
        description
          "Total number of ISIS routes";
      }

      leaf bgp {
        type uint32;
        description
          "Total number of BGP routes";
      }

      leaf sidmgr {
        type uint32;
        description
          "Total number of SIDMGR routes";
      }

      leaf ospf {
        type uint32;
        description
          "Total number of OSPF routes";
      }

      leaf mark-stale {
        type uint64;
        description
          "Number of routes marked stale";
      }

      leaf delete-stale {
        type uint64;
        description
          "Number of stale routes deleted";
      }

      leaf delete-cleanup {
        type uint64;
        description
          "Number of routes cleaned up / deleted";
      }
    }

    container redistributed-paths {
      description
        "This container describes redistributed paths statistics.";

      leaf mark-stale {
        type uint64;
        description
          "Number of paths marked stale";
      }

      leaf delete-stale {
        type uint64;
        description
          "Number of stale paths deleted";
      }
    }

    container notifications {
      description
        "This container describes redistribution notification statistics.";

      leaf additions-total {
        type uint64;
        description
          "Total number of route additions";
      }

      leaf additions-unknown {
        type uint64;
        description
          "Number of unknow client type route additions";
      }

      leaf additions-rejected {
        type uint64;
        description
          "Number of rejected/dropped route additions";
      }

      leaf deletions-total {
        type uint64;
        description
          "Total number of route deletions";
      }
    }
  }

  grouping ospf-rib-aggr-statistics {
    description
      "This grouping defines statistics related to aggregate routes.";

    container routes {
      description
        "This container describes aggregate routes statistics.";

      leaf summary-aggregate-ranges {
        type uint32;
        description
          "Number of summary aggregate range routes";
      }

      leaf redistribute-aggregate-ranges {
        type uint32;
        description
          "Number of redistribute aggregate range routes";
      }

      leaf summary-aggregate-contributors {
        type uint32;
        description
          "Number of summary aggregate contributor routes";
      }

      leaf redistribute-aggregate-contributors {
        type uint32;
        description
          "Number of redistribute aggregate contributor routes";
      }
    }

    container paths {
      description
        "This container describes aggregate paths statistics.";

      leaf summary-aggregate-ranges {
        type uint32;
        description
          "Number of summary aggregate range paths";
      }

      leaf redistribute-aggregate-ranges {
        type uint32;
        description
          "Number of redistribute aggregate range paths";
      }
    }
  }

  grouping ospf-rib-download-statistics {
    description
      "This grouping defines statistics related to route download.";

    container routes {
      description
        "This container describes routes download statistics.";

      leaf installed {
        type uint32;
        description
          "Number of routes installed";
      }

      leaf additions {
        type uint64;
        description
          "Number of route additions";
      }

      leaf deletions {
        type uint64;
        description
          "Number of route deletions";
      }

      leaf errors {
        type uint64;
        description
          "Number of errors encountered";
      }
    }
  }

  grouping ospf-rib-lsa-statistics {
    description
      "This grouping defines statistics related to RIB route LSA origination.";

    container lsas {
      description
        "This container describes route LSA origination statistics.";

      leaf total {
        type uint32;
        description
          "Total number of Summary/External LSAs originated";
      }

      leaf summary-lsas {
        type uint32;
        description
          "Total number of Summary LSAs originated";
      }

      leaf as-external-lsas {
        type uint32;
        description
          "Total number of External LSAs originated";
      }

      leaf advertisements {
        type uint64;
        description
          "Number of LSAs advertised";
      }

      leaf maxage {
        type uint64;
        description
          "Number of LSAs withdrawn/maxaged";
      }
    }
  }

  grouping ospf-rib-server-statistics {
    description
      "This grouping defines general statistics related to L3RIB server interaction.";

    leaf restarts {
      type uint32;
      description
        "Number of L3RIB server restarts seen";
    }

    leaf last-restart-timestamp {
      type string;
      description
        "The timestamp of the last L3RIB server restart seen.";
    }
  }

  grouping ospf-rib-nexthop-statistics {
    description
      "This grouping defines statistics related to Nexthops.";

    container nexthop-sets {
      description
        "This container describes nexthop-set statistics.";

      leaf total {
        type uint32;
        description
          "Total number of nexthop-sets";
      }

      leaf refcount-total {
        type uint32;
        description
          "Total number of refcounts";
      }

      leaf allocations {
        type uint64;
        description
          "Number of memory allocations";
      }

      leaf frees {
        type uint64;
        description
          "Number of frees";
      }

      leaf refcount-increments {
        type uint64;
        description
          "Number of refcount increment operations";
      }

      leaf refcount-decrements {
        type uint64;
        description
          "Number of refcount decrement operations";
      }

      leaf errors {
        type uint64;
        description
          "Total number of errors";
      }

      leaf errors-memory {
        type uint64;
        description
          "Number of memory allocation errors";
      }

      leaf errors-refcount {
        type uint64;
        description
          "Number of refcounting errors";
      }
    }
  }

  grouping ospf-global-rib-statistics-structure {
    description
      "This grouping defines statistics related to OSPF RIB.";

    container rib {
      description
        "This container describes OSPF RIB statistics.";

      container prefix {
        description
          "This container describes RIB prefix statistics.";

        uses ospf-rib-table-statistics;
      }

      container redistributed-prefix {
        description
          "This container describes RIB redistributed prefix statistics.";

        uses ospf-rib-table-statistics;
        uses ospf-rib-redist-statistics;
      }

      container asbr {
        description
          "This container describes RIB ASBR statistics.";

        uses ospf-rib-table-statistics;
      }

      container aggregate {
        description
          "This container describes RIB Aggregate statistics.";

        uses ospf-rib-aggr-statistics;
      }

      container download {
        description
          "This container describes RIB prefix download statistics.";

        uses ospf-rib-download-statistics;
      }

      container self-originate {
        description
          "This container describes self-originated LSAs from RIB prefixes.";

        uses ospf-rib-lsa-statistics;
      }

      container server {
        description
          "This container describes RIB server interaction statistics.";

        uses ospf-rib-server-statistics;
      }

      container nexthop {
        description
          "This container describes RIB Nexthop statistics.";

        uses ospf-rib-nexthop-statistics;
      }
    }
  }


  /*
   * SNMP Statistics
   */
  grouping ospf-snmp-trap-statistics {
    description
      "This grouping defines SNMP trap statistics.";

    leaf if-state-change {
      type uint64;
      description
        "Number of IfStateChange traps generated";
    }

    leaf nbr-state-change {
      type uint64;
      description
        "Number of NbrStateChange traps generated";
    }

    leaf if-config-error {
      type uint64;
      description
        "Number of IfConfigError traps generated";
    }

    leaf if-auth-failure {
      type uint64;
      description
        "Number of IfAuthFailure traps generated";
    }

    leaf if-rx-bad-packet {
      type uint64;
      description
        "Number of IfRxBadPacket traps generated";
    }

    leaf tx-retransmit {
      type uint64;
      description
        "Number of RxRetransmit traps generated";
    }

    leaf originate-lsa {
      type uint64;
      description
        "Number of OriginateLsa traps generated";
    }

    leaf max-age-lsa {
      type uint64;
      description
        "Number of MaxAgeLsa traps generated";
    }

    leaf lsdb-approaching-overflow {
      type uint64;
      description
        "Number of LsdbApproachingOverflow traps generated";
    }

    leaf lsdb-overflow {
      type uint64;
      description
        "Number of LsdbOverflow traps generated";
    }

    leaf gen-error {
      type uint64;
      description
        "Number of errors during trap generation";
    }
  }

  grouping ospf-snmp-request-statistics {
    description
      "This grouping defines SNMP request/response statistics.";

    leaf get-total {
      type uint64;
      description
        "Total number of Get requests";
    }

    leaf get-notfound {
      type uint64;
      description
        "Number of Get requests resulting in not-found error";
    }

    leaf get-error {
      type uint64;
      description
        "Number of Get requests resulting in errors excluding not-found";
    }

    leaf get-next-total {
      type uint64;
      description
        "Total number of Get-next requests";
    }

    leaf get-next-error {
      type uint64;
      description
        "Number of Get-Next requests resulting in errors";
    }
  }

  grouping ospf-global-snmp-statistics-structure {
    description
      "This grouping defines statistics related to OSPF SNMP.";

    container snmp {
      description
        "This container defines OSPF SNMP statistics.";

      container request {
        description
          "This container describes SNMP Get/GetNext/Walk statistics.";

        uses ospf-snmp-request-statistics;
      }

      container trap {
        description
          "This container describes SNMP trap statistics.";

        uses ospf-snmp-trap-statistics;
      }
    }
  }
}
