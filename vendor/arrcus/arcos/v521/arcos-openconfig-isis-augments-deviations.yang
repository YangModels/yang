module arcos-openconfig-isis-augments-deviations {
  yang-version 1.1;
  namespace "http://yang.arrcus.com/arcos/openconfig/isis/augments/deviations";
  prefix arc-oc-isis-aug-dev;

  import openconfig-network-instance {
    prefix oc-ni;
  }

  import arcos-openconfig-isis-augments {
    prefix arc-oc-isis-aug;
  }

  import arcos-system-types {
    prefix arc-sys-types;
  }

  import openconfig-keychain-types {
    prefix oc-keychain-types;
  }

  organization
    "Arrcus, Inc.";

  contact
    "Arrcus, Inc.
     2077 Gateway Place,
     San Jose, CA 95110
     E-mail: yang-support@arrcus.com";

  description
    "This module defines annotations for Arrcus
     implemention of the openconfig ISIS module.
     Copyright (c) 2019-2022 by Arrcus, Inc.
     All rights reserved.";

  revision "2022-12-20" {
    description
      "Changes for authentication support:
       * Use encrypted password string for global hello authentication
       * Default auth-type to SIMPLE_KEY";
  }

  deviation "/oc-ni:network-instances/oc-ni:network-instance"
          + "/oc-ni:protocols/oc-ni:protocol/oc-ni:isis/oc-ni:global"
          + "/oc-ni:afi-safi/oc-ni:af/arc-oc-isis-aug:default-information"
          + "/arc-oc-isis-aug:originate/arc-oc-isis-aug:config"
          + "/arc-oc-isis-aug:export-policy" {
    deviate add {
      max-elements 1;
    }
    description
      "Only support one policy in this release.";
  }

  deviation "/oc-ni:network-instances/oc-ni:network-instance"
          + "/oc-ni:protocols/oc-ni:protocol/oc-ni:isis/oc-ni:global"
          + "/oc-ni:afi-safi/oc-ni:af/arc-oc-isis-aug:default-information"
          + "/arc-oc-isis-aug:originate/arc-oc-isis-aug:config"
          + "/arc-oc-isis-aug:default-export-policy" {
    deviate not-supported;
    description
      "Not supported in this release";
  }

  deviation "/oc-ni:network-instances/oc-ni:network-instance"
          + "/oc-ni:protocols/oc-ni:protocol/oc-ni:isis/oc-ni:global"
          + "/oc-ni:afi-safi/oc-ni:af/arc-oc-isis-aug:default-information"
          + "/arc-oc-isis-aug:originate/arc-oc-isis-aug:state"
          + "/arc-oc-isis-aug:default-export-policy" {
    deviate not-supported;
    description
      "Not supported in this release";
  }

  deviation "/oc-ni:network-instances/oc-ni:network-instance" +
            "/oc-ni:protocols/oc-ni:protocol/oc-ni:isis" +
            "/oc-ni:global/arc-oc-isis-aug:hello-authentication" +
            "/arc-oc-isis-aug:key/arc-oc-isis-aug:config" +
            "/arc-oc-isis-aug:auth-password" {
    deviate replace {
      type arc-sys-types:encrypted-string;
    }
    description "Prevent storage of clear-text strings in the configuration database";
  }

  deviation "/oc-ni:network-instances/oc-ni:network-instance" +
            "/oc-ni:protocols/oc-ni:protocol/oc-ni:isis" +
            "/oc-ni:global/arc-oc-isis-aug:hello-authentication" +
            "/arc-oc-isis-aug:config/arc-oc-isis-aug:auth-type" {
    deviate add {
      default oc-keychain-types:SIMPLE_KEY;
    }
    description "Default auth type to use key-based auth";
  }

  deviation "/oc-ni:network-instances/oc-ni:network-instance" +
            "/oc-ni:protocols/oc-ni:protocol/oc-ni:isis" +
            "/oc-ni:levels/oc-ni:level" +
            "/oc-ni:authentication/oc-ni:config/oc-ni:auth-type" {
    deviate add {
      default oc-keychain-types:SIMPLE_KEY;
    }
    description "Default auth type to use key-based auth";
  }

  deviation "/oc-ni:network-instances/oc-ni:network-instance" +
            "/oc-ni:protocols/oc-ni:protocol/oc-ni:isis" +
            "/oc-ni:interfaces/oc-ni:interface" +
            "/oc-ni:authentication/oc-ni:config/oc-ni:auth-type" {
    deviate add {
      default oc-keychain-types:SIMPLE_KEY;
    }
    description "Default auth type to use key-based auth";
  }

  deviation "/oc-ni:network-instances/oc-ni:network-instance" +
            "/oc-ni:protocols/oc-ni:protocol/oc-ni:isis" +
            "/oc-ni:interfaces/oc-ni:interface" +
            "/oc-ni:levels/oc-ni:level" +
            "/oc-ni:hello-authentication/oc-ni:config/oc-ni:auth-type" {
    deviate add {
      default oc-keychain-types:SIMPLE_KEY;
    }
    description "Default auth type to use key-based auth";
  }
}
