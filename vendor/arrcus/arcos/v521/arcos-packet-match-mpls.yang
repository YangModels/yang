module arcos-packet-match-mpls {
  yang-version 1.1;
  namespace "http://yang.arrcus.com/arcos/packet-match-mpls";
  prefix arc-match-mpls;

  grouping mpls-fields-config {
    description
      "Configuration data of MPLS fields";

    leaf label-id {
      type uint32 {
        range "0..1048575";
      }
      description
      "Match the conditon that an IP packet contains a specific MPLS
      label.";
    }
  }

  grouping mpls-fields-state {
    description
      "State data of mpls-fields";
  }

  grouping mpls-fields-top {
    description
      "Destination mpls-fields top level grouping";

    container mpls {
      description
        "MPLS fields container";

      container config {
        description
          "Configuration data";
        uses mpls-fields-config;
      }

      container state {
        config false;
        description
          "State data";
        uses mpls-fields-config;
        uses mpls-fields-state;
      }
    }
  }
}
