module arcos-mbroker {
  yang-version 1.1;
  namespace "http://yang.arrcus.com/arcos/mbroker";
  prefix "arc-mbroker";

  typedef mbroker-type {
    type enumeration {
      enum "MPROXY" {
        value 1;
      }
      enum "MPS" {
        value 2;
      }
    }
  }

  typedef mbroker-ep-type {
    type enumeration {
      enum "SOURCE" {
        value 1;
      }
      enum "DRAIN" {
        value 2;
      }
      enum "PUBLISHER" {
        value 3;
      }
      enum "SUBSCRIBER" {
        value 4;
      }
    }
  }

  typedef mbroker-state {
    type enumeration {
      enum "INVALID" {
        value 0;
      }
      enum "UP" {
        value 1;
      }
      enum "DOWN" {
        value 2;
      }
      enum "MARK_SWEEP_TIMER" {
        value 3;
      }
    }
  }

  typedef mbroker-mode {
    type enumeration {
      enum "ACTIVE" {
        value 1;
      }
      enum "STANDBY" {
        value 2;
      }
      enum "ACTIVE-TO-STANDBY" {
        value 3;
      }
      enum "STANDBY-TO-ACTIVE" {
        value 4;
      }
      enum "UNKNOWN" {
        value 5;
      }
    }
  }

  grouping mb-ep-state {
    description "End-point state";
    leaf status {
      type mbroker-state;
      description
        "End point current status";
    }
    leaf reset-count {
      type uint16;
      description
        "Connection reset count";
    }
  }

  grouping mb-ep-tbl-state {
    description "End-point consolidated state info";
    leaf total-tables {
      type uint16;
      description
        "Total table count";
    }
    leaf total-entries {
      type uint64;
      description
        "Total sum of entries across all tables";
    }
    leaf total-msg-add {
      type uint64;
      description
        "Total add message count";
    }
    leaf total-msg-upd {
      type uint64;
      description
        "Total update message count";
    }
    leaf total-msg-del {
      type uint64;
      description
        "Total delete message count";
    }
  }

  grouping mb-tbl-state {
    description "Table state info";
    leaf msg-add {
      type uint64;
      description
        "Add message count";
    }
    leaf msg-upd {
      type uint64;
      description
        "Update message count";
    }
    leaf msg-del {
      type uint64;
      description
        "Delete message count";
    }
  }

  grouping mb-bind-client-tables {
    container table {
      description "Bind clinet per table info";
      list table {
        key "table-id";
        description "Table id";
        leaf table-id {
          type uint32;
          description
              "Table ID";
        }
        leaf table-size {
          type uint64;
          description
              "Table size";
        }
        uses mb-tbl-state;
      }
    }
  }

  grouping mb-ep-events {
    description "End-point last event";
    leaf ep-events {
      type string;
      description
          "End Point events";
    }
  }

  grouping mb-bind-clients {
    container bind-client {
      description "Bind client for source end-point";
      list bind-client {
        key "bind-client-name";
        description
          "Bind client to server end-point name";
        leaf bind-client-name {
          type string;
          description
            "End point name";
        }
        uses mb-ep-state;
        uses mb-ep-tbl-state;
        uses mb-bind-client-tables;
        uses mb-ep-events;
      }
    }
  }

  grouping mb-ep-source {
    container sources {
      list source {
        key "ep-name";
        description
          "Source end point";
        leaf ep-name {
          type string;
          description
            "End point name";
        }
        leaf ep-type {
          type mbroker-ep-type;
          description
            "End point type";
        }
        leaf uri {
          type string;
          description "Source End point URI protocol://ip-address:port";
        }
        leaf service {
          type string;
          description "Source service name";
        }
        uses mb-ep-state;
        uses mb-ep-tbl-state;
        uses mb-bind-clients;
        uses mb-ep-events;
      }
    }
  }

  grouping mb-ep-drain {
    container drains {
      list drain {
        key "ep-name";
        description
          "Drain end point";
        leaf ep-name {
          type string;
          description
            "End point name";
        }
        leaf ep-type {
          type mbroker-ep-type;
          description
            "End point type";
        }
        leaf uri {
          type string;
          description "Drain End point URI protocol://ip-address:port";
        }
        leaf service {
          type string;
          description "Drain service name";
        }
        leaf total-msg-left {
          type uint64;
          description "Drain service name";
        }
        leaf total-msg-sent {
          type uint64;
          description
            "Total sum of entries across all tables";
        }
        leaf total-msg-add {
          type uint64;
          description
            "Total add message count";
        }
        leaf total-msg-upd {
          type uint64;
          description
            "Total update message count";
        }
        leaf total-msg-del {
          type uint64;
          description
            "Total delete message count";
        }
        uses mb-ep-state;
        uses mb-ep-events;
      }
    }
  }

  grouping mps-tbl-pubs {
    container publishers {
      description "Publisher tables information";
      list publisher {
        key "pub-id";
        description "Publisher ID";
        leaf pub-id {
          type string;
          description
              "Publisher ID";
        }
        leaf total-messages-added {
          type uint64;
          description
            "Total add message count";
        }
        leaf total-messages-updated {
          type uint64;
          description
            "Total update message count";
        }
        leaf total-messages-deleted {
          type uint64;
          description
            "Total delete message count";
        }
      }
    }
  }

  grouping mps-tbl-subs {
    container subscribers {
      description "Subscriber tables information";
      list subscriber {
        key "sub-id";
        description "Subscriber ID";
        leaf sub-id {
          type string;
          description
              "Publisher ID";
        }
        leaf total-messages-remaining {
          type uint64;
          description "Messages yet to receive";
        }
        leaf total-messages-added {
          type uint64;
          description
            "Total add message count";
        }
        leaf total-messages-updated {
          type uint64;
          description
            "Total update message count";
        }
        leaf total-messages-deleted {
          type uint64;
          description
            "Total delete message count";
        }
      }
    }
  }

  grouping mb-mps-tbls {
    container tables {
      description "MPS tables info";
      list table {
        key "table-id";
        description "Table id";
        leaf table-id {
          type string;
          description
              "Table ID";
        }
        leaf table-size {
          type uint64;
          description
              "Table size";
        }
        leaf snapshot {
          type uint8;
          description
            "Table snapshot";
        }
        uses mb-tbl-state;
        uses mps-tbl-pubs;
        uses mps-tbl-subs;
      }
    }
  }

  grouping sub-tables {
    container tables {
      description "Subscriber tables information";
      list table {
        key "table-id";
        description "Table id";
        leaf table-id {
          type string;
          description
              "Table ID";
        }
        leaf table-size {
          type uint64;
          description
              "Table size";
        }
        leaf total-messages-remaining {
          type uint64;
          description "message yet to receive";
        }
        leaf total-messages-added {
          type uint64;
          description
            "Total add message count";
        }
        leaf total-messages-updated {
          type uint64;
          description
            "Total update message count";
        }
        leaf total-messages-deleted {
          type uint64;
          description
            "Total delete message count";
        }
      }
    }
  }

  grouping mb-sub-tbl-info {
    description "Subscriber consolidated table info";
    leaf total-tables {
      type uint16;
      description
        "Total table count";
    }
    leaf total-entries {
      type uint64;
      description
        "Total sum of entries across all tables";
    }
    leaf total-messages-added {
      type uint64;
      description
        "Total add messages rx";
    }
    leaf total-messages-updated {
      type uint64;
      description
        "Total update message rx";
    }
    leaf total-messages-deleted {
      type uint64;
      description
        "Total delete message rx";
    }
  }

  grouping mb-mps-sub {
    container subscribers {
      list subscriber {
        key "name";
        description
          "Subscriber handle";
        leaf name {
          type string;
          description
          "Subscriber name";
        }
        leaf ep-type {
          type mbroker-ep-type;
          description
            "End point type";
        }
        leaf uri {
          type string;
          description "Subscriber URI protocol://ip-address:port";
        }
        leaf service {
          type string;
          description "Subscriber service name";
        }
        uses mb-ep-state;
        uses mb-sub-tbl-info;
        uses sub-tables;
        uses mb-ep-events;
      }
    }
  }

  grouping mb-pub-tbl-info {
    description "Publisher consolidated tables info";
    leaf total-tables {
      type uint16;
      description
        "Total table count";
    }
    leaf total-entries {
      type uint64;
      description
        "Total sum of entries across all tables";
    }
    leaf total-messages-added {
      type uint64;
      description
        "Total add message count";
    }
    leaf total-messages-updated {
      type uint64;
      description
        "Total update message count";
    }
    leaf total-messages-deleted {
      type uint64;
      description
        "Total delete message count";
    }
  }

  grouping pub-tables {
    container tables {
      description "publisher tables information";
      list table {
        key "table-id";
        description "Table id";
        leaf table-id {
          type string;
          description
              "Table ID";
        }
        leaf table-size {
          type uint64;
          description
              "Table size";
        }
        uses mb-tbl-state;
      }
    }
  }

  grouping mb-mps-pub {
    container publishers {
      list publisher {
        key "name";
        description
          "Publisher handle";
        leaf name {
          type string;
          description
            "Publisher handle";
        }
        leaf ep-type {
          type mbroker-ep-type;
          description
            "End point type";
        }
        leaf uri {
          type string;
          description "Publisher URI protocol://ip-address:port";
        }
        leaf service {
          type string;
          description "Publisher service name";
        }
        uses mb-ep-state;
        uses mb-pub-tbl-info;
        uses pub-tables;
        uses mb-ep-events;
      }
    }
  }

  grouping mb-mpsc-pub {
    container mpsc-publishers {
      list publisher {
        key "name";
        description
          "Publisher handle";
        leaf name {
          type string;
          description
            "Publisher handle";
        }
        uses mb-ep-state;
        uses mb-mpsc-tbls;
        uses mb-ep-events;
      }
    }
  }

  grouping mb-mpsc-sub {
    container mpsc-subscribers {
      list subscriber {
        key "name";
        description
          "Subscriber handle";
        leaf name {
          type string;
          description
          "Subscriber name";
        }
        uses mb-ep-state;
        uses mb-mpsc-tbls;
        uses mb-ep-events;
      }
    }
  }

  grouping mb-mpsc-tbls {
    container mpsc-tables {
      description "MPS tables info";
      list table {
        key "table-id";
        description "Table id";
        leaf table-id {
          type string;
          description
              "Table ID";
        }
        leaf table-messages {
          type uint64;
          description
              "Table size";
        }
        leaf total-messages-added {
          type uint64;
          description
            "Total add message count";
        }
        leaf total-messages-updated {
          type uint64;
          description
            "Total update message count";
        }
        leaf total-messages-deleted {
          type uint64;
          description
            "Total delete message count";
        }
      }
    }
  }

  grouping mb-mpsc-client {
    container mpsc-client {
      list mpsc {
        key "name";
        description
          "MPSC client handle";
        leaf name {
          type string;
          description
            "MPSC client handle";
        }
        uses mb-ep-state;
        uses mb-mpsc-pub;
        uses mb-mpsc-sub;
      }
    }
  }

  grouping mb-mps {
    description "Message PubSub Service [MPS]";
    container summary {
      leaf instance-mode {
        type mbroker-mode;
        description "MPS instance mode";
      }
      leaf ctrl-uri {
        type string;
        description "Publisher URI protocol://ip-address:port";
      }
      leaf-list data-uri {
        type string;
        description "Publisher service name";
      }
      leaf total-clients {
        type uint32;
        description "Total number of MPS clients";
      }
      leaf total-publishers {
        type uint32;
        description "Total number of publishers";
      }
      leaf total-subscribers {
        type uint32;
        description "Total number of subscribers";
      }
      leaf total-tables {
        type uint32;
        description "Total number of tables";
      }
      leaf disk-path {
        type string;
        description "MPS file persistence directory";
      }
      leaf instance-directory {
        type string;
        description "MPS file persistence directory for this instance";
      }
      uses mb-ep-state;
    }
    uses mb-mpsc-client;
  }

  grouping mbroker-base {
    container mbroker {
      description
        "mbroker top level base";
      config false;
      list instances {
        key "instance";
        max-elements 64;
        description
          "Message broker instances";
        leaf instance {
          type string;
          description
              "Instance name";
        }
        leaf instance-type {
          type mbroker-type;
          description
              "Instance type";
        }
        uses mb-ep-source {
          when "instance-type = 'MPROXY'";
        }
        uses mb-ep-drain{
          when "instance-type = 'MPROXY'";
        }
        uses mb-mps {
          when "instance-type = 'MPS'";
        }
        uses mb-mps-pub {
          when "instance-type = 'MPS'";
        }
        uses mb-mps-sub {
          when "instance-type = 'MPS'";
        }
        uses mb-mps-tbls {
          when "instance-type = 'MPS'";
        }
      }
    }
  }
  uses mbroker-base;
}
