submodule arcos-ospfv3-area-interface {

  yang-version "1.1";

  belongs-to arcos-ospfv3 {
    prefix "arc-ospfv3";
  }

  import ietf-yang-types { prefix "yang"; }

  description
    "This submodule provides OSPFv3 configuration and operational
    state parameters that are specific to the interface context";

  grouping ospfv3-area-interface-config {
    description
      "Configuration parameters for an OSPFv3 interface";

    leaf interface-id {
      type uint32;
      description
        "32-bit number uniquely identifying this interface among the
         collection of this router's interfaces";
    }

    leaf instance-id {
      type uint32;
      default 0;
      description
        "The OSPF protocol instance associated with this OSPF interface";
    }
  }

  grouping ospfv3-area-interface-neighbor-state {
    description
      "Operation state parameters of an OSPFv3 neighbor";

    leaf interface-id {
      type uint32;
      description
        "32-bit number uniquely identifying this interface among the
         collection of the remote system's interfaces";
    }

    leaf dr-router-id {
      type yang:dotted-quad;
      description
        "The router-id of the designated router elected by the neighbor.";
    }

    leaf bdr-router-id {
      type yang:dotted-quad;
      description
        "The router-id of the backup designated router elected by the neighbor.";
    }
  }

  grouping ospfv3-area-interface-neighbor-bfd-structure {
    description
      "This grouping defines OSPFv3 neighbor BFD information.";

    container bfd {
      description
        "This container defines neighbor BFD state.";

      container state {
        leaf ipv6-bfd-up {
          type boolean;
          description
            "OSPF neighbor IPV6 BFD up";
        }
      }
    }
  }
}
