module arcos-mpsc {
  yang-version 1.1;
  namespace "http://yang.arrcus.com/arcos/mpsc";
  prefix "arc-mpsc";

  grouping ctrl-msg-counters {
    description "control message counters";
    container ctrl-msg-counters {
      leaf client-reg {
        type uint64;
        description
          "MPS ctrl msg client register counter";
      }
      leaf client-dereg {
        type uint64;
        description
          "MPS ctrl msg client deregister counter";
      }
      leaf pub-reg {
        type uint64;
        description
          "MPS ctrl msg publisher register counter";
      }
      leaf pub-dereg {
        type uint64;
        description
          "MPS ctrl msg publisher deregister counter";
      }
      leaf sub-reg {
        type uint64;
        description
          "MPS ctrl msg subscriber register counter";
      }
      leaf sub-dereg {
        type uint64;
        description
          "MPS ctrl msg subscriber deregister counter";
      }
      leaf tbl-create {
        type uint64;
        description
          "MPS ctrl msg table create counter";
      }
      leaf tbl-delete {
        type uint64;
        description
          "MPS ctrl msg table delete counter";
      }
      leaf tbl-subscribe {
        type uint64;
        description
          "MPS ctrl msg table subscribe counter";
      }
      leaf tbl-desubscribe {
        type uint64;
        description
          "MPS ctrl msg table desubscribe counter";
      }
      leaf tbl-subscribe-dp-ready {
        type uint64;
        description
          "MPS ctrl msg table subscribe DP ready counter";
      }
    }
  }

  grouping pub-register-error-counters {
    description "MPSC publisher register error counters";
    container pub-register-error-counters {
      leaf client-handle {
        type uint64;
        description
          "Invalid client handle error counter";
      }
      leaf bq-enqueue {
        type uint64;
        description
          "Failed to enqueue to ctrl tx queue error counter";
      }
    }
  }
  
  grouping sub-register-error-counters {
    description "MPSC subscriber register error counters";
    container sub-register-error-counters {
      leaf client-handle {
        type uint64;
        description
          "Invalid client handle error counter";
      }
      leaf bq-enqueue {
        type uint64;
        description
          "Failed to enqueue to ctrl tx queue error counter";
      }
    }
  }

  grouping pub-tbl-create-error-counters {
    description "MPSC publisher table create error counters";
    container pub-tbl-create-error-counters {
      leaf client-handle {
        type uint64;
        description
          "Invalid client handle error counter";
      }
      leaf bq-enqueue {
        type uint64;
        description
          "Failed to enqueue to ctrl tx queue error counter";
      }
    }
  }
  
  grouping sub-tbl-subscribe-error-counters {
    description "MPSC subcriber tabel subcriber error counters";
    container sub-tbl-subscribe-error-counters {
      leaf client-handle {
        type uint64;
        description
          "Invalid client handle error counter";
      }
      leaf bq-enqueue {
        type uint64;
        description
          "Failed to enqueue to ctrl tx queue error counter";
      }
    }
  }

  grouping pub-dereg-error-counters {
    description "MPSC publisher deregister blocking error counters";
    container pub-dereg-error-counters {
      leaf client-handle {
        type uint64;
        description
          "Invalid client handle error counter";
      }
      leaf pub-not-found {
        type uint64;
        description
          "publisher not found";
      }
      leaf already-admin-down {
        type uint64;
        description
          "publisher already admin down";
      }
      leaf bq-enqueue {
        type uint64;
        description
          "Failed to enqueue to ctrl tx queue error counter";
      }
      leaf timeout {
        type uint64;
        description
          "publisher deregister timeout";
      }
    }
  }
  
  grouping pub-tbl-del-error-counters {
    description "MPSC publisher table delete blocking error counters";
    container pub-tbl-del-error-counters {
      leaf client-handle {
        type uint64;
        description
          "Invalid client handle error counter";
      }
      leaf pub-not-found {
        type uint64;
        description
          "publisher not found";
      }
      leaf tbl-not-found {
        type uint64;
        description
          "publisher table not found";
      }
      leaf already-admin-down {
        type uint64;
        description
          "publisher table already admin down";
      }
      leaf bq-enqueue {
        type uint64;
        description
          "Failed to enqueue to ctrl tx queue error counter";
      }
      leaf timeout {
        type uint64;
        description
          "publisher table delete timeout";
      }
    }
  }

  grouping sub-dereg-error-counters {
    description "MPSC subscriber deregister blocking error counters";
    container sub-dereg-error-counters {
      leaf client-handle {
        type uint64;
        description
          "Invalid client handle error counter";
      }
      leaf sub-not-found {
        type uint64;
        description
          "subscriber not found";
      }
      leaf already-admin-down {
        type uint64;
        description
          "subscriber already admin down";
      }
      leaf bq-enqueue {
        type uint64;
        description
          "Failed to enqueue to ctrl tx queue error counter";
      }
      leaf timeout {
        type uint64;
        description
          "subscriber deregister timeout";
      }
    }
  }

  grouping sub-tbl-desubscribe-error-counters {
    description "MPSC subscriber table desubscribe blocking error counters";
    container sub-tbl-desubscribe-error-counters {
      leaf client-handle {
        type uint64;
        description
          "Invalid client handle error counter";
      }
      leaf sub-not-found {
        type uint64;
        description
          "subscriber not found";
      }
      leaf tbl-not-found {
        type uint64;
        description
          "subscriber table not found";
      }
      leaf already-admin-down {
        type uint64;
        description
          "subscriber table already admin down";
      }
      leaf bq-enqueue {
        type uint64;
        description
          "Failed to enqueue to ctrl tx queue error counter";
      }
      leaf timeout {
        type uint64;
        description
          "subscriber table desubscribe timeout";
      }
    }
  }

  grouping client-dereg-error-counters {
    description "MPSC client deregister blocking error counters";
    container client-dereg-error-counters {
      leaf client-handle {
        type uint64;
        description
          "Invalid client handle error counter";
      }
      leaf already-admin-down {
        type uint64;
        description
          "MPSC already in delete pending state";
      }
      leaf data-deinit {
        type uint64;
        description
          "MPSC data deinit failed";
      }
      leaf ctrl-deinit {
        type uint64;
        description
          "MPSC ctrl deinit failed";
      }
      leaf bq-enqueue {
        type uint64;
        description
          "Failed to enqueue to ctrl tx queue error counter";
      }
      leaf timeout {
        type uint64;
        description
          "client deregister timeout";
      }
    }
  }

  grouping ctrl-init-error-counters {
    description "control init error counters";
    container ctrl-init-error-counters {
      leaf client-handle {
        type uint64;
        description
          "Invalid client handle error counter";
      }
      leaf bq-enqueue {
        type uint64;
        description
          "Failed to enqueue to ctrl sync queue error counter";
      }
      uses pub-register-error-counters;
      uses sub-register-error-counters;
      uses pub-tbl-create-error-counters;
      uses sub-tbl-subscribe-error-counters;
    }
  }

  grouping ctrl-deinit-error-counters {
    description "control init error counters";
    container ctrl-deinit-error-counters {
      leaf client-handle {
        type uint64;
        description
          "Invalid client handle error counter";
      }
      leaf already-admin-down {
        type uint64;
        description
          "MPSC already in delete pending state";
      }
      leaf bq-enqueue {
        type uint64;
        description
          "Failed to enqueue to ctrl sync queue error counter";
      }
      leaf timeout {
        type uint64;
        description
          "client deregister timeout";
      }
      uses pub-dereg-error-counters;
      uses pub-tbl-del-error-counters;
      uses sub-dereg-error-counters;
      uses sub-tbl-desubscribe-error-counters;
      uses client-dereg-error-counters;
    }
  }

  grouping ctrl-error-counters {
    description "control error counters";
    container ctrl-error-counters {
      uses ctrl-init-error-counters;
      uses ctrl-deinit-error-counters;
    }
  }

  grouping ctrl {
    description "control counters";
    container ctrl{
      leaf tx_q-size {
        type uint64;
        description
          "ctrl tx_q size";
      }
      leaf ack_q-size {
        type uint64;
        description
          "ctrl ack_q size";
      }
      leaf syn_q-size {
        type uint64;
        description
          "ctrl syn_q size";
      }
      leaf sync_ack_list-size {
        type uint64;
        description
          "ctrl sync_ack_list size";
      }
      uses ctrl-msg-counters;
      uses ctrl-error-counters;
    }
  }

  grouping tbl-flags {
    description "MPSC table flags";
    container table-flags {
      leaf stat {
        type boolean;
        description
          "stat flag for mpsc_tbl_t";
      }
      leaf dp-tx-up {
        type boolean;
        description
          "dp_tx_up flag for mpsc_tbl_t";
      }
      leaf dp-rx-up {
        type boolean;
        description
          "dp_rx_up flag for mpsc_tbl_t";
      }
      leaf mps-tbl-up {
        type boolean;
        description
          "mps_tbl_up flag for mpsc_tbl_t";
      }
      leaf wc-sub {
        type boolean;
        description
          "wc_sub flag for mpsc_tbl_t";
      }
    }
  }

  grouping mpsc-sub-tbls {
    container tables {
      description "MPSC tables info";
      list table {
        key "table-id";
        description "Table id";
        leaf table-id {
          type string;
          description
            "Table ID";
        }
        leaf admin-down {
          type boolean;
          description
            "MPSC subscriber table admin-down flag";
        }
        leaf total-messages {
          type uint64;
          description
            "Table size";
        }
        leaf total-messages-added {
          type uint64;
          description
            "Table add message count";
        }
        leaf total-messages-updated {
          type uint64;
          description
            "Table update message count";
        }
        leaf total-messages-deleted {
          type uint64;
          description
            "Table delete message count";
        }
        leaf rx-bq-size {
          type uint64;
          description
            "rx-bq size";
        }
        leaf cache-add {
          type uint64;
          description
            "cache add";
        }
        leaf cache-upd {
          type uint64;
          description
            "cache update";
        }
        leaf cache-delete {
          type uint64;
          description
            "cache delete";
        }
        leaf app-context {
          type uint64;
          description
            "App context not set error counter";
        }
        leaf tbl {
          type uint64;
          description
            "tbl not found error counter";
        }
        leaf rx-dp {
          type uint64;
          description
            "rx-dp not found error counter";
        }
        leaf msg-enqueue {
          type uint64;
          description
            "msg enqueue failed error counter";
        }
        leaf sub-tbl-admin-down {
          type uint64;
          description
            "sub tbl admin down error counter";
        }
        leaf dp-not-created {
          type uint64;
          description
            "data path not created";
        }
        uses tbl-flags;
      }
    }
  }

  grouping mpsc-sub {
    container subscribers {
      list subscriber {
        key "name";
        description
          "Subscriber handle";
        leaf name {
          type string;
          description
            "Subscriber handle";
        }
        leaf admin-down {
          type boolean;
          description
            "MPSC Subscriber admin-down flag";
        }
        uses mpsc-sub-tbls;
      }
    }
  }

  grouping ml-send-error-counters {
    description "ml send error counters";
    container ml-send-error {
      leaf eagain {
        type uint64;
        description
          "eagain error counter";
      }
      leaf unreachable {
        type uint64;
        description
          "unreachable error counter";
      }
    }
  }

  grouping mpsc-pub-tbls {
    container tables {
      description "MPSC tables info";
      list table {
        key "table-id";
        description "Table id";
        leaf table-id {
          type string;
          description
            "Table ID";
        }
        leaf admin-down {
          type boolean;
          description
            "MPSC Publisher table admin-down flag";
        }
        leaf total-messages {
          type uint64;
          description
            "Table size";
        }
        leaf total-messages-added {
          type uint64;
          description
            "Table add message count";
        }
        leaf total-messages-updated {
          type uint64;
          description
            "Table update message count";
        }
        leaf total-messages-deleted {
          type uint64;
          description
            "Table delete message count";
        }
        leaf tx-ring-capacity {
          type uint64;
          description
            "tx ring capacity";
        }
        leaf tx-ring-size {
          type uint64;
          description
            "tx ring size";
        }
        leaf sync-ring-capacity {
          type uint64;
          description
            "sync ring capacity";
        }
        leaf sync-ring-size {
          type uint64;
          description
            "sync ring size";
        }
        leaf cache-add {
          type uint64;
          description
            "cache add";
        }
        leaf cache-upd {
          type uint64;
          description
            "cache update";
        }
        leaf cache-delete {
          type uint64;
          description
            "cache delete";
        }
        leaf invalid-args {
          type uint64;
          description
            "Invalid arguments error counter";
        }
        leaf pub-id {
          type uint64;
          description
            "Unknow pub id error counter";
        }
        leaf ep-tbl {
          type uint64;
          description
            "Unknow ep tbl error counter";
        }
        leaf tbl-admin-down {
          type uint64;
          description
            "tbl admin down error counter";
        }
        leaf tbl-not-acked {
          type uint64;
          description
            "tbl not acked error counter";
        }
        leaf pub-tbl-admin-down {
          type uint64;
          description
            "pub tbl admin down error counter";
        }
        uses tbl-flags;
        uses ml-send-error-counters;
      }
    }
  }

  grouping mpsc-pub {
    container publishers {
      list publisher {
        key "name";
        description
          "Publisher handle";
        leaf name {
          type string;
          description
            "Publisher handle";
        }
        leaf admin-down {
          type boolean;
          description
            "MPSC Publisher admin-down flag";
        }
        uses mpsc-pub-tbls;
        //uses mpsc-pub-error-counters;
      }
    }
  }

  grouping mpsc-client {
    container mpsc-client {
      config false;
      list clients {
        key "client";
        description
          "MPSC clients name";
        leaf client {
          type string;
          description
            "MPSC client handle";
        }
        leaf client-up {
          type boolean;
          description
            "MPSC CLIENT_UP flag";
        }
        leaf admin-down {
          type boolean;
          description
            "MPSC admin-down flag";
        }
        uses mpsc-pub;
        uses mpsc-sub;
        uses ctrl;
      }
    }
  }
  uses mpsc-client;
}
