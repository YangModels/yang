module arcos-interfaces-debug {
  yang-version 1.1;
  namespace "http://yang.arrcus.com/arcos/interfaces/debug";
  prefix arc-if-dbg;

  typedef ifmgr-debug-state {
    type enumeration {
      enum on {
        description
          "Enable debug";
      }
      enum off {
        description
          "Disable debug";
      }
    }
  }

  typedef ifmgr-debug-type {
    type enumeration {
      enum control {
        description
          "Control processing debugs";
      }
    }
  }

  container ifmgr-debug {
    description
      "Interface Manager debug control";

    action debug {
      input {
        leaf type {
          type ifmgr-debug-type;
          mandatory true;
          description
            "Debug to be controlled";
        }
        leaf op {
          type ifmgr-debug-state;
          mandatory true;
          description
            "Turn on/off operation";
        }
      }
      output {
        leaf result {
          type string;
          description
            "The status of operation";
        }
      }
    }
  }
}
