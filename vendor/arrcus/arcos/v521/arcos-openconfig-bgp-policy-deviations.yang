module arcos-openconfig-bgp-policy-deviations {
  yang-version 1.1;
  namespace "http://yang.arrcus.com/arcos/openconfig/bgp-policy/deviations";
  prefix arc-oc-bgp-pol-dev;

  import openconfig-routing-policy {
    prefix oc-rpol;
  }

  import openconfig-bgp-policy {
    prefix oc-bgp-pol;
  }

  import openconfig-bgp-types {
    prefix oc-bgp-types;
  }

  import arcos-openconfig-bgp-types {
    prefix arc-oc-bgp-types;
  }

  organization
    "Arrcus, Inc.";

    contact
        "Email: eng@arrcus.com";

  description
    "This module defines deviation statements for Arrcus
     implemention of the openconfig BGP policy module.";

  revision 2022-07-07 {
    description
      "Support bgp route-type LOCAL/INTERNAL/EXTERNAL";
  }

  revision 2018-08-14 {
      description "ArcOS release 2.2.1";
  }

  revision 2017-05-31 {
    description
      "Initial Revision
       * Limit community-set to a maximum of 16 members.
       * Limit ext-community-set to a maximum of 16 members.
       * Limit as-path-set to a maximum of 16 members.
       * Limit community-set name to 79 characters.
       * Limit ext-community-set name to 79 characters.
       * Limit as-path-set name to 79 characters.
       * Do not support route-type.
       * Do not support next-hop-in.
       * Do not support afi-safi-in.
       * Do not support community-count.
       * Fix set-community inline pattern.
       * Replace supported set-med type.
      ";

    reference
      "RFC 6020: YANG - A Data Modeling Language for the
       Network Configuration Protocol (NETCONF)";
  }

  deviation "/oc-rpol:routing-policy/oc-rpol:defined-sets" +
            "/oc-bgp-pol:bgp-defined-sets/oc-bgp-pol:community-sets" +
            "/oc-bgp-pol:community-set/oc-bgp-pol:config" +
            "/oc-bgp-pol:community-member" {
    deviate add {
      max-elements 32;
    }
    description "Only support up to 32 members in this release.";
  }

  deviation "/oc-rpol:routing-policy/oc-rpol:defined-sets" +
            "/oc-bgp-pol:bgp-defined-sets/oc-bgp-pol:ext-community-sets" +
            "/oc-bgp-pol:ext-community-set/oc-bgp-pol:config" +
            "/oc-bgp-pol:ext-community-member" {
    deviate replace {
      type union {
        type arc-oc-bgp-types:bgp-extcomm-type;
        type oc-bgp-types:bgp-community-regexp-type;
      }
    }
    description "Use bgp-extcomm-type.";
  }

  deviation "/oc-rpol:routing-policy/oc-rpol:defined-sets" +
            "/oc-bgp-pol:bgp-defined-sets/oc-bgp-pol:ext-community-sets" +
            "/oc-bgp-pol:ext-community-set/oc-bgp-pol:config" +
            "/oc-bgp-pol:ext-community-member" {
    deviate add {
      max-elements 32;
    }
    description "Only support up to 32 members in this release.";
  }

  deviation "/oc-rpol:routing-policy/oc-rpol:defined-sets" +
            "/oc-bgp-pol:bgp-defined-sets/oc-bgp-pol:as-path-sets" +
            "/oc-bgp-pol:as-path-set/oc-bgp-pol:config" +
            "/oc-bgp-pol:as-path-set-member" {
    deviate add {
      max-elements 32;
    }
    description "Only support up to 32 members in this release.";
  }

  deviation "/oc-rpol:routing-policy/oc-rpol:defined-sets" +
            "/oc-bgp-pol:bgp-defined-sets/oc-bgp-pol:community-sets" +
            "/oc-bgp-pol:community-set/oc-bgp-pol:config" +
            "/oc-bgp-pol:community-set-name" {
    deviate replace {
      type string {
        length "1..79";
      }
    }
    description "Limit size to 79 characters.";
  }

  deviation "/oc-rpol:routing-policy/oc-rpol:defined-sets" +
            "/oc-bgp-pol:bgp-defined-sets/oc-bgp-pol:ext-community-sets" +
            "/oc-bgp-pol:ext-community-set/oc-bgp-pol:config" +
            "/oc-bgp-pol:ext-community-set-name" {
    deviate replace {
      type string {
        length "1..79";
      }
    }
    description "Limit size to 79 characters.";
  }

  deviation "/oc-rpol:routing-policy/oc-rpol:defined-sets" +
            "/oc-bgp-pol:bgp-defined-sets/oc-bgp-pol:as-path-sets" +
            "/oc-bgp-pol:as-path-set/oc-bgp-pol:config" +
            "/oc-bgp-pol:as-path-set-name" {
    deviate replace {
      type string {
        length "1..79";
      }
    }
    description "Limit size to 79 characters.";
  }

  deviation "/oc-rpol:routing-policy/oc-rpol:policy-definitions" +
            "/oc-rpol:policy-definition/oc-rpol:statements" +
            "/oc-rpol:statement/oc-rpol:conditions" +
            "/oc-bgp-pol:bgp-conditions/oc-bgp-pol:config" +
            "/oc-bgp-pol:route-type" {
    deviate replace {
      type arc-oc-bgp-types:bgp-route-type;
    }
    description "Use bgp-route-type (local/internal/external)";
  }

  deviation "/oc-rpol:routing-policy/oc-rpol:policy-definitions" +
            "/oc-rpol:policy-definition/oc-rpol:statements" +
            "/oc-rpol:statement/oc-rpol:conditions" +
            "/oc-bgp-pol:bgp-conditions/oc-bgp-pol:state" +
            "/oc-bgp-pol:route-type" {
    deviate replace {
      type arc-oc-bgp-types:bgp-route-type;
    }
    description "Use bgp-route-type (local/internal/external)";
  }

  deviation "/oc-rpol:routing-policy/oc-rpol:policy-definitions" +
            "/oc-rpol:policy-definition/oc-rpol:statements" +
            "/oc-rpol:statement/oc-rpol:conditions" +
            "/oc-bgp-pol:bgp-conditions/oc-bgp-pol:config" +
            "/oc-bgp-pol:next-hop-in" {
    deviate not-supported;
    description "Not supported in this release.";
  }

  deviation "/oc-rpol:routing-policy/oc-rpol:policy-definitions" +
            "/oc-rpol:policy-definition/oc-rpol:statements" +
            "/oc-rpol:statement/oc-rpol:conditions" +
            "/oc-bgp-pol:bgp-conditions/oc-bgp-pol:state" +
            "/oc-bgp-pol:next-hop-in" {
    deviate not-supported;
    description "Not supported in this release.";
  }

  deviation "/oc-rpol:routing-policy/oc-rpol:policy-definitions" +
            "/oc-rpol:policy-definition/oc-rpol:statements" +
            "/oc-rpol:statement/oc-rpol:conditions" +
            "/oc-bgp-pol:bgp-conditions/oc-bgp-pol:config" +
            "/oc-bgp-pol:afi-safi-in" {
    deviate not-supported;
    description "Not supported in this release.";
  }

  deviation "/oc-rpol:routing-policy/oc-rpol:policy-definitions" +
            "/oc-rpol:policy-definition/oc-rpol:statements" +
            "/oc-rpol:statement/oc-rpol:conditions" +
            "/oc-bgp-pol:bgp-conditions/oc-bgp-pol:state" +
            "/oc-bgp-pol:afi-safi-in" {
    deviate not-supported;
    description "Not supported in this release.";
  }

  deviation "/oc-rpol:routing-policy/oc-rpol:policy-definitions" +
            "/oc-rpol:policy-definition/oc-rpol:statements" +
            "/oc-rpol:statement/oc-rpol:conditions" +
            "/oc-bgp-pol:bgp-conditions/oc-bgp-pol:community-count" {
    deviate not-supported;
    description "Not supported in this release.";
  }

  deviation "/oc-rpol:routing-policy/oc-rpol:policy-definitions" +
            "/oc-rpol:policy-definition/oc-rpol:statements" +
            "/oc-rpol:statement/oc-rpol:actions" +
            "/oc-bgp-pol:bgp-actions/oc-bgp-pol:set-ext-community" +
            "/oc-bgp-pol:inline/oc-bgp-pol:config" +
            "/oc-bgp-pol:ext-communities" {
    deviate replace {
      type arc-oc-bgp-types:bgp-extcomm-type;
    }
    description "Use bgp-extcomm-type.";
  }

  deviation "/oc-rpol:routing-policy/oc-rpol:policy-definitions" +
            "/oc-rpol:policy-definition/oc-rpol:statements" +
            "/oc-rpol:statement/oc-rpol:actions" +
            "/oc-bgp-pol:bgp-actions/oc-bgp-pol:set-ext-community" +
            "/oc-bgp-pol:inline/oc-bgp-pol:config" +
            "/oc-bgp-pol:ext-communities" {
    deviate add {
      max-elements 32;
    }
    description "Up to 32 members of bgp-extcomm-type.";
  }

  deviation "/oc-rpol:routing-policy/oc-rpol:policy-definitions" +
            "/oc-rpol:policy-definition/oc-rpol:statements" +
            "/oc-rpol:statement/oc-rpol:actions" +
            "/oc-bgp-pol:bgp-actions/oc-bgp-pol:set-community" +
            "/oc-bgp-pol:inline/oc-bgp-pol:config" +
            "/oc-bgp-pol:communities" {
    deviate replace {
      type union {

        /*
         * Exclude 0x00000000 - 0x0000FFFF and 0xFFFF0000 - 0xFFFFFFFF
         * in string. Allow full range of uint32 for vendor compatibility
         */
        type uint32;
        type string {
          pattern '(6553[0-4]|655[0-2][0-9]|654[0-9]{2}|65[0-4][0-9]{2}'  +
                  '|6[0-4][0-9]{3}|[1-5][0-9]{4}|[1-9][0-9]{1,3}|[1-9]):' +
                  '(6553[0-5]|655[0-2][0-9]|654[0-9]{2}|65[0-4][0-9]{2}'  +
                  '|6[0-4][0-9]{3}|[1-5][0-9]{4}|[1-9][0-9]{1,3}|[0-9])';
        }
        type oc-bgp-types:bgp-well-known-community-type;
      }
    }
    description
      "Replacement of type due to OpenConfig non-compliance with YANG
       1.0/1.1 pattern statement";
  }

  deviation "/oc-rpol:routing-policy/oc-rpol:policy-definitions" +
            "/oc-rpol:policy-definition/oc-rpol:statements" +
            "/oc-rpol:statement/oc-rpol:actions" +
            "/oc-bgp-pol:bgp-actions/oc-bgp-pol:set-community" +
            "/oc-bgp-pol:inline/oc-bgp-pol:config" +
            "/oc-bgp-pol:communities" {
    deviate add {
      max-elements 32;
    }
    description "Up to 32 members only";
  }

    deviation "/oc-rpol:routing-policy/oc-rpol:policy-definitions" +
            "/oc-rpol:policy-definition/oc-rpol:statements" +
            "/oc-rpol:statement/oc-rpol:actions" +
            "/oc-bgp-pol:bgp-actions/oc-bgp-pol:config/oc-bgp-pol:set-med" {
    deviate replace {
      type uint32;
    }
    description "Replace the supported set-med type.";
  }
}
