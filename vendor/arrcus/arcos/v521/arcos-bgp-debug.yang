module arcos-bgp-debug {
  yang-version 1.1;
  namespace "http://yang.arrcus.com/arcos/bgp/debug";
  prefix arc-bgp-dbg;

  import ietf-inet-types {
    prefix oc-inet;
  }

  import openconfig-interfaces {
    prefix oc-if;
  }

  typedef bgp-debug-state {
    type enumeration {
      enum off {
        description
          "Disable debug";
      }
      enum on {
        description
          "Enable debug";
      }
    }
  }

  typedef bgp-debug-type {
    type enumeration {
      enum fsm {
        description
          "BGP FSM debugs";
      }
      enum events {
        description
          "BGP Events debugs";
      }
      enum updates {
        description
          "BGP Updates debugs";
      }
      enum updates-in {
        description
          "BGP Updates In debugs";
      }
      enum updates-out {
        description
          "BGP Updates Out debugs";
      }
      enum prefix {
        description
          "BGP Prefix debugs";
      }
      enum keepalives {
        description
          "BGP Keepalives debugs";
      }
      enum rpol {
        description
          "BGP RPOL debugs";
      }
      enum packets {
        description
          "BGP packets debugs";
      }
      enum neighbors {
        description
          "BGP neighbors debugs";
      }
      enum rib {
        description
          "BGP rib debugs";
      }
      enum cleanup {
        description
          "BGP cleanup debugs";
      }
      enum rtr {
        description
          "BGP rtr debugs";
      }
      enum erpl {
        description
          "BGP eRPL debugs";
      }
      enum erpl-lib {
        description
          "eRPL client library debugs";
      }
      enum route-import {
        description
          "BGP route import debugs";
      }
      enum route-export {
        description
          "BGP route export debugs";
      }
      enum label {
        description
          "BGP label debugs";
      }
      enum commands {
        description
          "BGP commands debugs";
      }
      enum ha {
        description
          "BGP HA debugs";
      }
      enum netlink {
        description
          "BGP netlink debugs";
      }
      enum tunnel {
        description
          "BGP tunnel debugs";
      }
      enum container-lib {
        description
          "BGP container library debugs";
      }
      enum attrs {
        description
          "BGP attributes debugs";
      }
      enum protection-trackers {
        description
          "BGP Protection tracker debugs";
      }
      enum pfcp {
        description
          "BGP pfcp debugs";
      }
      enum all {
        description
          "BGP All debugs";
      }
    }
  }

  container bgp-debug {
    description
      "BGP debug control";

    action protocol {
      input {
        leaf debug {
          type bgp-debug-type;
          mandatory true;
          description
            "Debug to be controlled";
        }

        leaf op {
          type bgp-debug-state;
          mandatory true;
          description
            "Turn on/off operation";
        }
      }
      output {
        leaf result {
          type string;
          description
            "The status of operation";
        }
      }
    }

    action neighbor {
      input {
        leaf address {
          type union {
            type oc-inet:ip-address;
	    //            type leafref {
	    //              path "/oc-if:interfaces/oc-if:interface/oc-if:name";
	    //            }
          }
          description
            "Address of the BGP peer, either in IPv4 or IPv6, or un-numbered interface name";
        }

        leaf op {
          type bgp-debug-state;
          mandatory true;
          description
            "Turn on/off operation";
        }
      }
      output {
        leaf result {
          type string;
          description
            "The status of operation";
        }
      }
    }
  }

  grouping bgp-debugs-state {
    description
      "BGP debugs information";

    leaf debug-flag {
      type bgp-debug-type;
      description
        "BGP Debug flags such as events, updates, fsm etc";
    }

    leaf enabled {
      type boolean;
      description
        "Indicates whether the debug flag is enabled or not";
    }
  }

  grouping bgp-show-debug-top {
    container bgp-show-debugs {
      description
        "BGP show debugs information";

      list bgp-debug {
        key "debug-flag";

        description
          "BGP debugs information";

        leaf debug-flag {
          type leafref {
            path "../state/debug-flag";
          }
          description
            "BGP Debug flags such as events, updates, fsm etc";
        }

        container state {
          uses bgp-debugs-state;
        }
      }
    }
  }
}
