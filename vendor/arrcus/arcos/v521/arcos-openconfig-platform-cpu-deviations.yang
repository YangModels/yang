module arcos-openconfig-platform-cpu-deviations {
  yang-version 1.1;
  namespace "http://yang.arrcus.com/arcos/openconfig/platform/cpu/deviations";
  prefix arc-oc-platform-cpu-dev;

  import openconfig-platform {
    prefix oc-platform;
  }

  import openconfig-platform-cpu {
    prefix oc-platform-cpu;
  }

  organization
    "Arrcus, Inc.";

  contact
    "Email: eng@arrcus.com";

  description
    "This module defines deviation statements for Arrcus
     implemention of the openconfig platform module.";

  revision 2018-08-14 {
    description "ArcOS release 2.2.1";
  }

  revision 2017-07-10 {
    description
      "Initial Revision
       * xxx not supcpued.
      ";

    reference
      "RFC 6020: YANG - A Data Modeling Language for the
       Network Configuration Protocol (NETCONF)";
  }

  deviation "/oc-platform:components/oc-platform:component/oc-platform:cpu/oc-platform-cpu:utilization" {
    deviate not-supported;
    description "Not supported in this release";
  }
}
