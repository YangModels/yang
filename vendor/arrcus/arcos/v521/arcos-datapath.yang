module arcos-datapath {

  yang-version "1.1";

  namespace "http://yang.arrcus.com/arcos/datapath";

  prefix "arcos-dp";

  import arcos-platform {prefix arc-platform;}
  import arcos-datapath-types { prefix arcos-dp-types; }
  import arcos-datapath-aft { prefix "arcos-aft"; }
  import arcos-datapath-nexthop { prefix "arcos-nh"; }
  import arcos-datapath-tunnel { prefix "arcos-tnl"; }
  import arcos-datapath-queues { prefix "arcos-queues"; }
  import arcos-datapath-asic { prefix "arcos-asic"; }

  organization
    "XXXX - TBD - XXXX";

  contact
    "XXXX - TBD - XXXX";

  description
    "A model describing the various datapath instances in the system. A
     datapath instance is an entity that deals with packet processing at
     some level. Examples are network processors, application specific
     integrated circuits (ASICs), software forwarding instances and so
     on. Each datapath instance may be responsible for one more functions like
     packet forwarding, packet filtering (ACLs), QoS, tunnel encapsulations
     and so on. This model defines a datapath instance under which various
     feature/function subtrees can be defined to represent read-only state.";

  grouping datapath-instance-state {
    description
      "Grouping for datapath instance state.";

    leaf name {
      type string;
      description
        "Datapath instance name.";
    }

    leaf type {
      type identityref {
        base arcos-dp-types:ARCOS_DATAPATH_TYPE;
      }
      description
        "Type of datapath instance.";
    }
  }

  grouping forwarding-instance-state {
    description
      "This grouping describes forwarding state of a network instance";

    leaf name {
      type string;
      description
        "Network instance name.";
    }
    uses arcos-aft:aft-top;
  }

  grouping datapath-forwarding {
    description
      "This grouping is used to add containers for datapath features under
       a datapath instance.";

    container forwarding {
      list network-instance {
        key "name";
        description
          "Network instances configured on the local system";

        leaf name {
          type leafref {
            path "../state/name";
          }
          description
            "References the network instance name.";
        }
        container state {
          description
            "Operational forwarding state for a network instance";
          uses forwarding-instance-state;
        }
      }
      uses arcos-nh:nexthop-top;
      uses arcos-tnl:tunnel-top;
    }
  }

  grouping queues-top {
    description
      "Top-level grouping for queueing specific objects.";
    uses arcos-queues:voq-top;

  }

  grouping datapath-top {
    description
      "Top-level grouping for datapath instances.";

    container datapath-instances {
      config false;
      description
        "Top level container for all datapath instances.";

      list datapath-instance {
        key "name";
        description
        "List of datapath instances in the system keyed by name.";

        leaf name {
          type leafref {
            path "../state/name";
          }
          description
            "References the datapath instance name.";
        }
        container state {
          description
            "Operational state data for each datapath instance";
          uses datapath-instance-state;
        }
        uses datapath-forwarding;

        uses queues-top {
            when " ((/arc-platform:platform/arc-platform:family = 'arc-platform:BROADCOM_DNX') or "
               + "  (/arc-platform:platform/arc-platform:deployment-type = 'arc-platform:DISTRIBUTED'))";
        }

        uses arcos-asic:asic-pkt-count;
        uses arcos-asic:external-tcam-counter-top;
      }
    }
  }
  uses datapath-top;
}
