module arcos-system-logging-types {
  yang-version 1.1;
  namespace "http://yang.arrcus.com/arcos/system/logging/types";
  prefix arc-sys-log-types;

  organization
    "Arrcus, Inc.";

  contact
    "Arrcus, Inc.
     2077 Gateway Place
     Suite 400
     San Jose, CA 95110

     E-mail: yang-support@arrcus.com";

  description
    "This module defines native ArcOS system logging
     types.

     Copyright (c) 2016-2019 by Arrcus, Inc.
     All rights reserved.";


  revision 2020-02-26 {
    description "Initial version";
  }

  identity LOG_TIMESTAMP_FORMAT {
    description
      "Base identity for logging timestamp formats";
  }

  identity TRADITIONAL {
    base LOG_TIMESTAMP_FORMAT;
    description
      "RFC3164 Traditional timestamp format";
  }

  identity PRECISION {
    base LOG_TIMESTAMP_FORMAT;
    description
      "RFC3339 High precision timestamp format";
  }

}
