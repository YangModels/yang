module arcos-sync-e {
  yang-version 1.1;
  namespace "http://yang.arrcus.com/arcos/sync-e/";
  prefix arc-sync-e;

  import tailf-common {
    prefix tailf;
  }

  import openconfig-interfaces {
    prefix oc-if;
  }

  import ietf-yang-types {
    prefix yang;
  }

  import arcos-features {
    prefix arc-features;
  }

  import ietf-interfaces {
    prefix if;
    reference
      "RFC 8343: A YANG Data Model for Interface Management";
  }

  organization
    "Arrcus, Inc";

  contact
    "Arrcus, Inc.
     2077 Gateway Place
     Suite 400
     San Jose, CA 95110
     E-mail: yang-support@arrcus.com";

  description
    "This module lists arrcus sync-e related information.
     Copyright (c) 2023 by Arrcus, Inc.
     All rights reserved.";

  revision 2023-03-24 {
    description
      "Add sync-e configuration";
  }

  grouping sync-e-state {
    leaf sync-e-clock-state {
      config false;
      type enumeration {
        enum free-run {
          value 0;
          description "Clock is in free-run state";
        }
        enum holdover {
          value 1;
          tailf:code-name "synce-holdover";
          description "Clock is in holdover state";
        }
        enum locked {
          value 2;
          description "Clock is in locked state";
        }
      }
      description
        "SyncE clock state";
    }
    leaf synce-state-duration {
      config false;
      type string;
      description 
        "Duration of current SyncE Clock state.";
    }
    leaf dpll-clock-state {
      config false;
      type enumeration {
        enum free-run {
          value 0;
          description "DPLL Clock is in free-run state";
        }
        enum holdover {
          value 1;
          tailf:code-name "dpll-holdover";
          description "DPLL Clock is in holdover state";
        }
        enum fastlock {
          value 2;
          description "DPLL Clock is in fastlock state";
        }
        enum acquiring {
          value 3;
          description "DPLL Clock is in aquiring state";
        }
        enum locked {
          value 4;
          tailf:code-name "dpll-locked";
          description "DPLL Clock is in locked state";
        }
      }
      description
        "DPLL (Digital Phase Locked Loop) clock state.";
    }
  }

  container sync-e {
    leaf enabled {
      type boolean;
      default false;
      description 
        "Enable / Disable SyncE.";
    }
    leaf holdover {
      type uint32 {
        range 0..1440;
      }
      default 10;
      units "minutes";
      description
        "Set synchronous holdover time in minutes.";
    }
    leaf quality-level-enabled {
      type boolean;
      default true;
      description 
        "Enable / Disable quality level parameters.";
    }
    leaf revertive-enabled {
      type boolean;
      default true;
      description 
        "Configure revertive mode.";
    }
    leaf synchronization-network-option {
      type enumeration {
        enum option-1 {
          value 1;
        }
        enum option-2 {
          value 2;
        }
      }
      description
        "The Network synchronization networking options.
        Values for this enumeration are specified
        in G.781.";
      reference
        "ITU-T G.781-2017: 5.3.1";
    }
    leaf interface-name {
        config false;
        type if:interface-ref;
        description
            "SyncE interface which got selected as source,
            if not then interface which was configured as input sources will be displayed.";
    }
    leaf esmc-status {
        config false;
        type string;
        description
          "ESMC(Ethernet Synchronization messaging Channel) Interface status";
    }
    leaf is-selected-source {
        config false;
        type boolean;
        default true;
        description
          "ESMC(Ethernet Synchronization messaging Channel) Interface is selected as input source or not";
    }
    leaf ql-received {
        config false;
        type string;
        description
            "Quality-level received on interface.";
    }
    uses sync-e-state; 
  }

  grouping ptp-interface-sync-e-top {
    container sync-e {
      leaf enabled {
        type boolean;
        default false;
        description 
          "Enable / Disable synchronous mode on interface.";
      }
      leaf wait-to-restore {
        type uint8 {
          range 0..12;
        }
        default 5;
        units "minutes";
        description 
          "Configure wait to restore timer in minutes";
      }
      leaf clock-source-id {
        type uint8 {
          range 1..max;
        }
        description 
          "Specify Clock-Source ID";
      }
      leaf holdoff {
        type uint16 {
          range 300..1800;
        }
        default 300;
        units "milliseconds";
        description 
          "Enter hold-off timer value in milliseconds";
      }
      leaf input-source {
        type int32 {
          range -1..max;
        }
        default -1;
        description 
          "Configure input sources.
           Highest priority is 1, lowest is 255, and 0 will
           exclude the interface from the clock selection.
           Use -1 to disable the input source on the specific interface.";
      }
      leaf mode-lockout {
        type boolean;
        default false;
        description 
          "Enable / Disable the external command lockout.";
      }
      leaf mode-synchronous {
        type boolean;
        default false;
        description 
          "Enable / Disable Synchronous Mode.";
      }
      leaf set-output-source {
        type boolean;
        default false;
        description 
          "Set ethernet interface as a timing output source.";
      }
      leaf quality-level {
        type enumeration {
          enum QL_DNU {
            value 2;
          }
          enum QL_PRC {
            value 24;
          }
          enum QL_SEC {
            value 28;
          }
          enum QL_SSU_A {
            value 30;
          }
          enum QL_SSU_B {
            value 31;
          }
        }
        description
          "Configure clock source QL (quality level) as defined in ITU-T G.781.";
        reference
          "ITU-T standard G.781 section 5.4";
      }
    }
  }

  augment "/oc-if:interfaces/oc-if:interface" {
    uses ptp-interface-sync-e-top {
      when "/arc-features:features/arc-features:feature[arc-features:name=" +
           "'arc-features:ARCOS_PTP_BOUNDARY_CLOCK']/arc-features:supported = 'true'";
    }
  }
}
