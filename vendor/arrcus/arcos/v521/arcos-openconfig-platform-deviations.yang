module arcos-openconfig-platform-deviations {
  yang-version 1.1;
  namespace "http://yang.arrcus.com/arcos/openconfig/platform/deviations";
  prefix arc-oc-platform-dev;

  import openconfig-platform {
    prefix oc-platform;
  }

  import openconfig-platform-port {
    prefix oc-platform-port;
  }

  import openconfig-platform-cpu {
    prefix oc-platform-cpu;
  }

  import openconfig-platform-psu {
    prefix oc-platform-psu;
  }

  import openconfig-platform-ext {
    prefix oc-platform-ext;
  }

  organization
    "Arrcus, Inc.";

  contact
    "Arrcus, Inc.
     Customer Service
     Postal: 2077 Gateway Place
     San Jose, CA 95110
     Tel: +1 408 884-1965
     E-mail: yang-support@arrcus.com";

  description
    "This module defines deviation statements for Arrcus
     implemention of the openconfig platform module.

     Copyright (c) 2016-2022 by Arrcus, Inc.
     All rights reserved.";

  revision 2022-11-08 {
    description
      "Add deviate not-supported statements for multiple platform model
       nodes that are unsupported. Cleanup commented out stmts.
       Update contact information in file header.";
  }

  revision 2018-08-14 {
    description "ArcOS release 2.2.1";
  }

  revision 2017-07-10 {
    description
      "Initial Revision
       * xxx not supported.
      ";

    reference
      "RFC 6020: YANG - A Data Modeling Language for the
       Network Configuration Protocol (NETCONF)";
  }

  deviation "/oc-platform:components/oc-platform:component/" +
            "oc-platform:config" {
    deviate not-supported;
    description "Not supported in this release";
  }
  deviation "/oc-platform:components/oc-platform:component/" +
            "oc-platform:state/oc-platform:empty" {
    deviate not-supported;
    description "Not supported in this release";
  }
  deviation "/oc-platform:components/oc-platform:component/" +
            "oc-platform:state/oc-platform:oper-status" {
    deviate not-supported;
    description "Not supported in this release";
  }
  deviation "/oc-platform:components/oc-platform:component/oc-platform:state/" +
            "oc-platform:name" {
    deviate not-supported;
    description "Not supported in this release";
  }
  deviation "/oc-platform:components/oc-platform:component/oc-platform:state/" +
            "oc-platform:temperature" {
    deviate not-supported;
    description "Not supported in this release";
  }
  deviation "/oc-platform:components/oc-platform:component/oc-platform:state/" +
            "oc-platform:parent" {
    deviate not-supported;
    description "Not supported in this release";
  }
  deviation "/oc-platform:components/oc-platform:component/oc-platform:state/" +
            "oc-platform:location" {
    deviate not-supported;
    description "Not supported in this release";
  }
  deviation "/oc-platform:components/oc-platform:component/oc-platform:state/" +
            "oc-platform:mfg-date" {
    deviate not-supported;
    description "Not supported in this release";
  }
  deviation "/oc-platform:components/oc-platform:component/oc-platform:state/" +
            "oc-platform:hardware-version" {
    deviate not-supported;
    description "Not supported in this release";
  }
  deviation "/oc-platform:components/oc-platform:component/oc-platform:state/" +
            "oc-platform:firmware-version" {
    deviate not-supported;
    description "Not supported in this release";
  }
  deviation "/oc-platform:components/oc-platform:component/oc-platform:state/" +
            "oc-platform:memory" {
    deviate not-supported;
    description "Not supported in this release";
  }
  deviation "/oc-platform:components/oc-platform:component/oc-platform:state/" +
            "oc-platform:allocated-power" {
    deviate not-supported;
    description "Not supported in this release";
  }
  deviation "/oc-platform:components/oc-platform:component/oc-platform:state/" +
            "oc-platform:used-power" {
    deviate not-supported;
    description "Not supported in this release";
  }
  deviation "/oc-platform:components/oc-platform:component/oc-platform:properties/oc-platform:property/oc-platform:state/" +
            "oc-platform:configurable" {
    deviate not-supported;
    description "Not supported in this release";
  }
  deviation "/oc-platform:components/oc-platform:component/oc-platform:properties/oc-platform:property/oc-platform:state/" +
            "oc-platform:name" {
    deviate not-supported;
    description "Not supported in this release";
  }
  deviation "/oc-platform:components/oc-platform:component/oc-platform:state/" +
            "oc-platform:mfg-name" {
    deviate not-supported;
    description "Not supported in this release";
  }
  deviation "/oc-platform:components/oc-platform:component/oc-platform:state/" +
            "oc-platform:software-version" {
    deviate not-supported;
    description "Not supported in this release";
  }
  deviation "/oc-platform:components/oc-platform:component/oc-platform:state/" +
            "oc-platform:serial-no" {
    deviate not-supported;
    description "Not supported in this release";
  }
  deviation "/oc-platform:components/oc-platform:component/oc-platform:state/" +
            "oc-platform:part-no" {
    deviate not-supported;
    description "Not supported in this release";
  }
  deviation "/oc-platform:components/oc-platform:component/oc-platform:properties/oc-platform:property/oc-platform:config" {
    deviate not-supported;
    description "Not supported in this release";
  }
  //deviation "/oc-platform:components/oc-platform:component/oc-platform:config" {
   // deviate not-supported;
    //description "Not supported in this release";
  //}
  deviation "/oc-platform:components/oc-platform:component/oc-platform:chassis" {
    deviate not-supported;
    description "Not supported in this release";
  }
  deviation "/oc-platform:components/oc-platform:component/oc-platform:port/oc-platform-port:breakout-mode" {
    deviate not-supported;
    description "Not supported in this release";
  }
  deviation "/oc-platform:components/oc-platform:component/oc-platform:port/oc-platform:config" {
    deviate not-supported;
    description "Not supported in this release";
  }
  deviation "/oc-platform:components/oc-platform:component/oc-platform:port/oc-platform:state" {
    deviate not-supported;
    description "Not supported in this release";
  }
  deviation "/oc-platform:components/oc-platform:component/oc-platform:port" {
    deviate not-supported;
    description "Not supported in this release";
  }
  deviation "/oc-platform:components/oc-platform:component/oc-platform:power-supply/oc-platform:config/oc-platform-psu:enabled" {
    deviate not-supported;
    description "Not supported in this release";
  }
  deviation "/oc-platform:components/oc-platform:component/oc-platform:power-supply/oc-platform:config" {
    deviate not-supported;
   description "Not supported in this release";
  }
 // deviation "/oc-platform:components/oc-platform:component/oc-platform-transceiver:transceiver" {
  //  deviate not-supported;
   // description "Not supported in this release";
 // }
  //deviation "/oc-platform:components/oc-platform:component/oc-platform-transceiver:transceiver/oc-platform-transceiver:index" {
   // deviate not-supported;
    //description "Not supported in this release";
 // }
 // deviation "/oc-platform:components/oc-platform:component/oc-platform-transceiver:transceiver/oc-platform-transceiver:state/oc-platform-transceiver:pre-fec-ber" {
  //  deviate not-supported;
  //  description "Not supported in this release";
 // }
  //deviation "/oc-platform:components/oc-platform:component/oc-platform-transceiver:transceiver/oc-platform-transceiver:state/oc-platform-transceiver:post-fec-ber" {
   // deviate not-supported;
   // description "Not supported in this release";
 // }
 // deviation "/oc-platform:components/oc-platform:component/oc-platform-transceiver:transceiver/oc-platform-transceiver:state/oc-platform-transceiver:output-power" {
 //   deviate not-supported;
 //   description "Not supported in this release";
 // }
 // deviation "/oc-platform:components/oc-platform:component/oc-platform-transceiver:transceiver/oc-platform-transceiver:state/oc-platform-transceiver:input-power" {
 //   deviate not-supported;
 //   description "Not supported in this release";
 // }
 // deviation "/oc-platform:components/oc-platform:component/oc-platform-transceiver:transceiver/oc-platform-transceiver:state/oc-platform-transceiver:laser-bias-current" {
 //   deviate not-supported;
 //   description "Not supported in this release";
 // }
 // deviation "/oc-platform:components/oc-platform:component/oc-platform-transceiver:transceiver/oc-platform-transceiver:physical-channels" {
 //   deviate not-supported;
 //   description "Not supported in this release";
 // }
  deviation "/oc-platform:components/oc-platform:component/oc-platform:fan/oc-platform:config" {
    deviate not-supported;
    description "Not supported in this release";
  }
  //deviation "/oc-platform:components/oc-platform:component/oc-platform:config/oc-platform:power-supply/oc-platform:state/oc-platform:psu/oc-platform:config" {
   // deviate not-supported;
    //description "Not supported in this release";
  //}
  deviation "/oc-platform:components/oc-platform:component/oc-platform:fabric/oc-platform:config" {
    deviate not-supported;
    description "Not supported in this release";
  }
  deviation "/oc-platform:components/oc-platform:component/oc-platform:storage" {
    deviate not-supported;
    description "Not supported in this release";
  }
  deviation "/oc-platform:components/oc-platform:component/oc-platform:cpu/oc-platform-cpu:utilization" {
    deviate not-supported;
    description "Not supported in this release";
  }
  deviation "/oc-platform:components/oc-platform:component/oc-platform:cpu/oc-platform:state" {
    deviate not-supported;
    description "Not supported in this release";
  }
  deviation "/oc-platform:components/oc-platform:component/oc-platform:cpu/oc-platform:config" {
    deviate not-supported;
    description "Not supported in this release";
  }
  deviation "/oc-platform:components/oc-platform:component/oc-platform:cpu" {
    deviate not-supported;
    description "Not supported in this release";
  }
  deviation "/oc-platform:components/oc-platform:component/oc-platform:integrated-circuit" {
    deviate not-supported;
    description "Not supported in this release";
  }
  deviation "/oc-platform:components/oc-platform:component/oc-platform:backplane" {
    deviate not-supported;
    description "Not supported in this release";
  }
  //deviation "/oc-platform:components/oc-platform:component/oc-platform-linecard:linecard/oc-platform-linecard:config" {
  //  deviate not-supported;
  //  description "Not supported in this release";
 // }
  deviation "/oc-platform:components/oc-platform:component/oc-platform:subcomponents/oc-platform:subcomponent/oc-platform:config" {
    deviate not-supported;
    description "Not supported in this release";
  }
  deviation "/oc-platform:components/oc-platform:component/oc-platform:name" {
    deviate replace {
        type string;
    }
  }
  deviation "/oc-platform:components/oc-platform:component/oc-platform:properties/oc-platform:property/oc-platform:name" {
    deviate replace {
        type string;
    }
  }
  deviation "/oc-platform:components/oc-platform:component/oc-platform:subcomponents/oc-platform:subcomponent/oc-platform:name" {
    deviate replace {
        type string;
    }
  }
  deviation "/oc-platform:components/oc-platform:component/oc-platform:subcomponents/oc-platform:subcomponent/oc-platform:config/oc-platform:name" {
    deviate replace {
        type string;
    }
  }
  deviation "/oc-platform:components/oc-platform:component/oc-platform:subcomponents/oc-platform:subcomponent/oc-platform:state/oc-platform:name" {
    deviate replace {
        type string;
    }
  }
  deviation "/oc-platform:components/oc-platform:component/oc-platform:subcomponents/oc-platform:subcomponent/oc-platform:name" {
    deviate replace {
        config false;
    }
  }
  deviation "/oc-platform:components/oc-platform:component/oc-platform:subcomponents/oc-platform:subcomponent" {
    deviate replace {
        config false;
    }
  }
  deviation "/oc-platform:components/oc-platform:component/oc-platform:subcomponents" {
    deviate replace {
        config false;
    }
  }
  deviation "/oc-platform:components/oc-platform:component/oc-platform:properties/oc-platform:property/oc-platform:name" {
    deviate replace {
        config false;
    }
  }
  deviation "/oc-platform:components/oc-platform:component/oc-platform:properties/oc-platform:property" {
    deviate replace {
        config false;
    }
  }
  deviation "/oc-platform:components/oc-platform:component/oc-platform:properties" {
    deviate replace {
        config false;
    }
  }
  deviation "/oc-platform:components/oc-platform:component/oc-platform:name" {
    deviate replace {
        config false;
    }
  }
  deviation "/oc-platform:components/oc-platform:component" {
    deviate replace {
        config false;
    }
  }
  deviation "/oc-platform:components" {
    deviate replace {
        config false;
    }
  }
  deviation "/oc-platform:components/oc-platform:component/oc-platform:power-supply" {
    deviate replace {
        config false;
    }
  }
}
