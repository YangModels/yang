module arcos-system-types {
  yang-version 1.1;
  namespace "http://yang.arrcus.com/arcos/system/types";
  prefix arc-sys-types;

  import iana-crypt-hash {
    prefix ianach;
  }

  import tailf-common {
    prefix tailf;
  }

  organization
    "Arrcus, Inc.";

  contact
    "Arrcus, Inc.
     2077 Gateway Place
     Suite 400
     San Jose, CA 95110

     E-mail: yang-support@arrcus.com";

  description
    "This module defines native ArcOS system
     types.

     Copyright (c) 2016-2019 by Arrcus, Inc.
     All rights reserved.";

  revision 2022-09-30 {
    description
      "Added typedef tls-versions";
  }

  revision 2019-10-01 {
    description "Initial version";
  }

  typedef user-password {
    type ianach:crypt-hash {
      pattern
        '[a-zA-Z0-9\s!"#$'
      + "'"
      + '%&\(\)\*\+,\-\./:;<=>\?@\[\\\]^_|`{}~]{6,128}'
      + '|$6$(rounds=\d+$)?[a-zA-Z0-9./]{1,16}$[a-zA-Z0-9./]{86}';
    }
  }

  typedef encrypted-string {
    type tailf:aes-cfb-128-encrypted-string;
  }

  typedef ssh-cipher-suite {
    type enumeration {
      enum AES128_CBC {
        description
          "128-bit AES with Cipher Block Chaining";
      }
      enum AES192_CBC {
        description
          "192-bit AES with Cipher Block Chaining";
      }
      enum AES256_CBC {
        description
          "256-bit AES with Cipher Block Chaining";
      }
      enum "RIJNDAEL_CBC@LYSATOR.LIU.SE" {
        description
          "Rijndael/AES with Cipher Block Chaining";
      }
      enum AES128_CTR {
        description
          "128-bit AES with Counter Mode";
      }
      enum AES192_CTR {
        description
          "192-bit AES with Counter Mode";
      }
      enum AES256_CTR {
        description
          "256-bit AES with Counter Mode";
      }
      enum "AES128_GCM@OPENSSH.COM" {
        description
          "128-bit AES with Galois/Counter Mode";
      }
      enum "AES256_GCM@OPENSSH.COM" {
        description
          "256-bit AES with Galois/Counter Mode";
      }
      enum "CHACHA20_POLY1305@OPENSSH.COM" {
        description
          "ChaCha20 stream cipher and Poly1305 MAC";
      }
    }
  }

  typedef ssh-mac-suite {
    type enumeration {
      enum HMAC_SHA1 {
        description
          "Hash-based MAC using SHA1";
      }
      enum HMAC_SHA1_96 {
        description
          "96-bit Hash-based MAC using SHA1";
      }
      enum HMAC_SHA2_256 {
        description
          "256-bit Hash-based MAC using SHA2";
      }
      enum HMAC_SHA2_512 {
        description
          "512-bit Hash-based MAC using SHA2";
      }
      enum HMAC_MD5 {
        description
          "Hash-based MAC using MD5";
      }
      enum HMAC_MD5_96 {
        description
          "96-bit Hash-based MAC using MD5";
      }
      enum "UMAC_64@OPENSSH.COM" {
        description
          "64-bit Universal Hash-based MAC";
      }
      enum "UMAC_128@OPENSSH.COM" {
        description
          "128-bit Universal Hash-based MAC";
      }
      enum "HMAC_SHA1_ETM@OPENSSH.COM" {
        description
          "Hash-based MAC using SHA1 - Encrypt-then-MAC";
      }
      enum "HMAC_SHA1_96_ETM@OPENSSH.COM" {
        description
          "96-bit Hash-based MAC using SHA1 - Encrypt-then-MAC";
      }
      enum "HMAC_SHA2_256_ETM@OPENSSH.COM" {
        description
          "256-bit Hash-based MAC using SHA2 - Encrypt-then-MAC";
      }
      enum "HMAC_SHA2_512_ETM@OPENSSH.COM" {
        description
          "512-bit Hash-based MAC using SHA2 - Encrypt-then-MAC";
      }
      enum "HMAC_MD5_ETM@OPENSSH.COM" {
        description
          "Hash-based MAC using MD5 - Encrypt-then-MAC";
      }
      enum "HMAC_MD5_96_ETM@OPENSSH.COM" {
        description
          "96-bit Hash-based MAC using MD5 - Encrypt-then-MAC";
      }
      enum "UMAC_64_ETM@OPENSSH.COM" {
        description
          "64-bit Universal Hash-based MAC - Encrypt then MAC";
      }
      enum "UMAC_128_ETM@OPENSSH.COM" {
        description
          "128-bit Universal Hash-based MAC - Encrypt then MAC";
      }
    }
  }

  identity MM_ACTIVATION_MODE {
    description
      "Base identity for maintenance mode activation config.";
  }
  identity TIMER {
    base MM_ACTIVATION_MODE;
    description
      "Maintenance mode activation based on timer.";
  }
  identity HEURISTICS {
    base MM_ACTIVATION_MODE;
    description
      "Maintenance mode activation based on heuristics.";
  }
  identity MM_STATE {
    description
	    "Base type for maintenance mode state.";
  }
  identity UNKNOWN {
    base MM_STATE;
    description
      "Maintenance mode state unknown";
  }
  identity ENABLE_ACK_RCVD {
    base MM_STATE;
    description
      "Maintenance mode start received and processed.";
  }
  identity DISABLE_ACK_RCVD {
    base MM_STATE;
    description
      "Maintenance mode stop received and processed.";
  }
  identity DEACTIVATION_IN_PROGRESS {
    base MM_STATE;
    description
      "Maintenance mode stop received and in progress.";
  }
  identity ACTIVATION_IN_PROGRESS {
    base MM_STATE;
    description
      "Maintenance mode start received and in progress.";
  }
  identity PROFILING {
    base MM_STATE;
    description
      "Maintenance mode start ack received and profiling in progress.";
  }
  identity ENABLED {
    base MM_STATE;
    description
      "Maintenance mode enabled.";
  }
  identity READY {
    base MM_STATE;
    description
      "Maintenance mode activated.";
  }
  identity DISABLED {
    base MM_STATE;
    description
      "Maintenance mode disabled.";
  }
  identity FAILED {
    base MM_STATE;
    description
      "Maintenance mode activation failed at the profiling level";
  }
  identity TIMEOUT {
    base MM_STATE;
    description
      "Maintenance mode activation failed during the control plane activation phase.";
  }

  identity SNMP_AUTH_TYPE {
    description
      "Base identity for SNMP Authentication Hash Algorithms";
  }

  identity SNMP_AUTH_NONE {
    base SNMP_AUTH_TYPE;
    description
      "No Authentication Protocol";
  }

  identity SNMP_AUTH_MD5 {
    base SNMP_AUTH_TYPE;
    description
      "The HMAC-MD5-96 Digest Authentication Protocol";
  }

  identity SNMP_AUTH_SHA {
    base SNMP_AUTH_TYPE;
    description
      "The HMAC-SHA-96 Digest Authentication Protocol";
  }

  identity SNMP_PRIV_TYPE {
    description
      "Base identity for SNMP Privacy Ciphers";
  }

  identity SNMP_PRIV_NONE {
    base SNMP_PRIV_TYPE;
    description
      "No Privacy Ciphers";
  }

  identity SNMP_PRIV_DES {
    base SNMP_PRIV_TYPE;
    description
      "The CBC-DES Symmetric Encryption Protocol";
  }

  identity SNMP_PRIV_AES {
    base SNMP_PRIV_TYPE;
    description
      "The CFB128-AES-128 Privacy Protocol";
  }

  typedef tls-versions {
    type enumeration {
      enum DEFAULT {
        description
          "Specifies that TLS protocol versions tlsv1.2 tlsv1.1 are to be used by the
           server in that order of preference.";
      }

      enum TLS_1.1 {
        description
          "Version 1.1 of TLS Protocol";
      }

      enum TLS_1.2 {
        description
          "Version 1.2 of TLS Protocol";
      }
    }
  }
}
