module arcos-openconfig-vlan-augments {
  yang-version 1.1;
  namespace "http://yang.arrcus.com/arcos/openconfig/vlan/augments";
  prefix arc-oc-vlan-aug;


  import ietf-yang-types { prefix yang; }
  import ietf-inet-types { prefix inet; }
  import openconfig-vlan {prefix oc-vlan; }
  import openconfig-yang-types { prefix oc-yang; }
  import openconfig-interfaces {prefix oc-if; }
  import openconfig-vlan-types { prefix oc-vlan-types; }

  organization
    "Arrcus, Inc.";
  contact
    "Arrcus, Inc.
     2077 Gateway Place
     Suite 400
     San Jose, CA 95110
     E-mail: yang-support@arrcus.com";
  description
    "This module defines augments statements for the
     for OpenConfig vlan module.
     Copyright (c) 2016-2023 by Arrcus, Inc.
     All rights reserved.";

  revision 2023-03-31 {
    description
      "Adds vlan match any support";
  }

  revision 2023-03-13 {
    description
      "Add double-tagged support";
  }

  grouping vlan-egress-default-tpid-config {
    description
      "TPID configuration for dot1q-enabled interfaces";

    leaf egress-default-tpid {
      type identityref {
        base oc-vlan-types:TPID_TYPES;
      }
      default oc-vlan-types:TPID_0X8100;
      description
        "Optionally set the tag protocol identifier field (TPID) that
        is accepted on the VLAN";
    }
  }

  grouping vlan-double-map-config {
    description
      "TPID configuration for dot1q-enabled interfaces";
    
    leaf inner-tpid {
      type identityref {
        base oc-vlan-types:TPID_TYPES;
      }
      description
              "Set the tag protocol identifier field (TPID)";
    }
    leaf inner-vlan-id {
      type oc-vlan-types:vlan-id;
      description
        "Set the inner vlan-id";
    }
  }

  grouping vlan-match-any-node {
      leaf any {
          type empty;
          description
              "Match any packet with or without VLAN tags.";
      }
  }

  grouping vlan-match-any-top {
      container match-any {
          description
              "Match any packet with or without VLAN tags.";
          container config {
              uses vlan-match-any-node;
          }
          container state {
              config false;
              uses vlan-match-any-node;
          }
      }
  }

  augment "/oc-if:interfaces/oc-if:interface/oc-if:config" {
    description
      "Adds default egress TPID / ethertype setting for the base interface";

    uses vlan-egress-default-tpid-config;
  }

  augment "/oc-if:interfaces/oc-if:interface/oc-if:state" {
    description
      "Adds TPID / ethertype opstate for the base interface";

    uses vlan-egress-default-tpid-config;
  }

  augment "/oc-if:interfaces/oc-if:interface/oc-if:subinterfaces/oc-if:subinterface/" +
          "oc-vlan:vlan/oc-vlan:ingress-mapping/oc-vlan:config" {
    uses vlan-double-map-config;
  }
  augment "/oc-if:interfaces/oc-if:interface/oc-if:subinterfaces/oc-if:subinterface/" +
          "oc-vlan:vlan/oc-vlan:ingress-mapping/oc-vlan:state" {
    uses vlan-double-map-config;
  }

  augment "/oc-if:interfaces/oc-if:interface/oc-if:subinterfaces/oc-if:subinterface/" +
          "oc-vlan:vlan/oc-vlan:egress-mapping/oc-vlan:config" {
    uses vlan-double-map-config;
  }
  augment "/oc-if:interfaces/oc-if:interface/oc-if:subinterfaces/oc-if:subinterface/" +
          "oc-vlan:vlan/oc-vlan:egress-mapping/oc-vlan:state" {
    uses vlan-double-map-config;
  }

  augment "/oc-if:interfaces/oc-if:interface/oc-if:subinterfaces/oc-if:subinterface/" +
          "oc-vlan:vlan/oc-vlan:match" {
    uses vlan-match-any-top;
  }
}
