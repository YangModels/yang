module arcos-if-qos-service-tablemap {
  yang-version 1.1;
  namespace "http://yang.arrcus.com/arcos/interface/qos/service-tablemap";
  prefix arc-if-qos-svc-tbl;

  import arcos-qos {
    prefix arc-qos;
  }
  import arcos-qos-tablemap {
    prefix arc-qos-tbl;
  }
  import arcos-if-qos {
    prefix arc-if-qos;
  }
  import iana-if-type {
    prefix ianaift;
  }
  import openconfig-system {
    prefix oc-sys;
  }
  import openconfig-interfaces {
    prefix oc-if;
  }
  import openconfig-if-ethernet {
    prefix oc-eth;
  }
  import openconfig-if-aggregate {
    prefix oc-lag;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for qos specific tablemap instance on interfaces";

  grouping service-tablemap-attributes {
    description
      "Grouping that defines service instance of a tablemap";
    leaf direction {
      type enumeration {
        enum INGRESS {
          description
            "for incoming traffic";
        }
        enum EGRESS {
          description
            "for outgoing traffic";
        }
      }
      description
        "direction of traffic this service-tablemap takes effect on";
    }
    leaf name {
      type leafref {
        path "/arc-qos:qos/arc-qos-tbl:tablemaps/arc-qos-tbl:tablemap/arc-qos-tbl:name";
      }
      mandatory true;
      description
        "Name of a tablemap to be instantiated";
    }
  }

  grouping service-tablemaps-top {
    description
      "Main top-level grouping for generic definition of tablemap service instances";
    container service-tablemaps {
      description
        "Set of tablemap service instances configured";
      list service-tablemap {
        key "direction";
        description
          "A specific tablemap service instance";
        leaf direction {
          type leafref {
            path "../config/direction";
          }
          description
            "direction of traffic, service instance applicable to";
        }
        container config {
          description
            "Configuration parameters relating to tablemap service instance";
          uses service-tablemap-attributes;
        }
        container state {
          config false;
          description
            "Operational state parameters relating to tablemap service instance";
          uses service-tablemap-attributes;
        }
      }
    }
  }

  augment "/oc-if:interfaces/oc-if:interface/arc-if-qos:qos" {
    uses service-tablemaps-top {
      when "((current()/../oc-if:name != 'ma1') and "
         + " ((current()/../oc-if:config/oc-if:type = 'ianaift:ieee8023adLag') or "
         + " ((current()/../oc-if:config/oc-if:type = 'ianaift:ethernetCsmacd') and (boolean(current()/../oc-eth:ethernet/oc-eth:config/oc-lag:aggregate-id) != 'true'))))";
    }
    description
      "Augmenting tablemap service instance list under an interface";
  }

  augment "/oc-if:interfaces/oc-if:interface/oc-if:subinterfaces/oc-if:subinterface/arc-if-qos:qos" {
    uses service-tablemaps-top {
      when "((current()/../../../oc-if:config/oc-if:type = 'ianaift:ieee8023adLag') or " +
           " ((current()/../../../oc-if:config/oc-if:type = 'ianaift:ethernetCsmacd') and (boolean(current()/../../../oc-eth:ethernet/oc-eth:config/oc-lag:aggregate-id) != 'true')))";
    }
  }
  
  grouping system-qos-top {
    description
      "Top level grouping for system-based QoS";
    container qos {
      description
        "Quality of Service";
      uses service-tablemaps-top;
    }
  }

  augment "/oc-sys:system" {
    uses system-qos-top;
  }
}
