module tailf-tls {
  yang-version 1.1;
  namespace "http://tail-f.com/ns/tls";
  prefix tls;

  import ietf-netconf-acm {
    prefix nacm;
  }
  import ietf-x509-cert-to-name {
    prefix x509c2n;
  }
  import ietf-yang-types {
    prefix yang;
  }
  import tailf-common {
    prefix tailf;
  }

  organization "Tail-f Systems";

  description
    "This module contains configuration items for TLS key storage for HTTP
     based protocols, i.e. Web UI and RESTCONF.

     If the webui ssl transport conf section is enabled and configured to fetch
     TLS data from the database, the web server fetch these values upon start
     or reload. For further details see the Web UI chapter Web server section
     TLS data in database.

     Copyright 2019 Cisco Systems, Inc.
     All rights reserved.
     Permission is hereby granted to redistribute this file without
     modification.";

  revision 2019-06-13 {
    description
      "Initial revision, released as part of ConfD-7.3 / NCS-5.3.";
  }

  typedef tls-private-key {
    tailf:info "TLS Privaty Key";
    type tailf:aes-cfb-128-encrypted-string;
  }

  typedef tls-certificate {
    tailf:info "TLS Public Key Certificate";
    type binary;
  }

  typedef tls-ca-certificate {
    tailf:info "TLS CA Certificate";
    type binary;
  }

  container tls {
    presence "";
    nacm:default-deny-all;
    tailf:info "Global TLS keystore configuration";
    tailf:code-name tls_container;

    container private-key {
      leaf key-data {
        type tls-private-key;
        mandatory true;
        tailf:typepoint tls-mgmt-private-key;
        tailf:cli-multi-line-prompt;
        tailf:validate tls_mgmt {
          tailf:internal;
          tailf:dependency ".";
        }
        description
          "The binary data for the private key, in PEM format (text starting
           with '-----BEGIN ...-----'). If the key is encrypted, the
           passphrase for the key must be configured via 'passphrase'.

           Encrypted keys must be in PKCS#1 format and supported encryption
           algorithms are: RC2-CBC, DES-CBC, DES-EDE3-CBC, and AES-128-CBC.

           If the key is not encrypted both PKCS#1 and PKCS#8 formats can be
           used.";
      }
      leaf passphrase {
        tailf:info "Passphrase for key";
        type tailf:aes-cfb-128-encrypted-string;
        tailf:suppress-echo "true";
        description
          "The value of this leaf is used as passphrase for the key if
           it is encrypted.";
      }
    }

    container certificate {
      leaf cert-data {
        type tls-certificate;
        mandatory true;
        tailf:typepoint tls-mgmt-certificate;
        tailf:cli-multi-line-prompt;
        tailf:validate tls_mgmt {
          tailf:internal;
          tailf:dependency ".";
        }
        description
          "The binary data for the public key certificate, in PEM format
           (text starting with '-----BEGIN ...-----').";
      }
      leaf fingerprint {
        config false;
        type x509c2n:tls-fingerprint;
        tailf:callpoint tls_mgmt {
          tailf:internal;
        }
        tailf:info "SHA256 fingerprint of certificate.";
        description
          "SHA256 fingerprint of certificate. NB! First octet represents which
           hash algorithm is used, i.e. SHA256 (0x04),
           see x509c2n:tls-fingerprint.";
      }
    }

    list ca-certificates {
      key name;
      leaf name {
        type string;
      }
      leaf cacert-data {
        type tls-ca-certificate;
        tailf:typepoint tls-mgmt-ca-certificate;
        tailf:cli-multi-line-prompt;
        tailf:validate tls_mgmt {
          tailf:internal;
          tailf:dependency ".";
        }
        description
          "The binary data for the CA certificate, in PEM format (text starting
           with '-----BEGIN ...-----').";
      }
      leaf fingerprint {
        config false;
        type x509c2n:tls-fingerprint;
        tailf:callpoint tls_mgmt {
          tailf:internal;
        }
        tailf:info "SHA256 fingerprint of CA certificate.";
        description
          "SHA256 fingerprint of CA certificate. NB! First octet represents
           which hash algorithm is used, i.e. SHA256 (0x04), see
           x509c2n:tls-fingerprint.";
      }
    }
  }
}
