module arcos-openconfig-segment-routing-augments {
  yang-version 1.1;
  namespace "http://yang.arrcus.com/arcos/openconfig/segment-routing/augments";
  prefix arc-oc-sr-aug;

  /*
   * Import basic things
   */
  import openconfig-network-instance { prefix oc-netinst; }

  organization
    "Arrcus, Inc.";

  description
    "YANG data-model for openconfig-segment-routing augment";

  grouping srgb-used-labels {
    leaf-list used-labels {
      type uint32;
      description
        "List of labels that have already been allocated by protocols
        referencing the SRGB.";
    }
  }
  
  augment "/oc-netinst:network-instances/oc-netinst:network-instance" +
          "/oc-netinst:segment-routing/oc-netinst:srgbs/oc-netinst:srgb/oc-netinst:state" {
    uses srgb-used-labels;
  }

  grouping srlb-used-labels {
    leaf-list used-labels {
      type uint32;
      description
        "List of labels that have already been allocated by protocols
        referencing the SRLB.";
    }
  }

  grouping srlb-state {
    description
      "Operational state parameters relating to the SRLB.";

    leaf size {
      type uint32;
      description
        "The total number of SRLB entries that are available within the SRLB.";
    }

    leaf used {
      type uint32;
      description
        "The total number of SRLB entries that have already been allocated by
        protocols referencing the SRLB.";
    }
  }

  augment "/oc-netinst:network-instances/oc-netinst:network-instance" +
          "/oc-netinst:segment-routing/oc-netinst:srlbs/oc-netinst:srlb/oc-netinst:state" {
    uses srlb-state;
    uses srlb-used-labels;
  }

}
