module arcos-mmu-clear {
  yang-version 1.1;
  namespace "http://yang.arrcus.com/arcos/mmu/clear";
  prefix arc-mmu-clr;

  container mmu-buffer-stats {
    description
      "Clear MMU buffer statistics";

    action all {
      description
        "Clear all MMU buffer statistics";

      output {
        leaf result {
          type string;
          description
            "The status of the Clear operation";
        }
      }
    }
  }
}
