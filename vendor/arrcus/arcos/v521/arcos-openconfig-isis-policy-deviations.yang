module arcos-openconfig-isis-policy-deviations {
  yang-version 1.1;
  namespace "http://yang.arrcus.com/arcos/openconfig/isis-policy/deviations";
  prefix arc-oc-isis-pol-dev;

  import openconfig-routing-policy {
    prefix oc-rpol;
  }

  import openconfig-isis-policy {
    prefix oc-isis-pol;
  }

  deviation "/oc-rpol:routing-policy/oc-rpol:policy-definitions" +
            "/oc-rpol:policy-definition/oc-rpol:statements" +
            "/oc-rpol:statement/oc-rpol:actions/oc-rpol:igp-actions" +
            "/oc-isis-pol:isis-actions/oc-isis-pol:config" +
            "/oc-isis-pol:set-metric-type" {
    deviate not-supported;
    description "Not supported in this release.";
  }
}
