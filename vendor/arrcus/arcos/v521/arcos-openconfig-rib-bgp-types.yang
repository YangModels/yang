module arcos-openconfig-rib-bgp-types {
  yang-version 1.1;
  namespace "http://yang.arrcus.com/arcos/openconfig/rib/bgp/types";

  prefix arc-oc-bgprib-types;

  import openconfig-rib-bgp-types {
    prefix oc-rib-bgp-types;
  }

  organization
    "Arrcus, Inc.";

  contact
    "Arrcus, Inc.
     Customer Service
     Postal: 2077 Gateway Place
     San Jose, CA 95110
     Tel: +1 1XXX XXX-XXXX
     E-mail: xxx@arrcus.com";

  description
    "This module defines augmentation for Arrcus
     implemention of the openconfig-rib-bgp-types module.";

  revision 2018-06-14 {
    description
      "Initial Revision
       * Add bgp large community
      ";

    reference
      "RFC 6020: YANG - A Data Modeling Language for the
       Network Configuration Protocol (NETCONF)";
  }

  identity SRTE_SRV6_BINDING_SID {
    base oc-rib-bgp-types:TUNNEL_ENCAPSULATION_SUBTLV_TYPE;
    description
      "Binding SID to be used by the SR-TE policy described
      by the tunnel encapsulation attribute.";
    reference
      "draft-previdi-idr-segment-routing-te-policy";
  }

  identity GTP_TUNNEL {
    base oc-rib-bgp-types:TUNNEL_ENCAPSULATION_TYPE;
    description
      "GTP tunnel";
  }

  identity TUNNEL_EGRESS_ENDPOINT {
    base oc-rib-bgp-types:TUNNEL_ENCAPSULATION_SUBTLV_TYPE;
    description
      "Tunnel egress endpoint address";
  }
}
