module arcos-copp-service-policy {
  yang-version 1.1;
  namespace "http://yang.arrcus.com/arcos/copp/service-policy";
  prefix arc-copp-svc-pol;

  import arcos-policy {
    prefix arc-pol;
  }
  import arcos-service-policy {
    prefix arc-svc-pol;
  }
  import arcos-policy-action {
    prefix arc-pol-actn;
  }
  import arcos-platform {
    prefix arc-platform;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for copp specific policy on control plane interface";


  grouping control-plane-service-policy-state {
    container state {
      config false;

      list service-policy {
        key "direction";
        uses arc-svc-pol:service-policy-attributes;
      }
    }
    description
      "Grouping to define COPP policy instance state";
  }

  augment "/control-plane/service-policies" {
    uses control-plane-service-policy-state;
  }

  augment "/control-plane/service-policies/state/service-policy" {
    uses arc-pol:policy-classifiers-state-top {
      refine "classifiers" {
        config false;
      }
    }
  }

  augment "/control-plane/service-policies/state/service-policy"
        + "/classifiers/classifier/actions/action" {
    uses arc-pol-actn:mark-top;
  }

  augment "/control-plane/service-policies/state/service-policy"
        + "/classifiers/classifier/actions/action/mark/state" {
    uses arc-pol-actn:mark-local-tc-top;
  }

  augment "/control-plane/service-policies/state/service-policy"
        + "/classifiers/classifier/actions/action" {
    uses arc-pol-actn:police-top;
  }

  augment "/control-plane/service-policies/state/service-policy"
        + "/classifiers/classifier/actions/action/police/state" {
    uses arc-pol-actn:police-stats-top;
  }

  grouping control-plane-top {
    container control-plane {
      uses arc-svc-pol:service-policies-top;
      description
        "Target to enable COPP policy instance";
    }
    description
      "Grouping to define target for COPP policy instance";
  }

  uses control-plane-top {
    refine "control-plane/service-policies/service-policy/direction" {
      must "current() = 'INGRESS'" {
        error-message "Egress policies not supported for copp";
      }
    }
  }
}
