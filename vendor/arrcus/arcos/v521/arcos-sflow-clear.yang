module arcos-sflow-clear {
  yang-version 1.1;
  namespace "http://yang.arrcus.com/arcos/sflow/clear";
  prefix arc-sflow-clr;

  import arcos-platform {
    prefix arc-platform;
  }

  grouping sflow-counters-top {
    container sflow-counters {
      description
        "Clear sFlow statistics";

      action all {
        description
          "Clear all sFlow statistics";

        output {
          leaf result {
            type string;
            description
              "The status of the clear operation";
          }
        }
      }
    }
  }

  uses sflow-counters-top {
    when "(/arc-platform:platform/arc-platform:asic = 'arc-platform:BROADCOM_TRIDENT3') or
          (/arc-platform:platform/arc-platform:asic = 'arc-platform:BROADCOM_TRIDENT2') or
          (/arc-platform:platform/arc-platform:asic = 'arc-platform:BROADCOM_TOMAHAWK') or
          (/arc-platform:platform/arc-platform:asic = 'arc-platform:BROADCOM_TOMAHAWK3') or
          (/arc-platform:platform/arc-platform:asic = 'arc-platform:BROADCOM_HELIX4') or
          (/arc-platform:platform/arc-platform:family = 'arc-platform:BROADCOM_DNX_JPLUS') or
          (/arc-platform:platform/arc-platform:family = 'arc-platform:BROADCOM_DNX') or
          (/arc-platform:platform/arc-platform:asic = 'arc-platform:X86_64') or
          (boolean(/arc-platform:platform/arc-platform:asic) != 'true')";
  }
}
