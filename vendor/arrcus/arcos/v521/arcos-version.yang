module arcos-version {
  yang-version 1.1;
  namespace "http://yang.arrcus.com/arcos/version";
  prefix arc-version;

  grouping platform-info {
    description
      "Top-level grouping for platform specific
       data nodes";

    leaf product-name {
      type string;
      description
        "Product name";
    }

    leaf serial-number {
      type string;
      description
        "Serial number";
    }

    leaf mac-address {
      type string;
      description
        "Device mac address";
    }

    leaf form-factor {
      type string;
      description
        "Form factor of device";
    }

    leaf num-cpu-cores {
      type uint8;
      description
        "Number of CPU cores";
    }

    leaf cpu-info {
      type string;
      description
        "Device CPU information";
    }

    leaf total-memory {
      type string;
      description
        "Total available CPU memory";
    }
  }

  grouping version-state {
    description
      "Top-level grouping for version specific state
       data nodes";

    uses platform-info;

    leaf sw-version {
      type string;
      description
        "Version number";
    }
  }

  grouping version-dependencies-state {
    description
      "Top-level grouping for version dependency state
       data nodes";

    leaf package {
      type string {
        length "1..31";
      }
      description
        "Package name";
    }

    leaf version {
      type string {
        length "1..31";
      }
      description
        "Package version";
    }
  }


  grouping version-dependencies-top {
    container dependencies {
      description
        "Dependency information";

      list dependency {
        key "package";

        description
          "Package information";

        leaf package {
          type leafref {
            path "../state/package";
          }
          description
            "Package name";
        }

        container state {
          uses version-dependencies-state;
        }
      }
    }
  }

  grouping version-top {
    description
      "Top-level grouping for version specific data";

    container version {

      config false;

      container state {
        description
          "Operational state for version specific data";

        uses version-state;
      }

      uses version-dependencies-top;
    }
  }

}
