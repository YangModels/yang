module arcos-openconfig-if-ip-augments {
  yang-version 1.1;
  namespace "http://yang.arrcus.com/arcos/openconfig/interfaces/ip/augments";
  prefix arc-oc-ip-aug;

  import openconfig-if-ip {
    prefix oc-ip;
  }

  import openconfig-interfaces {
    prefix oc-if;
  }

  import openconfig-yang-types {
    prefix oc-yang;
  }

  import ietf-inet-types {
    prefix inet;
  }

  revision 2022-09-13 {
    description
      "Add mac-learning for L2 sub interfaces";
  }

  typedef vrrp-proto-version {
    type enumeration {
      enum VRRP_V2 {
        description "VRRP protocol version 2.";
      }
      enum VRRP_V3 {
        description "VRRP protocol version 3.";
      }
      enum VRRP_V2_V3 {
        description "VRRP protocol version 2 and 3.";
      }
    }
  }
  grouping ipv6-ra-config {
    description
      "Configuration parameters for IPv6 router advertisements.";

    leaf interval {
      type uint32 {
        range "4..1800";
      }
      default 600;
      units seconds;
      description
        "The interval between periodic router advertisement neighbor
        discovery messages sent on this interface expressed in
        seconds.";
    }

    leaf lifetime {
      type uint32 {
        range "0..9000";
      }
      units seconds;
      must 'current() = 0 or current() > ../interval' {
        error-message "If lifetime is not 0, it must be greater than interval";
      }
      description
        "The lifetime advertised in RA messages sent on this interface
         (in seconds), value 0 means don't use as default router.";
    }

    leaf suppress {
      type boolean;
      default false;
      description
        "When set to true, router advertisement neighbor discovery
        messages are not transmitted on this interface.";
    }

    leaf virtual-router-only {
      type boolean;
      default false;
      description
        "When set to true, router advertisement neighbor discovery
        messages are only sent for VRRP virtual-routers on this interface.";
    }

    leaf managed-config-flag {
      type boolean;
      default false;
      description
        "When set to true, router advertisement neighbor discovery
         messages are sent with the Managed address configuration flag set.";
    }

    leaf other-config-flag {
      type boolean;
      default false;
      description
        "When set to true, router advertisement neighbor discovery
         messages are sent with the Other configuration flag set.";
    }
  }

  grouping ipv6-ra-top {
    description
      "Top-level grouping for IPv6 router advertisements ";

    container router-advertisement {
      description
        "Configuration and operational state parameters relating to
        router advertisements.";

      container config {
        description
          "Configuration parameters relating to router advertisements
          for IPv6.";
        uses ipv6-ra-config;
      }

      container state {
        config false;
        description
          "Operational state parameters relating to router
           advertisements for IPv6.";
        uses ipv6-ra-config;
      }
    }
  }

  grouping ipv6-ra-addr-config {
    description
      "Per IPv6 address prefix configuration parameters for router advertisements.";

    leaf auto-config-flag {
      type boolean;
      default false;
      description
        "When set to true, router advertisement neighbor discovery
         messages for this address prefix are sent with the autonomous
         configurationflag set.";
    }
  }

  grouping ipv6-ra-addr-top {
    description
      "Top-level grouping for IPv6 per address prefix router advertisements";

    container router-advertisement {
      description
        "Configuration and operational state parameters relating to
        per address prefix router advertisements";

      container config {
        description
          "Configuration parameters relating to per address prefix
          router advertisements for IPv6.";
        uses ipv6-ra-addr-config;
      }

      container state {
        config false;
        description
          "Operational state parameters relating to per address prefix
          router advertisements for IPv6.";
        uses ipv6-ra-addr-config;
      }
    }
  }

  grouping vrrp-group-ag-state-top {
    description
      "Additional leafs for VRRP Group State ";

    leaf virtual-router-mode {
      type enumeration {
        enum MASTER {
          description "Virtual Router is in MASTER mode.";
        }
        enum BACKUP {
          description "Virtual Router is in BACKUP mode.";
        }
      }
      description
        "The mode of this specific Virtual Group
         on the current Virtual Router";
    }

    leaf advertisement-sent {
      type uint64;
      description
        "Number of VRRP advertisements sent for this VRRP group";
    }

    leaf advertisement-received {
      type uint64;
      description
        "Number of VRRP advertisements received for this VRRP group";
    }

    leaf advertisement-dropped {
      type uint64;
      description
        "Number of VRRP advertisements dropped for this VRRP group";
    }

    leaf virtual-mac-address {
      type oc-yang:mac-address;
      description
        "VRRP virtual mac address. It is in the format 00-00-5E-00-01-{VRID}
         where VRID is the Virtual Router ID";
    }
  }

  augment "/oc-if:interfaces/oc-if:interface/oc-if:subinterfaces" +
          "/oc-if:subinterface/oc-ip:ipv6" {
    uses ipv6-ra-top;
  }

  augment "/oc-if:interfaces/oc-if:interface/oc-if:subinterfaces" +
          "/oc-if:subinterface/oc-ip:ipv6/oc-ip:addresses/oc-ip:address" {
    uses ipv6-ra-addr-top;
  }

  grouping neighbor-config {
    description
      "Configuration parameters for neighbors.";
    leaf neighbor-timeout {
      description
        "neighbor time out in seconds.";
      type uint32 {
        range "60..65535";
      }
      units seconds;
      default 14400;
    }
  }

  augment "/oc-if:interfaces/oc-if:interface/oc-if:subinterfaces" +
          "/oc-if:subinterface/oc-ip:ipv4/oc-ip:config" {
    uses neighbor-config;
  }

  augment "/oc-if:interfaces/oc-if:interface/oc-if:subinterfaces" +
          "/oc-if:subinterface/oc-ip:ipv4/oc-ip:state" {
    uses neighbor-config;
  }

  augment "/oc-if:interfaces/oc-if:interface/oc-if:subinterfaces" +
          "/oc-if:subinterface/oc-ip:ipv6/oc-ip:config" {
    uses neighbor-config;
  }

  augment "/oc-if:interfaces/oc-if:interface/oc-if:subinterfaces" +
          "/oc-if:subinterface/oc-ip:ipv6/oc-ip:state" {
    uses neighbor-config;
  }

  augment "/oc-if:interfaces/oc-if:interface/oc-if:subinterfaces" +
          "/oc-if:subinterface/oc-ip:ipv4/oc-ip:addresses/oc-ip:address" +
          "/oc-ip:vrrp/oc-ip:vrrp-group/oc-ip:config" {
    leaf vrrp-version {
      description
        "Version of VRRP version to be enabled for this VRRP group.";
      type vrrp-proto-version;
      default "VRRP_V3";
    }
  }

  augment "/oc-if:interfaces/oc-if:interface/oc-if:subinterfaces" +
          "/oc-if:subinterface/oc-ip:ipv4/oc-ip:addresses/oc-ip:address" +
          "/oc-ip:vrrp/oc-ip:vrrp-group/oc-ip:state" {
    leaf vrrp-version {
      description
        "Version of VRRP version to be enabled for this VRRP group.";
      type vrrp-proto-version;
    }
  }

  augment "/oc-if:interfaces/oc-if:interface/oc-if:subinterfaces" +
          "/oc-if:subinterface/oc-ip:ipv4/oc-ip:addresses/oc-ip:address" +
          "/oc-ip:vrrp/oc-ip:vrrp-group/oc-ip:state" {
    uses vrrp-group-ag-state-top;
  }

  augment "/oc-if:interfaces/oc-if:interface/oc-if:subinterfaces" +
          "/oc-if:subinterface/oc-ip:ipv6/oc-ip:addresses/oc-ip:address" +
          "/oc-ip:vrrp/oc-ip:vrrp-group/oc-ip:state" {
    uses vrrp-group-ag-state-top;
  }

  augment "/oc-if:interfaces/oc-if:interface/oc-if:subinterfaces/" +
    "oc-if:subinterface/oc-ip:ipv4/oc-ip:addresses/oc-ip:address/oc-ip:config" {
    leaf label-index {
      type uint32;
      description
      "Label index - Parameter related to Segment Routing";
    }
  }

  augment "/oc-if:interfaces/oc-if:interface/oc-if:subinterfaces/" +
    "oc-if:subinterface/oc-ip:ipv4/oc-ip:addresses/oc-ip:address/oc-ip:state" {
    leaf label-index {
      type uint32;
      description
      "Label index - Parameter related to Segment Routing";
    }
  }

  augment "/oc-if:interfaces/oc-if:interface/oc-if:subinterfaces/" +
    "oc-if:subinterface/oc-ip:ipv6/oc-ip:addresses/oc-ip:address/oc-ip:config" {
    leaf label-index {
      type uint32;
      description
      "Label index - Parameter related to Segment Routing";
    }
  }

  augment "/oc-if:interfaces/oc-if:interface/oc-if:subinterfaces/" +
    "oc-if:subinterface/oc-ip:ipv6/oc-ip:addresses/oc-ip:address/oc-ip:state" {
    leaf label-index {
      type uint32;
      description
      "Label index - Parameter related to Segment Routing";
    }
  }

  augment "/oc-if:interfaces/oc-if:interface/oc-if:subinterfaces/" +
    "oc-if:subinterface/oc-ip:ipv4/oc-ip:addresses/oc-ip:address/oc-ip:config" {
    leaf secondary {
      type empty;
      must "(count(/oc-if:interfaces/oc-if:interface/oc-if:subinterfaces/oc-if:subinterface/oc-ip:ipv4/oc-ip:addresses/oc-ip:address) > 1)" {
          error-message "Cannot delete the primary IP address from interface as the secondary IP config exists";
      }
      description "Indicates whether the IP address is a primary or a secondary IP address";
    }
  }

  augment "/oc-if:interfaces/oc-if:interface/oc-if:subinterfaces/" +
    "oc-if:subinterface/oc-ip:ipv4/oc-ip:addresses/oc-ip:address/oc-ip:state" {
    leaf secondary {
      type empty;
      description "Indicates whether the IP address is a primary or a secondary IP address";
    }
  }

  grouping ipv6-link-local-address {
    description
      "IPv6 link-local address for the interface.";

    leaf ipv6-link-local {
      type inet:ipv6-address-no-zone;
      description
        "[adapted from IETF IP model RFC 7277]

         The IPv6 link-local address on the
         interface.";
    }
  }

  grouping dynamic-address-top {
    description
      "Subinterface data for logical interfaces
       associated with a physical interface.";

    container dynamic {
      config false;
      description
        "Enclosing container for the list of subinterfaces
         associated with a physical interface.";
      uses ipv6-link-local-address;
    }
  }

  augment "/oc-if:interfaces/oc-if:interface/oc-if:subinterfaces/" +
    "oc-if:subinterface/oc-if:state" {
    uses dynamic-address-top;
  }

  grouping subinterface-config {
    leaf mac-learning {
      type boolean;
      default true;
      when "current()/../../oc-ip:ipv4/oc-ip:config/oc-ip:enabled = 'false' and " +
           "current()/../../oc-ip:ipv6/oc-ip:config/oc-ip:enabled = 'false'";
      description
        "When this leaf is set to true, MAC learning is enabled for
        the subinterface, such that MAC addresses are learned
        from ingress frames and added to the FDB.";
    }
  }

  grouping subinterface-state {
    leaf mac-learning {
      type boolean;
      when "current()/../../oc-ip:ipv4/oc-ip:config/oc-ip:enabled = 'false' and " +
           "current()/../../oc-ip:ipv6/oc-ip:config/oc-ip:enabled = 'false'";
      description
        "Operation value of mac learning for this subinterface";
    }
  }

  augment "/oc-if:interfaces/oc-if:interface/oc-if:subinterfaces/" +
          "oc-if:subinterface/oc-if:config" {
    uses subinterface-config;
  }

  augment "/oc-if:interfaces/oc-if:interface/oc-if:subinterfaces/" +
          "oc-if:subinterface/oc-if:state" {
    uses subinterface-state;
  }
}
