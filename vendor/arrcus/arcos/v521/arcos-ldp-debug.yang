/**
 * Filename: arcos-ldp-debug.yang
 *
 * Description:
 * YANG data-model for LDP Debugs Action 
 *
 * Copyright 2019 by Arrcus, Inc.
 * All rights reserved.
 */

module arcos-ldp-debug {
  namespace "http://yang.arrcus.com/arcos/ldp/debug";

  prefix arc-ldp-debug;

  import ietf-inet-types { prefix inet; }
  import openconfig-types { prefix "oc-types"; }
  import ietf-interfaces { prefix ietf-if; }
  import tailf-common { prefix tailf; }

  organization
    "Arrcus, Inc.";

  contact
    "Lalit";

  description
    "YANG data-model for LDP Debugs definitions.";

  typedef ldp-debug-state {
    type enumeration { 
      enum on {
        description
          "Enable debug";
      }
      enum off {
        description
          "Disable debug";
      }
    }
  }

  typedef ldp-debug-type {
    type enumeration { 
      enum ldp {
        description
          "Control ldp debugs";
      }
      enum ldp-engine {
        description
          "Control ldp-engine debugs";
      }
      enum session {
        description
          "Control ldp session debugs";
      }
      enum all {
        description
          "Control All debugs";
      }
    }
  }

  container ldp-debug {
    description
      "LDP debug control";
    tailf:action debug {
      tailf:cli-operational-mode;
      tailf:cli-mount-point "tech-support";
      tailf:actionpoint ldp-debug-point;
      input {
        leaf type {
        type ldp-debug-type;
        mandatory true;
          description
          "Debug to be controlled";
        }
        leaf op {
        type ldp-debug-state;
        mandatory true;
          description
          "turn on/off operation";
        }
      }
      output {
        leaf result {
        type string;
          description
          "The status of operation"; 
        }
      }
    }
  }
}
