module arcos-ospf {

  yang-version "1.1";

  namespace "http://yang.arrcus.com/arcos/ospf";

  prefix "arc-ospf";

  import openconfig-extensions { prefix "oc-ext"; }
  import openconfig-network-instance { prefix "oc-netinst"; }
  import openconfig-policy-types { prefix "oc-pol-types"; }

  // Include submodules
  include arcos-ospf-common;
  include arcos-ospf-statistics;
  include arcos-ospf-spf;
  include arcos-ospf-rib;
  include arcos-ospf-global;
  include arcos-ospf-as;
  include arcos-ospf-area;
  include arcos-ospf-area-interface;
  include arcos-ospf-aggregate;

  description
    "A model for Open Shortest Path First (OSPF) protocol";

  // OpenConfig specific extensions for module metadata.
  oc-ext:regexp-posix;

  grouping ospfv2-top {
    description
      "Top-level OSPFv2 configuration and operational state";

    container ospfv2 {
      description
        "Top-level configuration and operational state for
        Open Shortest Path First (OSPF) v2";

      uses ospf-global-structure;
      uses ospf-as-scope-structure;
      uses ospf-areas-structure;
    }
  }

  grouping ospfv3-top {
    description
      "Top-level OSPFv3 configuration and operational state";

    container ospfv3 {
      description
        "Top-level configuration and operational state for
        Open Shortest Path First (OSPF) v3";

      uses ospf-global-structure;
      uses ospf-as-scope-structure;
      uses ospf-areas-structure;
    }
  }


  /*
   * Augment: network-instances network-instance protocols protocol
   */
  augment "/oc-netinst:network-instances/oc-netinst:network-instance" +
          "/oc-netinst:protocols/oc-netinst:protocol" {

    uses ospfv2-top {
      when "oc-netinst:config/oc-netinst:identifier = 'oc-pol-types:OSPF'" {
        description
          "Include ospfv2 only when protocol is OSPF.";
      }

      description
        "OSPFv2 protocol";
    }
  }

  /*
   * Augment: network-instances network-instance protocols protocol
   */
  augment "/oc-netinst:network-instances/oc-netinst:network-instance" +
          "/oc-netinst:protocols/oc-netinst:protocol" {

    uses ospfv3-top {
      when "oc-netinst:config/oc-netinst:identifier = 'oc-pol-types:OSPF3'" {
        description
          "Include ospfv3 only when protocol is OSPF3.";
      }

      description
        "OSPFv3 protocol";
    }
  }
}
