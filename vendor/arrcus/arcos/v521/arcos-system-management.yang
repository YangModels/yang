module arcos-system-management {
  yang-version 1.1;
  namespace "http://yang.arrcus.com/arcos/system/management";
  prefix arc-sys-mgmt;

  import openconfig-system-logging {
    prefix oc-sys-log;
  }

  import arcos-system-types {
    prefix arc-sys-types;
  }

  organization
    "Arrcus, Inc.";

  contact
    "Arrcus, Inc.
     2077 Gateway Place
     Suite 400
     San Jose, CA 95110

     E-mail: yang-support@arrcus.com";

  description
    "This module contains definitions for the
     native ArcOS system management domain.

     Copyright (c) 2016-2019 by Arrcus, Inc.
     All rights reserved.";


  revision 2022-09-30 {
    description
      "Added leaf-list protocols under tls";
  }

  revision 2019-10-15 {
    description "Initial version";
  }

  grouping system-tls-config {
    description
      "";

    leaf certificate-file {
      type string {
        length "1..100";
      }
      default "/mnt/onl/config/pki/certificate";
      must 'boolean(../key-file)' {
        error-message
          "If certificate-file is configured, key-file must be configured";
      }
      description
        "Absolute file path of the server certificate";
    }

    leaf key-file {
      type string {
        length "1..100";
      }
      default "/mnt/onl/config/pki/key.pem";
      must 'boolean(../certificate-file)' {
        error-message
          "If key-file is configured, certificate-file must be configured";
      }
      description
        "Absolute file path to the corresponding private key file for the
         server certificate";
    }

    leaf-list protocols {
      type arc-sys-types:tls-versions;
      ordered-by user;
      default "DEFAULT";
      must "(not(../protocols = 'DEFAULT' and count(../protocols) > 1))" {
        error-message "'DEFAULT' and TLS protocol versions are mutually exclusive";
      }
      description
        "An ordered list of TLS protocol versions that the agent supports";
      }
  }

  grouping system-tls-top {
    description
      "Top-level grouping for system TLS attributes";

    container tls {
      description
        "Top-level container for TLS attributes";

      container config {
        description
          "Configuration data for TLS related attributes";

        uses system-tls-config;
      }

      container state {
        config false;

        description
          "Operational state data for TLS related attributes";

        uses system-tls-config;
      }
    }
  }

  grouping system-clients-state {
    description
      "Operational state data of connected clients";

    leaf-list paths {
      type string;
      description
        "Subscribed Paths";
    }
  }

  grouping system-clients-top {
    description
      "Top-level grouping for system client data";

    container clients {
      description
        "Top level container for connected clients";
      container state {
        config false;
        description
          "Operational state data for the clients";
        list client {
          leaf peer-address {
            type string;
            description
              "IP address and port of the connected client";
          }
          uses system-clients-state;
        }
      }
    }
  }

  grouping logType {
    description
      "Common log configuration parameters. These parameters
       take effect for both existing and new sessions.";
    container syslog {
      leaf enabled {
        type boolean;
        default "false";
        description
          "enabled is either 'true' or 'false'. If 'true', syslog
           messages are sent.";
      }
      leaf facility {
        type identityref {
          base oc-sys-log:SYSLOG_FACILITY;
        }
        must "derived-from-or-self(current(), 'oc-sys-log:SYSTEM_DEAMON') or " +
             "derived-from-or-self(current(), 'oc-sys-log:AUTHPRIV') or " +
             "derived-from-or-self(current(), 'oc-sys-log:LOCAL0') or " +
             "derived-from-or-self(current(), 'oc-sys-log:LOCAL1') or " +
             "derived-from-or-self(current(), 'oc-sys-log:LOCAL2') or " +
             "derived-from-or-self(current(), 'oc-sys-log:LOCAL3') or " +
             "derived-from-or-self(current(), 'oc-sys-log:LOCAL4') or " +
             "derived-from-or-self(current(), 'oc-sys-log:LOCAL5') or " +
             "derived-from-or-self(current(), 'oc-sys-log:LOCAL6') or " +
             "derived-from-or-self(current(), 'oc-sys-log:LOCAL7')" {
          error-message "audit log facility is either SYSTEM_DAEMON,
                         AUTHPRIV, LOCAL0, LOCAL1, LOCAL2, LOCAL3, LOCAL4,
                         LOCAL5, LOCAL6, LOCAL7";
        }
        description
          "facility is either 'daemon', 'authpriv',
           'local0', ..., 'local7'";
      }
    }
  }

  grouping audit-log-top {
    container auditLog {
      description
        "auditLog is an audit log recording successful and failed
         logins to the ConfD backplane and also user operations
         performed from the CLI or northbound interfaces. This log
         is enabled by default. This configuration parameter takes
         effect for both existing and new sessions.";
      uses logType;
    }
  }
}
