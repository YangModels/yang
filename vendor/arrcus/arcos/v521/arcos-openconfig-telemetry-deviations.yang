module arcos-openconfig-telemetry-deviations {
  yang-version 1.1;
  namespace "http://yang.arrcus.com/arcos/openconfig/telemetry/deviations";
  prefix arc-oc-telemetry-dev;

  import openconfig-telemetry {
    prefix oc-telemetry;
  }

  import ietf-inet-types {
    prefix inet;
  }

  organization
    "Arrcus, Inc.";

  contact
    "Arrcus, Inc.
     2077 Gateway Place
     Suite 400
     San Jose, CA 95110

     E-mail: yang-support@arrcus.com";

  description
    "This module defines ArcOS deviations to the
     OpenConfig telemetry module.

     Copyright (c) 2016-2019 by Arrcus, Inc.
     All rights reserved.";

  revision 2019-10-27 {
    description "Initial revision";
  }

  deviation "/oc-telemetry:telemetry-system/oc-telemetry:destination-groups" +
            "/oc-telemetry:destination-group/oc-telemetry:destinations" +
            "/oc-telemetry:destination/oc-telemetry:config/oc-telemetry:destination-address" {
    deviate replace {
      type union {
        type inet:ip-address;
        type inet:domain-name;
      }
    }
    description "To match internal implementation";
  }

  deviation "/oc-telemetry:telemetry-system/oc-telemetry:destination-groups" +
            "/oc-telemetry:destination-group/oc-telemetry:destinations" +
            "/oc-telemetry:destination/oc-telemetry:state/oc-telemetry:destination-address" {
    deviate replace {
      type union {
        type inet:ip-address;
        type inet:domain-name;
      }
    }
    description "To match internal implementation";
  }

  deviation "/oc-telemetry:telemetry-system/oc-telemetry:destination-groups" +
            "/oc-telemetry:destination-group" {
    deviate add {
      max-elements 3;
    }
    description "To match internal implementation";
  }

  deviation "/oc-telemetry:telemetry-system/oc-telemetry:destination-groups" +
            "/oc-telemetry:destination-group/oc-telemetry:destinations/oc-telemetry:destination" {
    deviate add {
      min-elements 1;
      max-elements 5;
    }
    description "To match internal implementation";
  }

  deviation "/oc-telemetry:telemetry-system/oc-telemetry:subscriptions" +
            "/oc-telemetry:persistent-subscriptions/oc-telemetry:persistent-subscription" {
    deviate add {
      max-elements 3;
    }
    description "To match internal implementation";
  }

  deviation "/oc-telemetry:telemetry-system/oc-telemetry:subscriptions" +
            "/oc-telemetry:persistent-subscriptions/oc-telemetry:persistent-subscription" +
            "/oc-telemetry:destination-groups/oc-telemetry:destination-group" {
    deviate add {
      min-elements 1;
      max-elements 1;
    }
    description "To match internal implementation";
  }

  deviation "/oc-telemetry:telemetry-system/oc-telemetry:sensor-groups" {
    deviate not-supported;
    description "Not supported in this release.";
  }

  deviation "/oc-telemetry:telemetry-system/oc-telemetry:subscriptions" +
            "/oc-telemetry:dynamic-subscriptions" {
    deviate not-supported;
    description "Not supported in this release.";
  }

  deviation "/oc-telemetry:telemetry-system/oc-telemetry:subscriptions" +
            "/oc-telemetry:persistent-subscriptions/oc-telemetry:persistent-subscription" +
            "/oc-telemetry:sensor-profiles" {
    deviate not-supported;
    description "Not supported in this release.";
  }

  deviation "/oc-telemetry:telemetry-system/oc-telemetry:subscriptions" +
            "/oc-telemetry:persistent-subscriptions/oc-telemetry:persistent-subscription" +
            "/oc-telemetry:config/oc-telemetry:local-source-address" {
    deviate not-supported;
    description "Not supported in this release.";
  }

  deviation "/oc-telemetry:telemetry-system/oc-telemetry:subscriptions" +
            "/oc-telemetry:persistent-subscriptions/oc-telemetry:persistent-subscription" +
            "/oc-telemetry:state/oc-telemetry:local-source-address" {
    deviate not-supported;
    description "Not supported in this release.";
  }

  deviation "/oc-telemetry:telemetry-system/oc-telemetry:subscriptions" +
            "/oc-telemetry:persistent-subscriptions/oc-telemetry:persistent-subscription" +
            "/oc-telemetry:config/oc-telemetry:originated-qos-marking" {
    deviate not-supported;
    description "Not supported in this release.";
  }

  deviation "/oc-telemetry:telemetry-system/oc-telemetry:subscriptions" +
            "/oc-telemetry:persistent-subscriptions/oc-telemetry:persistent-subscription" +
            "/oc-telemetry:state/oc-telemetry:id" {
    deviate not-supported;
    description "Not supported in this release.";
  }

  deviation "/oc-telemetry:telemetry-system/oc-telemetry:subscriptions" +
            "/oc-telemetry:persistent-subscriptions/oc-telemetry:persistent-subscription" +
            "/oc-telemetry:state/oc-telemetry:originated-qos-marking" {
    deviate not-supported;
    description "Not supported in this release.";
  }

  deviation "/oc-telemetry:telemetry-system/oc-telemetry:subscriptions" +
            "/oc-telemetry:persistent-subscriptions/oc-telemetry:persistent-subscription" +
            "/oc-telemetry:config/oc-telemetry:protocol" {
    deviate not-supported;
    description "Not supported in this release.";
  }

  deviation "/oc-telemetry:telemetry-system/oc-telemetry:subscriptions" +
            "/oc-telemetry:persistent-subscriptions/oc-telemetry:persistent-subscription" +
            "/oc-telemetry:state/oc-telemetry:protocol" {
    deviate not-supported;
    description "Not supported in this release.";
  }

  deviation "/oc-telemetry:telemetry-system/oc-telemetry:subscriptions" +
            "/oc-telemetry:persistent-subscriptions/oc-telemetry:persistent-subscription" +
            "/oc-telemetry:config/oc-telemetry:encoding" {
    deviate not-supported;
    description "Not supported in this release.";
  }

  deviation "/oc-telemetry:telemetry-system/oc-telemetry:subscriptions" +
            "/oc-telemetry:persistent-subscriptions/oc-telemetry:persistent-subscription" +
            "/oc-telemetry:state/oc-telemetry:encoding" {
    deviate not-supported;
    description "Not supported in this release.";
  }

}
