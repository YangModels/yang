module arcos-dpal {
  yang-version 1.1;
  namespace "http://yang.arrcus.com/arcos/dpal";
  prefix arc-dpal;

  grouping dpal-common {
    leaf state {
      type string;
    }
    list internal {
      key "attr-name attr-value";

      leaf attr-name {
        type string;
      }
      leaf attr-value {
        type string;
      }
    }
  }

  grouping dpal-stats {
    container stats {
      leaf total-creates {
        type uint64;
      }
      leaf total-placeholders {
        type uint64;
      }
      leaf total-deletes {
        type uint64;
      }
      leaf total-updates {
        type uint64;
      }
      leaf total-create-deferrals {
        type uint64;
      }
      leaf total-update-deferrals {
        type uint64;
      }
      leaf total-delete-deferrals {
        type uint64;
      }
      leaf total-create-failures {
        type uint64;
      }
      leaf total-update-failures {
        type uint64;
      }
      leaf total-delete-failures {
        type uint64;
      }
      leaf total-retries {
        type uint64;
      }
      leaf total-in-retry-q {
        type uint64;
      }
      leaf total-in-slow-retry-q {
        type uint64;
      }
    }
  }

  container dpal {
    description
      "Arrcus Data Plane Adaptation Layer - DPAL (tm) - internals";

    list object-type {
      key "object-type";

      config false;

      leaf object-type {
        type string;
      }

      uses dpal-stats;

      container generic-entries {
        list entry {
          key "key";

          leaf key {
            type string;
          }

          leaf key-octets {
            type binary;
          }

          uses dpal-common;

          list parent {
            key "parent-type parent-key";

            leaf parent-type {
              type string;
            }

            leaf parent-key {
              type string;
            }
          }

          list pending-parent {
            key "pending-parent-type pending-parent-key";

            leaf pending-parent-type {
              type string;
            }

            leaf pending-parent-key {
              type string;
            }
          }
        }
      }
    }
  }
}
