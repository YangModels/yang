module arcos-copp-service-policy-deviations {
  yang-version 1.1;
  namespace "http://yang.arrcus.com/arcos/copp/service-policy/deviations";
  prefix arc-copp-svc-pol-dev;

  import arcos-copp-service-policy {
    prefix arc-copp-svc-pol;
  }
  import arcos-copp {
    prefix arc-copp;
  }
  import arcos-copp-policy {
    prefix arc-copp-pol;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for control plane service-policy deviations";

  deviation "/arc-copp-svc-pol:control-plane/arc-copp-svc-pol:service-policies"
          + "/arc-copp-svc-pol:service-policy/arc-copp-svc-pol:config/arc-copp-svc-pol:name" {
    deviate replace {
      type leafref {
        path "/arc-copp:copp/arc-copp-pol:policies/arc-copp-pol:policy/arc-copp-pol:name";
      }
    }
  }
}
