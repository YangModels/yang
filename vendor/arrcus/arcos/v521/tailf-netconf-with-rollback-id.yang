module tailf-netconf-with-rollback-id {
  yang-version 1.1;
  namespace "http://tail-f.com/ns/netconf/with-rollback-id";
  prefix wrbid;

  import ietf-netconf {
    prefix nc;
  }

  import tailf-netconf-transactions {
    prefix tr;
  }

  import tailf-rollback {
    prefix rollback;
  }

  description
    "This module adds a parameter 'with-rollback-id' to the
     following rpcs:

       o  edit-config
       o  copy-config
       o  commit
       o  commit-transaction

     This parameter lets the client request that the id of the generate
     rollback file is returned in the reply to the request.

     Copyright 2020 Cisco Systems, Inc.
     All rights reserved.
     Permission is hereby granted to redistribute this file without
     modification.";

  revision 2020-06-25 {
    description
      "Initial revision.";
  }

  grouping with-rollback-id-params {
    leaf with-rollback-id {
      type empty;
    }
  }
  grouping with-rollback-id-reply {
    uses rollback:rollback-commit-result;
  }

  /*
   * RPC augmentations
   */
  augment '/nc:edit-config/nc:input' {
    uses with-rollback-id-params;
  }
  augment '/nc:edit-config/nc:output' {
    uses with-rollback-id-reply;
  }

  augment '/nc:copy-config/nc:input' {
    uses with-rollback-id-params;
  }
  augment '/nc:copy-config/nc:output' {
    uses with-rollback-id-reply;
  }

  augment '/nc:commit/nc:input' {
    uses with-rollback-id-params;
  }
  augment '/nc:commit/nc:output' {
    uses with-rollback-id-reply;
  }

  augment '/tr:commit-transaction/tr:input' {
    uses with-rollback-id-params;
  }
  augment '/tr:commit-transaction/tr:output' {
    uses with-rollback-id-reply;
  }
}
