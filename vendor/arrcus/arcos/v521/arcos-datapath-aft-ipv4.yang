submodule arcos-datapath-aft-ipv4 {
  yang-version "1.1";

  belongs-to "arcos-datapath-aft" {
    prefix "arcos-dp-aft";
  }

  import ietf-inet-types { prefix "inet"; }

  // Include common cross-AFT groupings from the common submodule.
  include arcos-datapath-aft-common;

  organization
    "XXXXX";

  contact
    "XXXXX";

  description
    "Submodule containing definitions of groupings for the abstract
    forwarding tables for IPv4.";

  grouping aft-ipv4-unicast-flat-structural {
    description
      "Structural grouping defining the schema for the flattened IPv4 unicast
      abstract forwarding table.";

    action v4-route {
      description
        "IPv4 route lookup";
      input {
        leaf prefix {
          type inet:ipv4-prefix;
          mandatory true;
          description
            "The IPv4 address to be looked up from RIB";
        }
      }
      output {
        leaf prefix {
          type inet:ipv4-prefix;
          description
            "The IPv4 address to be looked up from RIB";
        }
        uses aft-ipv4-unicast-entry-flat-state;
      }
    }
  }

  grouping aft-ipv4-unicast-entry-flat-state {
    description
      "Operational state parameters for the IPv4 unicast entry.";
    uses aft-common-entry-flat-state;
  }

  grouping aft-ipv4-unicast-structural {
    description
      "Structural grouping defining the schema for the IPv4 unicast
      abstract forwarding table.";

    list ipv4-entry {
      key "prefix";

      description
        "List of the IPv4 unicast entries within the abstract
        forwarding table. This list is keyed by the destination IPv4
        prefix.";

      leaf prefix {
        type leafref {
          path "../state/prefix";
        }
        description
          "Reference to the IPv4 unicast destination prefix which
          must be matched to utilise the AFT entry.";
      }

      container state {
        description
          "Operational state parameters for the IPv4 unicast AFT
          entry.";
        uses aft-ipv4-unicast-entry-config;
        uses aft-ipv4-unicast-entry-state;
      }
    }
  }

  grouping aft-ipv4-unicast-entry-config {
    description
      "Configuration parameters for the IPv4 unicast entry.";

    leaf prefix {
        type inet:ipv4-prefix;
        description
          "The IPv4 destination prefix that should be matched to
          utilise the AFT entry.";
    }
  }

  grouping aft-ipv4-unicast-entry-state {
    description
      "Operational state parameters for the IPv4 unicast entry.";
    uses aft-common-entry-state;
  }
}
