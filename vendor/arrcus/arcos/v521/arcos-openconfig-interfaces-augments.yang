module arcos-openconfig-interfaces-augments {
  yang-version 1.1;
  namespace "http://yang.arrcus.com/arcos/openconfig/interfaces/augments";
  prefix arc-oc-if-aug;

  import openconfig-interfaces {
    prefix oc-if;
  }

  import openconfig-yang-types {
    prefix oc-yang;
  }

  import openconfig-network-instance {
    prefix oc-ni;
  }

  import openconfig-if-ethernet {
    prefix oc-eth;
  }

  import openconfig-vlan {
    prefix oc-vlan;
  }

  import ietf-yang-types {
    prefix yang;
  }

  import ietf-inet-types {
    prefix inet;
  }

  import iana-if-type {
    prefix ianaift;
  }

  import tailf-common {
    prefix tailf;
  }

  import arcos-features {
    prefix arc-features;
  }

  import arcos-platform {
    prefix arc-platform;
  }
  import arcos-portsec {
    prefix arc-portsec;
  }

  organization
    "Arrcus, Inc.";

  contact
    "Arrcus, Inc.
     2077 Gateway Place
     Suite 400
     San Jose, CA 95110

     E-mail: yang-support@arrcus.com";

  description
    "This module contains definitions for the
     native ArcOS Port Sec feature.

     Copyright (c) 2016-2022 by Arrcus, Inc.
     All rights reserved.";

  revision 2023-02-08 {
    description
      "Interface debounce timer support";
  }

  revision 2022-09-13 {
    description
      "Added mac-learning";
  }

  revision 2022-05-09 {
    description
      "portsec fixes";
  }

  typedef fec-types {
    type enumeration {
      enum fec-none {
        value 1;
      }
      enum base-r {
        value 2;
      }
      enum rs {
        value 3;
      }
      enum rs-108 {
        value 4;
      }
      enum rs-206 {
        value 5;
      }
      enum rs-272 {
        value 6;
      }
      enum rs-304 {
        value 7;
      }
      enum rs-544 {
        value 8;
      }
      enum rs-545 {
        value 9;
      }
      enum rs-272-2xn {
        value 10;
      }
      enum rs-544-2xn {
        value 11;
      }
    }
  }

  grouping dynamic-ipv4-address {
    description
      "Per IPv4 address configuration data for the
       interface.";

    leaf ip {
      type inet:ipv4-address-no-zone;
      description
        "[adapted from IETF IP model RFC 7277]

         The IPv4 address on the interface.";
    }
    leaf prefix-length {
      type uint8 {
        range "0..32";
      }
      description
        "[adapted from IETF IP model RFC 7277]

         The length of the subnet prefix.";
    }
  }

  grouping dynamic-ipv6-address {
    description
      "Per IPv6 address configuration data for the
       interface.";

    leaf ipv6 {
      type inet:ipv6-address-no-zone;
      description
        "[adapted from IETF IP model RFC 7277]

         The IPv6 address on the interface.";
    }
    leaf ipv6-prefix-length {
      type uint8 {
        range "0..128";
      }
      description
        "[adapted from IETF IP model RFC 7277]

         The length of the subnet prefix.";
    }
  }

  grouping dynamic-address-top {
    description
      "Subinterface data for logical interfaces
       associated with a physical interface.";

    container dynamic {
      config false;
      description
        "Enclosing container for the list of subinterfaces
         associated with a physical interface.";

      uses dynamic-ipv4-address;
      uses dynamic-ipv6-address;
    }
  }

  grouping subinterface-config {
    leaf network-instance {
      type string;
      description
        "The L3 network-instance that this subinterface is associated
         with.  When this leaf is unspecified, the subinterface is
         associated with the default network instance.";
    }
  }

  grouping if-error-counters {
    description
      "Error counters";

    leaf fcs-error {
      when "/oc-if:interfaces/oc-if:interface/oc-if:config/" +
           "oc-if:type = 'ianaift:ethernetCsmacd'" {
        description
        "FCS Error count";
      }
      type yang:counter64;
    }
    leaf align-error {
      when "/oc-if:interfaces/oc-if:interface/oc-if:config/" +
           "oc-if:type = 'ianaift:ethernetCsmacd'" {
        description
        "Alignment Error count";
      }
      type yang:counter64;
    }
    leaf symbol-error {
      when "/oc-if:interfaces/oc-if:interface/oc-if:config/" +
           "oc-if:type = 'ianaift:ethernetCsmacd'" {
        description
        "Symbol Error count";
      }
      type yang:counter64;
    }
    leaf runt-pkts {
      when "/oc-if:interfaces/oc-if:interface/oc-if:config/" +
           "oc-if:type = 'ianaift:ethernetCsmacd'" {
        description
        "Undersize pkt count";
      }
      type yang:counter64;
    }
  }

  augment "/oc-if:interfaces/oc-if:interface/oc-if:subinterfaces/" +
          "oc-if:subinterface/oc-if:config" {
    uses subinterface-config;
  }

  augment "/oc-if:interfaces/oc-if:interface/oc-if:subinterfaces/" +
          "oc-if:subinterface/oc-if:state" {
    leaf network-instance {
      type oc-ni:network-instance-ref;
      description
        "The L3 network-instance that this subinterface is associated with.
         When this leaf is unspecified, subinterface is associated with the
         the default network instance.";
    }
  }

  augment "/oc-if:interfaces/oc-if:interface/oc-if:state/oc-if:counters" {
    leaf in-bits-rate {
      type yang:counter64;
      description
      "input rate in bits";
    }
    leaf in-bits-rate-brief {
      type string;
      description
      "input rate in bits in string format";
    }
    leaf in-pkts-rate {
      type yang:counter64;
      description
      "input pkts rate";
    }
    leaf out-bits-rate {
      type yang:counter64;
      description
      "output rate in bits";
    }
    leaf out-bits-rate-brief {
      type string;
      description
      "output rate in bits in string format";
    }
    leaf out-bits-rate-unit {
      type string;
      description
      "output rate unit";
    }
    leaf out-pkts-rate {
      type yang:counter64;
      description
      "output pkts rate";
    }
    leaf queue-drop-pkts {
      when "/oc-if:interfaces/oc-if:interface/oc-if:config/" +
           "oc-if:type = 'ianaift:ethernetCsmacd' and " +
           "/arc-features:features/arc-features:feature[arc-features:name='arc-features:ARCOS_QoS']" +
           "/arc-features:supported = 'true'" {
        description
        "Count of Queue Drop Packets";
      }
      type yang:counter64;
    }
    container errors {
      config false;
      description
        "Error counters";
      uses if-error-counters;
    }
    leaf in-ipv4-discards {
      type oc-yang:counter64;
      description
        "input ipv4 discards packets";
    }
    leaf in-stp-discards {
      type oc-yang:counter64;
      description
        "input stp discards packets";
    }
    leaf in-vlan-discards {
      type oc-yang:counter64;
      description
        "input vlan discards packets";
    }
    leaf in-tcam-discards {
      type oc-yang:counter64;
      description
        "input tcam discards packets";
    }
    leaf in-policy-discards {
      type oc-yang:counter64;
      description
        "input policy discards packets";
    }
    leaf carrier-transitions {
      type oc-yang:counter64;
      description
        "Number of times the interface state has transitioned between up and
         down since the time the device restarted or the last-clear time,
         whichever is most recent";
    }
    leaf giant-pkts {
      type yang:counter64;
      description
        "Oversize pkt count";
    }

    leaf in-mtu-exceeded-discards {
      type oc-yang:counter64;
      description
        "Input MTU exceeded discards packets";
    }
  }

  grouping port-security-top {
    container port-security {
      leaf profile {
        type leafref {
          path "/arc-portsec:port-security/arc-portsec:profiles/arc-portsec:" +
          "profile/arc-portsec:name";
        }
        description
          "Port security profile";
      }
      leaf enable {
        type boolean;
        description
          "Enable or disable security profile";
      }
      leaf-list static-mac-list {
        type yang:mac-address;
        description
          "Configured list of static macs";
      }
    }
  }

  grouping interface-config {
    leaf fec {
      when "/oc-if:interfaces/oc-if:interface/oc-if:config/" +
           "oc-if:type = 'ianaift:ethernetCsmacd'";
      description
      "Forward error correction type to use for this ethernet interface";
      type fec-types;
    }

    leaf autostate {
      type boolean;
      when "/oc-if:interfaces/oc-if:interface/oc-if:config/" +
           "oc-if:type = 'ianaift:l3ipvlan'";
      description
        "Enable/disable interface state management on this interface";
    }

    leaf mac-learning {
      type boolean;
      default true;
      when "derived-from-or-self(current()/../oc-if:type, 'ianaift:ethernetCsmacd') or " +
           "derived-from-or-self(current()/../oc-if:type, 'ianaift:ieee8023adLag')";
      description
        "When this leaf is set to true, MAC learning is enabled for
        the interface, such that MAC addresses are learned
        from ingress frames and added to the FDB.";
    }

    leaf load-interval {
      type uint16 {
        range 5..300;
      }
      description "Interface counter load interval in seconds";
    }

    uses port-security-top {
      when "../oc-eth:ethernet/" +
           "oc-vlan:switched-vlan/oc-vlan:config/oc-vlan:interface-mode = 'ACCESS'" {
         description "Port security enabled only on ACCESS interfaces";
      }
    }
  }

  grouping interface-state {
    leaf load-interval {
      type uint16;
      description
        "Interface counter load interval in seconds";
    }

    leaf media-type {
      type string;
      description
        "Media type of the interface";
    }

    leaf module-type {
      type string;
      description
        "Module type of the interface";
    }

    leaf fec {
      type fec-types;
      when "/oc-if:interfaces/oc-if:interface/oc-if:config/" +
           "oc-if:type = 'ianaift:ethernetCsmacd'";
      description
        "Operational value of forward error correction type in use for this interface";
    }

    leaf fec-corrected-errors {
      type uint64;
      when "/oc-if:interfaces/oc-if:interface/oc-if:config/" +
           "oc-if:type = 'ianaift:ethernetCsmacd'";
      description
        "Count of FEC corrected errors";
    }

    leaf fec-uncorrected-errors {
      type uint64;
      when "/oc-if:interfaces/oc-if:interface/oc-if:config/" +
           "oc-if:type = 'ianaift:ethernetCsmacd'";
      description
        "Count of FEC uncorrected errors";
    }

    leaf speed-group {
      type uint8;
      when "/oc-if:interfaces/oc-if:interface/oc-if:config/" +
           "oc-if:type = 'ianaift:ethernetCsmacd'";
      description
        "Speed group that this interface belongs to";
    }

    leaf autostate {
      type boolean;
      when "/oc-if:interfaces/oc-if:interface/oc-if:config/" +
           "oc-if:type = 'ianaift:l3ipvlan'";
      description
        "Operation value of interface state management used for this interface";
    }

    leaf mac-learning {
      type boolean;
      when "derived-from-or-self(current()/../oc-if:type, 'ianaift:ethernetCsmacd') or " +
           "derived-from-or-self(current()/../oc-if:type, 'ianaift:ieee8023adLag')";
      description
        "Operation value of mac learning for this interface";
    }

    leaf errDisable {
      type string;
      description
        "Interface disable reason";
    }
    leaf time-elapsed-since-last-change {
      type string;
      description
        "Time Elapsed since last state change";
    }
    uses dynamic-address-top;
  }

  grouping debounce-info {
    description
      "Configuration and State data for interface debounce";

    leaf up {
      type uint32 {
        range 1..30000;
      }
      units "milliseconds";
      description "Interface debounce (from DOWN to UP) interval in milliseconds";
    }

    leaf down {
      type uint32 {
        range 1..30000;
      }
      units "milliseconds";
      description "Interface debounce (from UP to DOWN) interval in milliseconds";
    }
  }

  grouping debounce-logical-top {
    description "Top-level data definitions for interface debounce";

    container debounce-interval {
      description
        "Configuration and State for interface debounce interval";

      uses debounce-info;
    }
  }

  augment "/oc-if:interfaces/oc-if:interface/oc-if:config" {
    uses interface-config;
    uses debounce-logical-top;
  }

  augment "/oc-if:interfaces/oc-if:interface/oc-if:state" {
    uses interface-state;
    uses debounce-logical-top;
  }
}
