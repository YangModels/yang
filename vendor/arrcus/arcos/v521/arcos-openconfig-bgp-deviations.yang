module arcos-openconfig-bgp-deviations {
  yang-version 1.1;
  namespace "http://yang.arrcus.com/arcos/openconfig/bgp/deviations";
  prefix arc-oc-bgp-dev;

  import openconfig-bgp {
    prefix oc-bgp;  
  }

  deviation "/oc-bgp:bgp" {
    deviate not-supported;
    description "BGP configuration is allowed under network instance,
                 and is not supported at root level.";
  }
}
