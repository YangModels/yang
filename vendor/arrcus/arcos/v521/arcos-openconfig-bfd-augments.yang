module arcos-openconfig-bfd-augments {
  yang-version 1.1;
  namespace "http://yang.arrcus.com/arcos/openconfig/bfd/augments";
  prefix arc-oc-bfd-aug;

  import openconfig-bfd {
    prefix oc-bfd;
  }
  import ietf-inet-types {
    prefix inet;
  }
  import openconfig-interfaces {
    prefix oc-if;
  }

  organization
    "Arrcus, Inc.";

  contact
    "Email: eng@arrcus.com";

  description
    "This module defines augmentation for Arrcus
     implementation of the openconfig BFD module.";

  revision 2018-11-14 {
    description
      "Initial Revision
      ";
  }

  grouping bfd-peer-state-top {
    leaf hw-offload-status {
      type boolean;
      description
        "Hardware offload status.";
    }
    leaf interface {
      type leafref {
        path "/oc-if:interfaces/oc-if:interface/oc-if:name";
      }
      description "Micro BFD interface";
    }
    leaf parent-interface {
      type leafref {
        path "/oc-if:interfaces/oc-if:interface/oc-if:name";
      }
      description "Micro BFD Parent interface";
    }
    leaf hw-endpoint-id {
      type int32;
      description
        "Hardware Endpoint ID.";
    }
    leaf network-instance {
      type string;
      description
        "Network Instance Name.";
    }
  }

  grouping bfd-micro-remote-address-top {
    container remote-address {
      leaf ipv4 {
          type inet:ipv4-address-no-zone;
          description "Destination IPV4 address for the micro BFD sessions";
      }
      leaf ipv6 {
          type inet:ipv6-address-no-zone;
          description "Destination IPV6 address for the micro BFD sessions";
      }
    }
  }
  grouping bfd-micro-intf-config {
    uses bfd-micro-remote-address-top;
    leaf enabled {
      type boolean;
      description "Enable Micro BFD sessions";
    }
  }
  augment "/oc-if:interfaces/oc-if:interface" {
    when "current()/oc-if:config/oc-if:type = 'ianaift:ieee8023adLag'" {
      description "Micro BFD configs for LAG interface";
    }

    container bfd {
      description "BFD interface specific configurations";
      container micro {
        description "Micro BFD interface specific configurations";
        container config {
          description "Micro BFD interface configurations";
          uses bfd-micro-intf-config;
        }
        container state {
          description "Micro BFD interface sessions states";
          config false;
          uses bfd-micro-intf-config;
        }
      }
    }
  }

  augment "/oc-bfd:bfd/oc-bfd:interfaces/oc-bfd:interface/oc-bfd:peers" +
          "/oc-bfd:peer/oc-bfd:state" {
    uses bfd-peer-state-top;
  }

  augment "/oc-bfd:bfd/oc-bfd:interfaces/oc-bfd:interface/oc-bfd:config" {
    leaf v4-hw-offload {
      type boolean;
      description "BFDv4 Hardware offload";
    }
    leaf v6-hw-offload {
      type boolean;
      description "BFDv6 Hardware offload";
    }
  }

  augment "/oc-bfd:bfd/oc-bfd:interfaces/oc-bfd:interface/oc-bfd:state" {
    leaf v4-hw-offload {
      type boolean;
      description "BFDv4 Hardware offload";
    }
    leaf v6-hw-offload {
      type boolean;
      description "BFDv6 Hardware offload";
    }
  }
}
