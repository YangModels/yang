module arcos-openconfig-bfd-deviations {
  yang-version 1.1;
  namespace "http://yang.arrcus.com/arcos/openconfig/bfd/deviations";

  prefix arc-oc-bfd-dev;

  import openconfig-bfd {
    prefix oc-bfd;
  }

  organization
    "Arrcus, Inc.";

  contact
    "Email: eng@arrcus.com";

  description
    "This module defines deviation statements for Arrcus
     implementation of the openconfig bfd module.";

    revision 2018-08-14 {
        description "ArcOS release 2.2.1";
    }


  revision 2017-09-07 {
    description
      "Initial Revision";

  reference
    "RFC 6020: YANG - A Data Modeling Language for the
     Network Configuration Protocol (NETCONF)";
  }

  deviation "/oc-bfd:bfd/oc-bfd:interfaces/oc-bfd:interface/oc-bfd:config/oc-bfd:desired-minimum-tx-interval" {
    deviate add {
      mandatory true;
    }
  }
  deviation "/oc-bfd:bfd/oc-bfd:interfaces/oc-bfd:interface/oc-bfd:config/oc-bfd:required-minimum-receive" {
    deviate add {
      mandatory true;
    }
  }
  deviation "/oc-bfd:bfd/oc-bfd:interfaces/oc-bfd:interface/oc-bfd:config/oc-bfd:detection-multiplier" {
    deviate add {
      mandatory true;
    }
  }

  deviation "/oc-bfd:bfd/oc-bfd:interfaces/oc-bfd:interface/oc-bfd:config/oc-bfd:local-address" {
    deviate not-supported;
    description "Not supported in this release";
  }
  deviation "/oc-bfd:bfd/oc-bfd:interfaces/oc-bfd:interface/oc-bfd:state/oc-bfd:local-address" {
    deviate not-supported;
    description "Not supported in this release";
  }
  deviation "/oc-bfd:bfd/oc-bfd:interfaces/oc-bfd:interface/oc-bfd:micro-bfd-sessions" {
    deviate not-supported;
    description "Not supported in this release";
  }
  deviation "/oc-bfd:bfd/oc-bfd:interfaces/oc-bfd:interface/oc-bfd:config/oc-bfd:enable-per-member-link" {
    deviate not-supported;
    description "Not supported in this release";
  }
  deviation "/oc-bfd:bfd/oc-bfd:interfaces/oc-bfd:interface/oc-bfd:state/oc-bfd:enable-per-member-link" {
    deviate not-supported;
    description "Not supported in this release";
  }
  deviation "/oc-bfd:bfd/oc-bfd:interfaces/oc-bfd:interface/oc-bfd:interface-ref" {
    deviate not-supported;
    description "Not supported in this release";
  }
  /* Temporary*/
  deviation "/oc-bfd:bfd/oc-bfd:interfaces/oc-bfd:interface/oc-bfd:peers/oc-bfd:peer/oc-bfd:state/oc-bfd:echo" {
    deviate not-supported;
    description "Not supported in this release";
  }
  deviation "/oc-bfd:bfd/oc-bfd:interfaces/oc-bfd:interface/oc-bfd:peers/oc-bfd:peer/oc-bfd:state/oc-bfd:last-failure-time" {
    deviate not-supported;
    description "Not supported in this release";
  }
  deviation "/oc-bfd:bfd/oc-bfd:interfaces/oc-bfd:interface/oc-bfd:peers/oc-bfd:peer/oc-bfd:state/oc-bfd:failure-transitions" {
    deviate not-supported;
    description "Not supported in this release";
  }
  deviation "/oc-bfd:bfd/oc-bfd:interfaces/oc-bfd:interface/oc-bfd:peers/oc-bfd:peer/oc-bfd:state/oc-bfd:local-diagnostic-code" {
    deviate not-supported;
    description "Not supported in this release";
  }
  deviation "/oc-bfd:bfd/oc-bfd:interfaces/oc-bfd:interface/oc-bfd:peers/oc-bfd:peer/oc-bfd:state/oc-bfd:remote-diagnostic-code" {
    deviate not-supported;
    description "Not supported in this release";
  }
  deviation "/oc-bfd:bfd/oc-bfd:interfaces/oc-bfd:interface/oc-bfd:peers/oc-bfd:peer/oc-bfd:state/oc-bfd:demand-mode-requested" {
    deviate not-supported;
    description "Not supported in this release";
  }
  deviation "/oc-bfd:bfd/oc-bfd:interfaces/oc-bfd:interface/oc-bfd:peers/oc-bfd:peer/oc-bfd:state/oc-bfd:remote-authentication-enabled" {
    deviate not-supported;
    description "Not supported in this release";
  }
  deviation "/oc-bfd:bfd/oc-bfd:interfaces/oc-bfd:interface/oc-bfd:peers/oc-bfd:peer/oc-bfd:state/oc-bfd:remote-control-plane-independent" {
    deviate not-supported;
    description "Not supported in this release";
  }
  deviation "/oc-bfd:bfd/oc-bfd:interfaces/oc-bfd:interface/oc-bfd:peers/oc-bfd:peer/oc-bfd:state/oc-bfd:async/oc-bfd:last-packet-transmitted" {
    deviate not-supported;
    description "Not supported in this release";
  }
  deviation "/oc-bfd:bfd/oc-bfd:interfaces/oc-bfd:interface/oc-bfd:peers/oc-bfd:peer/oc-bfd:state/oc-bfd:async/oc-bfd:last-packet-received" {
    deviate not-supported;
    description "Not supported in this release";
  }
  deviation "/oc-bfd:bfd/oc-bfd:interfaces/oc-bfd:interface/oc-bfd:peers/oc-bfd:peer/oc-bfd:state/oc-bfd:async/oc-bfd:up-transitions" {
    deviate not-supported;
    description "Not supported in this release";
  }
}
