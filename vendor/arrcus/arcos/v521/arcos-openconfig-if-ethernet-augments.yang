module arcos-openconfig-if-ethernet-augments {
  yang-version 1.1;
  namespace "http://yang.arrcus.com/arcos/openconfig/if/ethernet/augments";
  prefix arc-oc-if-eth-aug;

  import openconfig-interfaces {
    prefix oc-if;
  }

  import openconfig-if-ethernet {
    prefix oc-eth;
  }

  import arcos-openconfig-interfaces-augments {
    prefix arc-oc-int;
  }


  grouping interface-ethernet-common {
    leaf-list advertise-fec {
      type arc-oc-int:fec-types;
      description
      "Forward error correction type to advertise use for this ethernet interface";
    }

    leaf-list advertise-speed {
      type identityref {
        base oc-eth:ETHERNET_SPEED;
      }
      description
      "Speeds advertise for this ethernet interface";
    }
  }

  augment "/oc-if:interfaces/oc-if:interface/oc-eth:ethernet/oc-eth:state" {
    uses interface-ethernet-common;
  }

  augment "/oc-if:interfaces/oc-if:interface/oc-eth:ethernet/oc-eth:config" {
    uses interface-ethernet-common;
  }
}
