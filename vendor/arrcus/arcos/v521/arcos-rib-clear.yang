module arcos-rib-clear {
  yang-version 1.1;
  namespace "http://yang.arrcus.com/arcos/rib/clear";
  prefix arc-rib-clr;

  import ietf-inet-types { prefix inet; }

  container rib-clear {
    action v4-route {
      input {
        leaf prefix {
        type inet:ipv4-prefix;
        mandatory true;
          description
          "The IPv4 prefix to be deleted from RIB";
        }
      }
      output {
        leaf result {
        type string;
          description
          "The status of operation"; 
        }
      }
    }
    action v6-route {
      input {
        leaf prefix {
        type inet:ipv6-prefix;
        mandatory true;
          description
          "The IP64 prefix to be deleted from RIB";
        }
      }
      output {
        leaf result {
        type string;
          description
          "The status of operation"; 
        }
      }
    }
  }
}
