module arcos-datapath-aft {

  yang-version "1.1";

  namespace "http://yang.arrcus.com/arcos/datapath/aft";

  prefix "arcos-dp-aft";

  // Include IPv4 AFT submodule.
  include arcos-datapath-aft-ipv4;

  // Include IPv6 AFT submodule.
  include arcos-datapath-aft-ipv6;

  // Include MPLS AFT submodule.
  include arcos-datapath-aft-mpls;

  // Include SRv6 SID submodule.
  include arcos-datapath-aft-srv6;

  // Include the common cross-AFT entities.
  include arcos-datapath-aft-common;

  //Include the mac-table submodule.
  include arcos-datapath-aft-mac;

  organization
    "XXXX - TBD - XXXX";

  contact
    "XXXX - TBD - XXXX";

  description
    "A model describing the forwarding entries installed in a datapath
    instance. It is based on the Openconfig Abstract Forwarding Table (AFT)
    mode. It should be noted that this model is not expected to
    align 1:1 with the underlying structure used directly by a
    forwarding element (e.g., linecard), but rather provide an
    abstraction that can be consumed by an NMS to observe, and in some
    cases manipulate, the internal forwarding database in a simplified
    manner. Since the underlying model of the forwarding table is not
    expected to align with this model, the structure described herein
    is referred to as an Abstract Forwarding Table (AFT), rather than
    the FIB.";

  revision "2023-03-29" {
    description
      "Added support of Mac fdb";
  }

  grouping aft-top {
    description
      "Top-level grouping allowing per-protocol instantiation of the
      AFT.";

    container afts {
      config false;
      description
        "The abstract forwarding tables (AFTs) that are associated
        with the network instance. An AFT is instantiated per-protocol
        running within the network-instance - such that one exists for
        IPv4 Unicast, IPv6 Unicast, MPLS, L2 forwarding entries, etc.
        A forwarding entry within the FIB has a set of next-hops,
        which may be a reference to an entry within another table -
        e.g., where a Layer 3 next-hop has an associated Layer 2
        forwarding entry.";

      container ipv4-unicast {
        description

          "The abstract forwarding table for IPv4 unicast. Entries
          within this table are uniquely keyed on the IPv4 unicast
          destination prefix which is matched by ingress packets.

          The data set represented by the IPv4 Unicast AFT is the set
          of entries from the IPv4 unicast RIB that have been selected
          for installation into the FIB of the device exporting the
          data structure.";

        uses aft-ipv4-unicast-structural;
      }

      container ipv4-unicast-flat {
        description

          "The abstract forwarding table for IPv4 unicast flattened.
          Entries within this table are uniquely keyed on the IPv4
          unicast destination prefix which is matched by ingress packets.

          The data set represented by the IPv4 Unicast AFT is the set
          of entries from the IPv4 unicast RIB that have been selected
          for installation into the FIB of the device exporting the
          data structure.";

        uses aft-ipv4-unicast-flat-structural;
      }

      container ipv6-unicast {
        description
          "The abstract forwarding table for IPv6 unicast. Entries
          within this table are uniquely keyed on the IPv6 unicast
          destination prefix which is matched by ingress packets.

          The data set represented by the IPv6 Unicast AFTis the set
          of entries within the IPv6 RIB that ";

        uses aft-ipv6-unicast-structural;
      }

      container ipv6-unicast-flat {
        description
          "The abstract forwarding table for IPv6 unicast flattened.
          Entries within this table are uniquely keyed on the IPv6
          unicast destination prefix which is matched by ingress packets.

          The data set represented by the IPv6 Unicast AFTis the set
          of entries within the IPv6 RIB that ";

        uses aft-ipv6-unicast-flat-structural;
      }

      container mpls {
        description
          "The abstract forwarding table for MPLS label based
          forwarding entries. Entries within the table are keyed based
          on the top-most MPLS label in the stack on the ingress
          packet.";

        uses aft-mpls-structural;
      }

      container srv6-sid {
        description
          "The abstract forwarding table for SRv6 SID based forwarding
          entries. Entries within the table are keyed based on the
          SRv6 Local SID which is matched by ingress packets";

          uses aft-srv6-sid-structural;
      }

      container mac-entries{
        description
            "The abstract forwarding table for Mac based forwarding
            entries.";
        uses aft-mac-structural;
      }
/*
      container ethernet {
        description
          "The abstract forwarding table for Ethernet based forwarding
          entries. Entries within the table are keyed based on the
          destination MAC address on the ingress packet.";

        uses aft-ethernet-structural;
      }
*/
    }
  }
}
