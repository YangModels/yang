module arcos-bgp-rnh {
  yang-version 1.1;
  namespace "http://yang.arrcus.com/arcos/bgp/rnh";
  prefix arc-bgp-rnh;

  import ietf-inet-types {
    prefix inet;
  }

  import arcos-openconfig-bgp-types {
    prefix arc-oc-bgp-types;
  }

  grouping rnh {
    description
      "Parameters related to a BGP group";
    leaf rnh-addr {
      type inet:ip-prefix;
      description
        "The next-hop that is tracked";
    }
    leaf interface-name {
      type string;
      description
        "The interface of the next-hop";
    }
    leaf rnh-type {
      type string;
      description
        "The next-hop type";
    }
    leaf path-count {
      type uint32;
      description
        "The path count";
    }
    leaf neighbor-count {
      type uint32;
      description
        "The neighbor count";
    }
    leaf total-reference-count {
      type uint32;
      description
        "The total reference count";
    }
    leaf metric {
      type uint32;
      description
        "metric of IGP route";
    }
    leaf per-nexthop-label {
      type uint32;
      description
        "Per-nexthop label if allocated";
    }
    leaf per-nexthop-sid {
      type inet:ipv6-address;
      description
        "Per-nexthop segment ID if allocated";
    }
    leaf local-next-hop {
      type boolean;
      description
        "local nexthop";
    }
    leaf interface-status {
      type boolean;
      description
        "interface status";
    }
    leaf link-local {
      type boolean;
      description
        "link-local";
    }
    leaf rfc5549-nexthop {
      type boolean;
      description
        "rfc5549 nexthop";
    }
    leaf stale-nexthop {
      type boolean;
      description
        "The nexthop is stale due to RIB restart";
    }
    leaf mpls-reachability {
      type boolean;
      description
        "The nexthop is reachable via a labeled path";
    }
    leaf srv6-nexthop {
      type boolean;
      description
        "The nexthop represents remote SRv6 SID";
    }
    leaf srv6-oam-state {
      type identityref {
        base arc-oc-bgp-types:SRV6_OAM_STATES;
      }
      description
        "For SRv6 next-hop only: health state as reported by OAM";
    }
    leaf srv6-oam-profile {
      type string;
      description
        "For SRv6 next-hop only: profile used in OAM tracking";
    }
  }

  grouping bgp-rnh-list {
    description
      "The list of BGP next hops";

    container rnhs {
      config false;
      list rnh {
        key "rnh-addr interface-name";
        description
          "List of BGP next-hops tracked with RIB";
        uses rnh;
      }
    }
  }
}
