module arcos-copp-policy-deviations {
  yang-version 1.1;
  namespace "http://yang.arrcus.com/arcos/copp/policy/deviations";
  prefix arc-copp-pol-dev;

  import arcos-copp {
    prefix arc-copp;
  }
  import arcos-copp-classifier {
    prefix arc-copp-cfr;
  }
  import arcos-copp-policy {
    prefix arc-copp-pol;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for copp policy validations
     Expanded from the copp policy data model";


  deviation "/arc-copp:copp/arc-copp-pol:policies/arc-copp-pol:policy"
          + "/arc-copp-pol:classifiers/arc-copp-pol:classifier"
          + "/arc-copp-pol:actions/arc-copp-pol:action"
          + "/arc-copp-pol:police/arc-copp-pol:config/arc-copp-pol:peak" {
    deviate not-supported;
    description
      "Not supported in this release";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:state/arc-copp-pol:peak" {
    deviate not-supported;
    description
      "Not supported in this release";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:config/arc-copp-pol:exceed" {
    deviate not-supported;
    description
      "Not supported in this release";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:state/arc-copp-pol:exceed" {
    deviate not-supported;
    description
      "Not supported in this release";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:config"
          + "/arc-copp-pol:committed/arc-copp-pol:rate/arc-copp-pol:unit" {
    deviate not-supported;
    description
      "bps rate is not relevant to copp, deviate it out.
       default unit is pps";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:state"
          + "/arc-copp-pol:committed/arc-copp-pol:rate/arc-copp-pol:unit" {
    deviate not-supported;
    description
      "bps rate is not relevant to copp, deviate it out.
       default unit is pps";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:config"
          + "/arc-copp-pol:committed/arc-copp-pol:burst/arc-copp-pol:unit" {
    deviate not-supported;
    description
      "bytes burst is not relevant to copp, deviate it out.
       default unit is packets";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:state"
          + "/arc-copp-pol:committed/arc-copp-pol:burst/arc-copp-pol:unit" {
    deviate not-supported;
    description
      "bytes burst is not relevant to copp, deviate it out.
       default unit is packets";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:config"
          + "/arc-copp-pol:conform" {
    deviate not-supported;
    description
      "specifying conform action-type not supported in this release";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:state"
          + "/arc-copp-pol:conform" {
    deviate not-supported;
    description
      "specifying conform action-type not supported in this release";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:config"
          + "/arc-copp-pol:exceed" {
    deviate not-supported;
    description
      "specifying exceed action-type not supported in this release";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:state"
          + "/arc-copp-pol:exceed" {
    deviate not-supported;
    description
      "specifying exceed action-type not supported in this release";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:config"
          + "/arc-copp-pol:violate" {
    deviate not-supported;
    description
      "specifying violate action-type not supported in this release";
  }

  deviation "/arc-copp:copp/arc-copp-pol:policies/arc-copp-pol:policy"
          + "/arc-copp-pol:classifiers/arc-copp-pol:classifier"
          + "/arc-copp-pol:actions/arc-copp-pol:action"
          + "/arc-copp-pol:police/arc-copp-pol:state"
          + "/arc-copp-pol:violate" {
    deviate not-supported;
    description
      "specifying violate action-type not supported in this release";
  }
}
