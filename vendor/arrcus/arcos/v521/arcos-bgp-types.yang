module arcos-bgp-types {
  yang-version 1.1;
  namespace "http://yang.arrcus.com/arcos/bgp/types";
  prefix arc-bgp-types;

  import ietf-inet-types {
    prefix inet;
  }

  import openconfig-interfaces {
    prefix oc-if;
  }

  organization
    "Arrcus, Inc.";

  contact
    "Email: yang-support@arrcus.com";

  description
    "ArcOS BGP Types Data Model";

  revision 2019-08-20 {
    description "ArcOS 3.3.1";
  }

  typedef bgp-route-refresh-type {
    type enumeration {
      enum in {
        description
          "BGP neighbor inbound route refresh";
      }
      enum out {
        description
          "BGP neighbor outbound route refresh";
      }
    }
  }

  typedef bgp-next-hop-type {
    type union {
      type enumeration {
        enum SELF {
          description
            "Special designation for local router's own address,
             i.e next-hop-self";
        }
        enum UNCHANGED {
          description
            "Special designation to not change the next-hop when
             advertising to the remote-peer i.e next-hop-unchanged";
        }
      }
    }
    description
      "Type definition for specifying next-hop";
  }

  typedef bgp-capability-state {
    type enumeration {
      enum UNNEGOTIABLE {
        description
          "Capability sent but not received OR not sent but received";
      }
      enum NEGOTIATED {
        description
          "Capability sent and received";
      }
    }
  }

  typedef srv6-tunnel-endpoint-type {
    type enumeration {
      enum INGRESS {
        description
          "SRv6 ingress tunnel endpoint";
      }
      enum EGRESS {
        description
          "SRv6 egress tunnel endpoint";
      }
      enum NONE {
        description
          "Neither an SRv6 ingress nor egress tunnel endpoint";
      }
    }
  }

  typedef bgp-as-type {
    type enumeration {
      enum ASN16 {
        description
          "2-byte (16-bit) AS number";
      }
      enum ASN32 {
        description
          "4-byte (32-bit) AS number";
      }
    }
  }

  typedef bgp-interface-state {
    type enumeration {
      enum UP {
        value 1;
        description
          "Ready to pass packets.";
      }
      enum DOWN {
        value 2;
        description
          "The interface does not pass any packets.";
      }
    }
  }

  typedef bgp-rib-origin-type {
    type union {
      type inet:ip-address-no-zone;
      //      type leafref {
      //        path "/oc-if:interfaces/oc-if:interface/oc-if:name";
      //      }
    }
    description
      "The origin type represents either a no zone IP address,
      or an interface name";
  }

  grouping bgp-adj-rib-attr-state {
    description
      "Path attributes that are not expected to be shared across
      route entries, specific to Adj-RIB";

    leaf path-id {
      type uint64;
      description
        "When the BGP speaker supports advertisement of multiple
        paths for a prefix, the path identifier is used to
        uniquely identify a route based on the combination of the
        prefix and path id.";
    }
  }

  grouping bgp-loc-rib-common-keys {
    description
      "Common references used in keys for IPv4 and IPv6
      LOC-RIB entries";

    leaf origin {
      type union {
        type inet:ip-address;
	//        type leafref {
	//          path "/oc-if:interfaces/oc-if:interface/oc-if:name";
	//        }
      }
      description
        "Indicates the origin of the route.";
    }

    leaf path-id {
      type uint64;
      description
        "When the BGP speaker supports advertisement of multiple
        paths for a prefix, the path identifier is used to
        uniquely identify a route based on the combination of the
        prefix and path id.";
    }
  }
}
