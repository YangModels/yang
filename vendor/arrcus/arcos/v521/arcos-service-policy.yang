module arcos-service-policy {
  yang-version 1.1;
  namespace "http://yang.arrcus.com/arcos/service-policy";
  prefix arc-svc-plc;

  organization
    "Arrcus, Inc.";
  contact
    "Arrcus, Inc.
     Customer Service
     Postal: 2077 Gateway Place
     San Jose, CA 95110
     Tel: +1 1XXX XXX-XXXX
     E-mail: xxx@arrcus.com";
  description
    "YANG data-model for generic service-policy instances.
     This is a base data model for service-policy that different
     apps can make use of to associate with different targets
     (Look at example, arrcus-qos-service-policy-interface.yang)";

  grouping service-policy-attributes {
    description
      "Grouping that defines service instance of a policy";
    leaf direction {
      type enumeration {
        enum INGRESS {
          description
            "for the incoming traffic";
        }
        enum EGRESS {
          description
            "for the outgoing traffic";
        }
      }
      description
        "direction of traffic this service-policy takes effect on";
    }
    leaf name {
      type string {
        length "1..79";
      }
      mandatory true;
      description
        "Name of a policy to be instantiated";
    }
  }

  grouping service-policies-top {
    description
      "Grouping for generic definition of policy service instances";
    container service-policies {
      description
        "Container for policy service instance data-base";
      list service-policy {
        key "direction";
        description
          "A specific policy service instance";
        leaf direction {
          type leafref {
            path "../config/direction";
          }
          description
            "specific direction of traffic service instance is applicable to";
        }
        container config {
          description
            "Configuration parameters relating to policy service instance";
          uses service-policy-attributes;
        }
        container state {
          config false;
          description
            "Operational state parameters relating to policy service instance";
          uses service-policy-attributes;
        }
      }
    }
  }
}
