module arcos-arp-nd-global {
  yang-version 1.1;
  namespace "http://yang.arrcus.com/arcos/ip-neighbor";
  prefix arc-ip-nbr;

  container ip-neighbor {
    description
      "Global ARP and ND neighbor configuration";

    leaf persistence {
      type uint8 {
        range "5..255";
      }
      description "neighbor persistence sampling time in sec";
    }
  }
}
