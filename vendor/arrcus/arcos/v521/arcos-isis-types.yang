module arcos-isis-types {
  yang-version 1.1;
  namespace "http://yang.arrcus.com/arcos/isis/types";
  prefix arc-isis-types;

  identity level-bits {
    description "Base identitfy type for level-bits.";
  }

  identity LEVEL_NONE {
    base level-bits;
    description "Identitfy for no level-bits set.";
  }

  identity LEVEL_1 {
    base level-bits;
    description "Identitfy for level 1 bit set.";
  }

  identity LEVEL_2 {
    base level-bits;
    description "Identitfy for level 2 bit set.";
  }

  identity LEVEL_1_2 {
    base level-bits;
    description "Identitfy for level 1 and 2 bits set.";
  }

  typedef network-type {
    type enumeration {
      enum UNKNOWN {
        description "This enum describes a unknown interface.";
      }
      enum LOOPBACK {
        description "This enum describes a loopback interface.";
      }
      enum POINT_TO_POINT {
        description "This enum describes a point-to-point interface.";
      }
      enum BROADCAST {
        description "This enum describes a broadcast interface.";
      }
    }
    description
        "This type defines ISIS interface network types.";
  }

  typedef node-id {
    type string {
      pattern
        '[0-9A-Fa-f]{4}\.[0-9A-Fa-f]{4}\.[0-9A-Fa-f]{4}\.[0-9][0-9]';
    }
    description
      "This type defines ISIS node ID. ISIS node ID type should be in
       the form of xxxx.xxxx.xxxx.xx. It is used to represent LAN ID
       and circuit ID";
  }

  typedef system-name {
    type string {
      pattern '.*';
    }
    description
      "This type defines ISIS node name. ISIS system ID type should be in
       the form of <name>, where <name> is either a hostname or in the
       format 'XXXX.XXXX.XXXX'.";
  }

  typedef node-name {
    type string {
      pattern '.*\.[0-9A-Fa-f]{2}';
    }
    description
      "This type defines ISIS node name. ISIS node ID type should be in
       the form of <name>.xx, where <name> is either a hostname or in the
       format 'XXXX.XXXX.XXXX'. It is used to represent LAN ID and circuit ID";
  }

  typedef lsp-name {
    type string {
      pattern '.*\.[0-9A-Fa-f]{2}-[0-9A-Fa-f]{2}';
    }
    description
      "This type defines ISIS LSP name. ISIS LSP name type should be in
      the form of <name>.xx-xx, where <name> is either a hostname or in the
      format 'XXXX.XXXX.XXXX'.";
  }
}
