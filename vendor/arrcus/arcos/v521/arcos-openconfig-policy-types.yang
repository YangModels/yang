module arcos-openconfig-policy-types {
  yang-version 1.1;
  namespace "http://yang.arrcus.com/arcos/openconfig/policy-types";
  prefix arc-oc-pol-types;

  import openconfig-policy-types {
    prefix oc-pol-types;
  }
  organization
    "Arrcus, Inc.";

  description
    "YANG data-model for openconfig-policy-types augment";

  revision 2022-12-12 {
    description
      "* Add L2FM protocol type to support static vxlan.";
  }

  identity ADJACENCY {
    base oc-pol-types:INSTALL_PROTOCOL_TYPE;
    description
      "Adjacency route";
  }

  identity LDP {
    base oc-pol-types:INSTALL_PROTOCOL_TYPE;
    description
      "LDP";
  }

  identity SIDMGR {
    base oc-pol-types:INSTALL_PROTOCOL_TYPE;
    description
      "SIDMGR";
  }

  identity LAG {
    base oc-pol-types:INSTALL_PROTOCOL_TYPE;
    description
      "Link Aggregation";
  }

  identity INTERNAL {
    base oc-pol-types:INSTALL_PROTOCOL_TYPE;
    description
      "Internal route";
  }

  identity L2FM {
    base oc-pol-types:INSTALL_PROTOCOL_TYPE;
    description
      "L2FM route";
  }
}
