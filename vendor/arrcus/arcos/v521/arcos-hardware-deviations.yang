module arcos-hardware-deviations {
  yang-version 1.1;
  namespace "http://yang.arrcus.com/arcos/hardware/deviations";
  prefix arc-hw-dev;

  import arcos-hardware {
    prefix arc-hw;
  }

  import arcos-runtime {
    prefix arc-runtime;
  }

  deviation "/arc-runtime:runtime-instances/arc-runtime:runtime-instance" +
            "/arc-hw:hardware/arc-hw:config" {
    deviate not-supported;
  }

  deviation "/arc-runtime:runtime-instances/arc-runtime:runtime-instance" +
            "/arc-hw:hardware/arc-hw:state" {
    deviate not-supported;
  }
}
