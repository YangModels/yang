submodule arcos-ospfv2-common {

  yang-version "1.1";

  belongs-to arcos-ospfv2 {
    prefix "arc-ospfv2";
  }

  import ietf-yang-types { prefix "yang"; }
  import openconfig-types { prefix "oc-types"; }
  import arcos-ospf-types { prefix "arc-ospf-types"; }

  description
    "This submodule provides OSPFv2 configuration and operational
    state parameters that are common under one or more contexts.";

  /*
   * OSPFv2 packet Option bits
   */
  grouping ospfv2-packet-options {
    description
      "OSPFv2 packet Options field";

    container options {
      leaf e-bit {
        type boolean;
        description
          "This bit describes the way AS-external-LSAs are flooded";
      }

      leaf np-bit {
        type boolean;
        description
          "This bit describes the handling of Type-7 LSAs";
      }

      leaf ea-bit {
        type boolean;
        description
          "This bit describes the router's willingness to receive and
          forward External-Attributes-LSAs";
      }
    }
  }
}
