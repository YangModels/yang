module tailf-confd-progress {
  namespace "http://tail-f.com/ns/confd-progress";
  prefix confd-progress;

  import tailf-progress {
    prefix progress;
  }

  description
    "This module contains a collection of YANG definitions for
     tracing progress in ConfD.

     Copyright 2020 Cisco Systems, Inc.
     All rights reserved.
     Permission is hereby granted to redistribute this file without
     modification.";

  revision 2020-06-29 {
    description
      "Released as part of ConfD-7.4.

       Initial revision.";
  }

  augment "/progress:progress/progress:trace" {
    leaf-list debug {
      description
        "Additional debug tracing. These are consciously left out of the
         normal debug level due to the high amount of output.
         Use with care.";
      type enumeration {
        enum xpath {
          description
            "Detailed output from the XPath evaluator.";
        }
        enum kicker {
          description
            "Detailed output from data kicker evaluation.";
        }
        enum subscriber {
          description
            "Detailed output from CDB subscribers.";
        }
      }
    }
  }
}
