module arcos-interfaces-cache {
  yang-version 1.1;
  namespace "http://yang.arrcus.com/arcos/interfaces/cache";
  prefix arc-if-cache;

  container ifcache-entries {
    description
      "ifcache table entries";

    config false;

    list ifcache-entry {
      description
        "Interface of entry";

      key "ifname";

      leaf ifname {
        type string;
        description
          "Interface name";
      }

      leaf actor-flags {
        type uint8;
        description
          "Actor LACP flags";
      }

      leaf partner-flags {
        type uint16;
        description
          "Partner LACP flags";
      }

      leaf slave-state {
        type uint8;
        description
          "Slave state in case of LACP member";
      }
    }
  }
}
