module arcos-platform {
  yang-version 1.1;
  namespace "http://yang.arrcus.com/arcos/platform";
  prefix arc-platform;

  organization
    "Arrcus, Inc.";

  contact
    "Arrcus, Inc.
     2077 Gateway Place
     Suite 400
     San Jose, CA 95110

     E-mail: yang-support@arrcus.com";

  description
    "This module contains definitions for the native
     ArcOS platform domain.

     Note that while the data-nodes contained within
     this model are read/write, it is for purposes
     of ArcOS system initialization.  Write access is
     not permitted to the data-nodes contained within
     this data-model.

     Copyright (c) 2016-2020 by Arrcus, Inc.
     All rights reserved.";

  revision 2022-12-20 {
    description "Add support for ufispace  platform s9600-30dx";
  }

  revision 2020-02-26 {
    description "Initial version";
  }

  identity ASIC_VENDOR_DEVICE_FAMILY {
    description
      "Base type for device family";
  }

  identity BROADCOM_XGS {
    base ASIC_VENDOR_DEVICE_FAMILY;
    description
      "Broadcom XGS device family";
  }

  identity BROADCOM_DNX {
    base ASIC_VENDOR_DEVICE_FAMILY;
    description
      "Broadcom DNX device J2 family";
  }

  identity BROADCOM_DNX_JPLUS {
    base ASIC_VENDOR_DEVICE_FAMILY;
    description
      "Broadcom DNX device JPlus family";
  }

  identity BROADCOM_DNX_FABRIC {
    base ASIC_VENDOR_DEVICE_FAMILY;
    description
      "Broadcom DNX device family";
  }

  identity INTEL_TOFINO_SERIES {
    base ASIC_VENDOR_DEVICE_FAMILY;
    description
      "INTEL Tofino device family";
  }

  identity VIRTUAL {
    base ASIC_VENDOR_DEVICE_FAMILY;
    description
      "Virtual device";
  }

  identity ASIC_VENDOR_DEVICE_TYPE {
    description
      "Base type for asic device type";
  }

  identity BROADCOM_TRIDENT2 {
    base ASIC_VENDOR_DEVICE_TYPE;
    description
      "Broadcom TD2 device";
  }

  identity BROADCOM_TOMAHAWK {
    base ASIC_VENDOR_DEVICE_TYPE;
    description
      "Broadcom TH device";
  }

  identity BROADCOM_HELIX4 {
    base ASIC_VENDOR_DEVICE_TYPE;
    description
      "Broadcom HX4 device";
  }

  identity BROADCOM_TRIDENT3 {
    base ASIC_VENDOR_DEVICE_TYPE;
    description
      "Broadcom TD3 device";
  }

  identity BROADCOM_TRIDENT4 {
    base ASIC_VENDOR_DEVICE_TYPE;
    description
      "Broadcom TD4 device";
  }

  identity BROADCOM_JERICHOPLUS {
    base ASIC_VENDOR_DEVICE_TYPE;
    description
      "Broadcom JPLUS device";
  }

  identity BROADCOM_JERICHO2 {
    base ASIC_VENDOR_DEVICE_TYPE;
    description
      "Broadcom J2 device";
  }

  identity BROADCOM_Q2A {
    base ASIC_VENDOR_DEVICE_TYPE;
    description
      "Broadcom Q2A device";
  }

  identity BROADCOM_X2C {
    base ASIC_VENDOR_DEVICE_TYPE;
    description
      "Broadcom J2C/Q2C device";
  }

  identity BROADCOM_RAMON {
    base ASIC_VENDOR_DEVICE_TYPE;
    description
      "Broadcom Ramon device";
  }

  identity BROADCOM_TOMAHAWK3 {
    base ASIC_VENDOR_DEVICE_TYPE;
    description
      "Broadcom TH3 device";
  }

  identity INTEL_TOFINO {
    base ASIC_VENDOR_DEVICE_TYPE;
    description
      "INTEL Tofino 32x100 device";
  }

  identity X86_64 {
    base ASIC_VENDOR_DEVICE_TYPE;
    description
      "Intel x86_64 device";
  }

  identity ARCOS_PLATFORM {
    description
      "Base type for ARCOS platform";
  }

  identity REDSTONE_XP {
    base ARCOS_PLATFORM;
    description
      "Celestica sysid x86-64-cel-redstone-xp-r0";
  }
  identity SEASTONE_XP {
    base ARCOS_PLATFORM;
    description
      "Celestica sysid x86-64-cel-seastone-r0";
  }
  identity AS5712 {
    base ARCOS_PLATFORM;
    description
      "Accton sysid x86-64-accton-as5712-54x-r0";
  }
  identity AS7712 {
    base ARCOS_PLATFORM;
    description
      "Accton sysid x86-64-accton-as7712-32x-r0";
  }
  identity HALIBURTON {
    base ARCOS_PLATFORM;
    description
      "Celestica sysid x86-64-cel-e1031-r0";
  }
  identity IX7 {
    base ARCOS_PLATFORM;
    description
      "Quanta sysid x86-64-quanta-ix7-rglbmc-r0";
  }
  identity IX8 {
    base ARCOS_PLATFORM;
    description
      "Quanta sysid x86-64-quanta-ix8-rglbmc-r0";
  }
  identity IX8A {
    base ARCOS_PLATFORM;
    description
      "Quanta sysid x86-64-quanta-ix8a-dnv-r0";
  }
  identity IXAE_COMEDNV {
    base ARCOS_PLATFORM;
    description
      "Quanta sysid x86-64-quanta-ixae-comednv-r0";
  }
  identity IXAE_COME {
    base ARCOS_PLATFORM;
    description
      "Quanta sysid x86-64-quanta-ixae-come-r0";
  }
  identity IXA_COMEDNV {
    base ARCOS_PLATFORM;
    description
      "Quanta sysid x86-64-quanta-ixa-comednv-r0";
  }
  identity IXA_COME {
    base ARCOS_PLATFORM;
    description
      "Quanta sysid x86-64-quanta-ixa-come-r0";
  }
  identity SEASTONE_2 {
    base ARCOS_PLATFORM;
    description
      "Celestica sysid x86-64-cel-seastone-2-r0";
  }
  identity AGC5648S {
    base ARCOS_PLATFORM;
    description
      "Delta sysid x86-64-delta-agc5648s-r0";
  }
  identity QUESTONE_2 {
    base ARCOS_PLATFORM;
    description
      "Celestica sysid x86-64-cel-questone-2-r0";
  }
  identity QUESTONE_2A {
    base ARCOS_PLATFORM;
    description
      "Celestica sysid x86-64-cel-questone-2a-r0";
  }
  identity AGC9020S {
    base ARCOS_PLATFORM;
    description
      "Delta sysid x86-64-delta-agc9020s-r0";
  }
  identity AS4630_54PE {
    base ARCOS_PLATFORM;
    description
      "Accton sysid x86-64-accton-as4630-54pe-r0";
  }
  identity AS4630_54TE {
    base ARCOS_PLATFORM;
    description
      "Accton sysid x86-64-accton-as4630-54te-r0";
  }
  identity AS7326 {
    base ARCOS_PLATFORM;
    description
      "Accton sysid x86-64-accton-as7326-56x-r0";
  }
  identity AS7726_32X {
    base ARCOS_PLATFORM;
    description
      "Accton sysid x86-64-accton-as7726-32x-r0";
  }
  identity AS7926 {
    base ARCOS_PLATFORM;
    description
      "Delta sysid x86-64-accton-as7926-80xk-r0";
  }
  identity AS7926_40XKE {
    base ARCOS_PLATFORM;
    description
      "Delta sysid x86-64-accton-as7926-40xke-r0";
  }
  identity AS7926_40XKE_ROA {
    base ARCOS_PLATFORM;
    description
      "Delta sysid x86-64-accton-as7926-40xke-r0a";
  }
  identity AS9926_24D {
    base ARCOS_PLATFORM;
    description
      "Delta sysid x86-64-accton-as9926-24d-r0";
  }
  identity S9701_78DC {
    base ARCOS_PLATFORM;
    description
      "UFISpace sysid x86-64-ufispace-s9701-78dc-r0";
  }
  identity S9510_28DC {
    base ARCOS_PLATFORM;
    description
      "UFISpace sysid x86-64-ufispace-s9510-28dc-r0";
  }
  identity S9600_72XC {
    base ARCOS_PLATFORM;
    description
      "UFISpace sysid x86-64-ufispace-s9600-72xc-r0";
  }
  identity UFI_76D {
    base ARCOS_PLATFORM;
    description
      "UFISpace sysid x86_64-ufispace_s9710_76d-r0";
  }
  identity S9600_32X {
    base ARCOS_PLATFORM;
    description
      "UFISpace sysid x86-64-ufispace-s9600-32x-r0";
  }
  identity S9600_30DX {
    base ARCOS_PLATFORM;
    description
      "UFISpace sysid x86-64-ufispace-s9600-30dx-r0";
  }
  identity S9705_48D {
    base ARCOS_PLATFORM;
    description
      "UFISpace sysid x86-64-ufispace-s9705-48d-r7";
  }

  identity S9700_23D {
    base ARCOS_PLATFORM;
    description
      "UFISpace sysid x86-64-ufispace-s9700-23d-r7";
  }

  identity S9300-32D {
    base ARCOS_PLATFORM;
    description
      "UFISpace sysid x86-64-ufispace-s9300-32d-r0";
  }
  
  identity S9300-32DB {
    base ARCOS_PLATFORM;
    description
      "UFISpace sysid x86-64-ufispace-s9300-32db-r0";
  }

  identity S9301-32DB {
    base ARCOS_PLATFORM;
    description
      "UFISpace sysid x86-64-ufispace-s9301-32db-r0";
  }

  identity S9180_32X {
    base ARCOS_PLATFORM;
    description
      "Ingrasys sysid x86-64-ingrasys-s9180-32x-r0";
  }

  identity AURORA_710 {
    base ARCOS_PLATFORM;
    description
      "Netberg sysid x86-64-netberg-aurora-710-r0";
  }

  identity VM {
    base ARCOS_PLATFORM;
    description
      "Virtual machine";
  }

  identity OS {
     base ARCOS_PLATFORM;
     description
       "ArcOS on virtual or container";
   }
   identity RR {
     base ARCOS_PLATFORM;
     description
       "ArcRR on virtual or container";
   }

  identity SILVERSTONE {
    base ARCOS_PLATFORM;
    description
      "Celestica sysid x86-64-cel-silverstone-r0";
  }
  identity SILVERSTONE_DP {
    base ARCOS_PLATFORM;
    description
      "Celestica sysid x86-64-cel-silverstone-dp-r0";
  }
  identity B6910_3C {
    base ARCOS_PLATFORM;
    description
      "Ruijie sysid x86-64-ruijie-b6910-3c-r0";
  }
  identity AS9716_32D {
    base ARCOS_PLATFORM;
    description
      "Accton sysid x86-64-accton-as9716-32d-r0";
  }
  identity IVYSTONE {
    base ARCOS_PLATFORM;
    description
      "Celestica sysid x86-64-cel-ivystone-r0";
  }

  identity UFI_53DX {
    base ARCOS_PLATFORM;
    description
       "Ufispace sysid x86-64-ufispace-s9700-53dx-r9";
  }

  identity ARCOS_DEPLOYMENT_TYPE {
    description
      "Base type for ARCOS deployment type";
  }

  identity STANDALONE {
    base ARCOS_DEPLOYMENT_TYPE;
    description
      "Standalone deployment type";
  }
  identity DISTRIBUTED {
    base ARCOS_DEPLOYMENT_TYPE;
    description
      "Distributed deployment type";
  }

  container platform {
    leaf type {
      type identityref {
        base ARCOS_PLATFORM;
      }
      description
        "Name of platform";
    }

    leaf family {
      type identityref {
        base ASIC_VENDOR_DEVICE_FAMILY;
      }
      description
        "Name of asic device family";
    }

    leaf asic {
      type identityref {
        base ASIC_VENDOR_DEVICE_TYPE;
      }
      description
        "Type of asic device";
    }

    leaf form-factor {
      type enumeration {
        enum UNKNOWN;
        enum 48x10GbE+6x40GbE;
        enum 48x25GbE+8x100GbE;
        enum 64x25GbE+8x100GbE;
        enum 32x100GbE;
        enum 32x400GbE;
        enum 36x400GbE;
        enum 24x400GbE;
        enum 48x1GbE+4x10GbE;
        enum 48x1GbE+4x25GbE+2x100GbE;
        enum 48x25GbE+6x100GbE;
        enum 20x100GbE;
        enum 40x100GbE;
        enum 24x100GbE+6x400GbE;
        enum 96x100GbE;
        enum 128x100GbE;
        enum 80x100GbE;
        enum 24x200GbE+8x400GbE;
        enum FF_VIRTUAL;
        enum FF_CONTAINER;
        enum 4x100GbE+24x25GbE;
        enum 10x400GbE;
      }
      description
        "Form factor of device";
    }

    leaf deployment-type {
      type identityref {
        base ARCOS_DEPLOYMENT_TYPE;
      }
      description
        "Kind of deployment standalone/distributed";
    }
  }
}
