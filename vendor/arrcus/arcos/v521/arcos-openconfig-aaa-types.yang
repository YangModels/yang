module arcos-openconfig-aaa-types {
  yang-version 1.1;
  namespace "http://yang.arrcus.com/arcos/openconfig/aaa/types";
  prefix arc-oc-aaa-types;

  import openconfig-aaa-types {
    prefix oc-aaa-types;
  }

  organization
    "Arrcus, Inc.";

  contact
    "Arrcus, Inc.
     2077 Gateway Place
     Suite 400
     San Jose, CA 95110

     E-mail: yang-support@arrcus.com";

  description
    "This module defines additional types/identities
     that base off of OpenConfig AAA types.

     Copyright (c) 2016-2019 by Arrcus, Inc.
     All rights reserved.";

  identity SYSTEM_ROLE_OPERATOR {
    base oc-aaa-types:SYSTEM_DEFINED_ROLES;
    description
      "Built-in role that limits user access to operational commands
       on the device.";
  }
}
