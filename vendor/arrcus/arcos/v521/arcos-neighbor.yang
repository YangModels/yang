module arcos-neighbor {
  yang-version 1.1;
  namespace "http://yang.arrcus.com/arcos/neighbor";
  prefix arc-nbr;

  import arcos-neighbor-types {
    prefix arc-nbr-types;
  }

  import openconfig-yang-types {
    prefix oc-yang;
  }

  import ietf-yang-types {
    prefix yang;
  }

  import ietf-inet-types {
    prefix inet;
  }

  organization
    "Arrcus, Inc.";

  contact
    "Arrcus, Inc.
     2077 Gateway Place
     Suite 400
     San Jose, CA 95110

     E-mail: yang-support@arrcus.com";

  description
    "This module contains definitions for the
     native ArcOS neighbor domain.

     Copyright (c) 2016-2019 by Arrcus, Inc.
     All rights reserved.";


  revision 2019-10-29 {
    description "Initial version";
  }


  container arp-entries {
    description
      "Address Resolution Protocol (ARP) table entries";

    config false;

    list arp-entry {
      key "ip ifname";

      description
        "IP Address and Interface of entry";

      leaf ip {
        type inet:ipv4-address-no-zone;
        description
          "Layer 3 IPv4 Address";
      }

      leaf ifname {
        type string;
        description
          "Interface over which ARP learned";
      }

      leaf hwaddr {
        mandatory true;
        type oc-yang:mac-address;
        description
          "Layer 2 address";
      }

      leaf last-updated {
        type yang:date-and-time;
        description
          "Last update time";
      }

      leaf age {
        type string;
        description
        "Time Elapsed since last change";
      }
    }
  }

  container arp-clear {
    description
      "Clear ARP entries";

    action all {
      description
        "Clear all ARP entries";

      output {
        leaf result {
          type string;
          description
            "The status of the operation";
        }
      }
    }

    action arp {
      description
        "Clear specific ARP entries";

      input {
        leaf ip {
          mandatory true;
          type inet:ipv4-address-no-zone;
          description
            "The IPv4 address to be cleared";
        }
      }
      output {
        leaf result {
          type string;
          description
            "The status of the operation";
        }
      }
    }

    action interface {
      description
        "Clear interface specific ARP entries";

      input {
        leaf name {
          mandatory true;
          type string;
          description
            "Interface to be cleared";
        }
      }
      output {
        leaf result {
          type string;
          description
            "The status of the operation";
        }
      }
    }

  }

  container ndp-entries {
    description
      "IPv6 Neighbor Discovery Protocol (NDP) table entries";

    config false;

    list ndp-entry {
      key "ip ifname";

      description
        "IP Address and Interface of entry";

      leaf ip {
        type inet:ipv6-address-no-zone;
        description
          "Layer 3 IPv6 Address";
      }

      leaf ifname {
        type string;
        description
          "Interface over which NDP learned";
      }

      leaf hwaddr {
        mandatory true;
        type oc-yang:mac-address;
        description
          "Layer 2 address";
      }

      leaf last-updated {
        type yang:date-and-time;
        description
          "Last update time";
      }

      leaf age {
        type string;
        description
        "Time Elapsed since last change";
      }
    }
  }

  container ndp-clear {
    description
      "Clear NDP entries";

    action all {
      description
        "Clear NDP entries for all interfaces";

      input {
        leaf global-only {
          default true;
          type boolean;
          description
            "If only the ipv6 global addresses need to be cleared. 
            Both global and link-local address entries are cleared when set to false.";
        }
      }

      output {
        leaf result {
          type string;
          description
            "The status of the operation";
        }
      }
    }

    action ndp {
      description
        "Clear specific NDP entries";

      input {
        leaf ipv6 {
          mandatory true;
          type inet:ipv6-address-no-zone;
          description
            "The IPv6 address to be cleared";
        }
      }
      output {
        leaf result {
          type string;
          description
            "The status of the operation";
        }
      }
    }
    action interface {
      description
        "Clear interface specific NDP entries";

      input {
        leaf global-only {
          default true;
          type boolean;
          description
            "If only the ipv6 global addresses need to be cleared. 
            Both global and link-local address entries are cleared when set to false.";
        }
        leaf name {
          mandatory true;
          type string;
          description
            "Interface to be cleared";
        }
      }
      output {
        leaf result {
          type string;
          description
            "The status of the operation";
        }
      }
    }
  }

  container adj-debug {
    description
      "Adjacency manager debug control";

    action ipv4 {
      input {
        leaf debug {
          mandatory true;
          type arc-nbr-types:adj-debug-type;
          description
            "Debug to be controlled";
        }

        leaf op {
          mandatory true;
          type arc-nbr-types:adj-debug-state;
          description
            "Turn on/off operation";
        }
      }
      output {
        leaf result {
          type string;
          description
            "The status of the operation";
        }
      }
    }

    action ipv6 {
      input {
        leaf debug {
          mandatory true;
          type arc-nbr-types:adj-debug-type;
          description
            "Debug to be controlled";
        }

        leaf op {
          mandatory true;
          type arc-nbr-types:adj-debug-state;
          description
            "Turn on/off operation";
        }
      }
      output {
        leaf result {
          type string;
          description
            "The status of the operation";
        }
      }
    }
  }

}
