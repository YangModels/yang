module arcos-runtime {
  yang-version 1.1;
  namespace "http://yang.arrcus.com/arcos/runtime";
  prefix arc-runtime;

  import openconfig-platform {
    prefix oc-platform;
  }

  import arcos-platform { prefix arc-platform; }

  typedef runtime-inst-type {
    type enumeration {
      enum DATAPATH_MGMT {
        description
          "Runtime instance managing an underlying datapath";
      }

      enum PUNTPATH_MGMT {
        description
          "Runtime instance managing the puntpath";
      }
    }
  }

  grouping runtime-inst-top {
    description
      "Top level grouping for runtime instances in ArcOS";

    container runtime-instances {
      when "/arc-platform:platform/arc-platform:deployment-type = 'arc-platform:DISTRIBUTED'";
      list runtime-instance {
        key "instance-name";
        config false;

        description
          " The Control plane Forwarding table associated with an address family.";

        leaf instance-name {
          type string;
          description
            "Unique name identifying the current runtime instance";
          mandatory true;
        }

        leaf instance-type {
          type runtime-inst-type;
          description
            "Type of the runtime instance";
          mandatory true;
        }

        leaf deployed-on {
          type leafref {
            path "/oc-platform:components/oc-platform:component" +
                 "/oc-platform:name";
          }
          description
            "Reference to component that this runtime instance is deployed on";
          mandatory true;
        }
      }
    }
  }
  uses runtime-inst-top;
}
