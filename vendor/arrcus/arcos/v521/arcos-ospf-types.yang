module arcos-ospf-types {

  yang-version "1.1";

  namespace "http://yang.arrcus.com/arcos/ospf/types";

  prefix "arc-ospf-types";

  import ietf-yang-types { prefix "yang"; }
  import openconfig-extensions { prefix "oc-ext"; }

  description
    "Type definitions for OSPF";

  // OpenConfig specific extensions for module metadata.
  oc-ext:regexp-posix;


  typedef ospf-log-adj-changes-type {
    type enumeration {
      enum LOG_ADJ_DISABLE {
        description
          "Syslog is not generated when Neighbor state changes.";
      }
      enum LOG_ADJ_ENABLE_LIMITED {
        description
          "Syslog is generated when Neighbor state changes to DOWN or FULL.";
      }
      enum LOG_ADJ_ENABLE_DETAILED {
        description
          "Syslog is generated when Neighbor state changes to any state.";
      }
    }

    description
      "Type to specify whether and how often syslogs are generated when
      an OSPF neighbor change its states.";
  }

  typedef ospf-maintenance-trigger-type {
    type enumeration {
      enum MAINTENANCE_TRIGGER_ALWAYS {
        description
          "Maintenance-mode triggered always.";
      }
    }

    description
      "Type to specify the type of maintenance-mode trigger.";
  }

  typedef ospf-max-lsa-sm-state-type {
    type enumeration {
      enum MAX_LSA_DISABLED {
        description
          "Max-LSA is disabled.";
      }

      enum MAX_LSA_NORMAL {
        description
          "Max-LSA is in Normal state and limit is not reached.";
      }

      enum MAX_LSA_LIMIT {
        description
          "Max-LSA limit has been reached.";
      }

      enum MAX_LSA_DOWN {
        description
          "Max-LSA is in Down state.";
      }

      enum MAX_LSA_PERMA_DOWN {
        description
          "Max-LSA is in permanent Down state.";
      }
    }

    description
      "Type to specify the state of Max-LSA.";
  }

  typedef ospf-area-type {
    type enumeration {
      enum AREA_TYPE_NORMAL {
        description
          "Normal area";
      }
      enum AREA_TYPE_STUB {
        description
          "Stub area";
      }
    }

    description
      "Type to specify the type of an OSPF area.";
  }

  /*
   * Area ID type
   */
  typedef ospf-area-identifier {
    type union {
      type uint32;
      type yang:dotted-quad;
    }
    description
      "An identifier for an area with OSPF version 2 or 3. This value
      is expressed as either a dotted-quad, or a unsigned 32-bit
      number";
  }

  typedef ospf-metric-type {
    type enumeration {
      enum TYPE_1_METRIC {
        description
          "Type-1 external metric";
      }
      enum TYPE_2_METRIC {
        description
          "Type-2 external metric";
      }
    }

    description
      "Type to specify the external metric type of a OSPF route.";
  }

  /*
   * Metric value type
   */
  typedef ospf-metric {
    type uint16 {
      range "1..65535";
    }
    description
      "A common type that can be utilised to express an OSPF metric";
  }

  /*
   * SR SID Type
   */
  typedef sr-sid-type {
    type enumeration {
      enum LABEL {
        description
          "When the length of the SR/Label Sub-TLV is specified to be 3, then
          the right-most 20-bits represent a label value within the SR/Label
          Sub-TLV. When this leaf is set to a value of Label the first-entry
          leaf should be interpreted to be an MPLS label.";
      }
      enum SID {
        description
          "When the length of the SR/Label Sub-TLV is specified to be 4, then
          the value specified in the first-entry leaf should be specified to
          be a segment identifier.";
      }
    }
    description
      "A common type used to express the type of segment identifier that is
      used in LSDB entries relating to segment routing";
  }

  /*
   * Address aggregate advertisement type
   */
  typedef ospf-aggregate-advertisement {
    type enumeration {
      enum AGGREGATE_ADVERTISE {
        description
          "Advertise a given OSPF address aggregate.";
      }

      enum AGGREGATE_DONT_ADVERTISE {
        description
          "Do not advertise a given OSPF address aggregate.";
      }
    }
    description
      "Advertisement status of an OSPF address aggregate.";
  }

  /*
   * LSA Type identity
   */
  identity OSPF_LSA_TYPE {
    description
      "Base identity for an OSPF LSA type. This identity is intended
      to be used across both OSPFv2 and OSPFv3. Identity values that
      correspond to only one OSPF version are marked as such.";
  }

  identity ROUTER_LSA {
    base "OSPF_LSA_TYPE";
    description
      "Type 1 - ROUTER_LSA. An LSA originated by each router within
      the area describing the state and cost of the router's links
      in the area.";
    reference "RFC2328";
  }

  identity NETWORK_LSA {
    base "OSPF_LSA_TYPE";
    description
      "Type 2 - NETWORK_LSA. An LSA originated for each broadcast and
      non-broadcast multiple access (NBMA) in the area. This LSA is
      originated by the designated router.";
    reference "RFC2328";
  }

  identity SUMMARY_IP_NETWORK_LSA {
    base "OSPF_LSA_TYPE";
    description
      "Type 3 - SUMMARY_IP_NETWORK_LSA. An LSA originated by area
      border routers describing inter-area destinations. This LSA type
      is used when the destination is an IP network";
    reference "RFC2328";
  }

  identity SUMMARY_ASBR_LSA {
    base "OSPF_LSA_TYPE";
    description
      "Type 4 - SUMMARY_ASBR_LSA. An LSA originated by an area border
      router describing inter-area destinations. This LSA type is used
      when the destination is an AS boundary router.";
    reference "RFC2328";
  }

  identity AS_EXTERNAL_LSA {
    base "OSPF_LSA_TYPE";
    description
      "Type 5 - AS_EXTERNAL_LSA. This LSA type is used to describe
      destinations external to the autonomous system, and is
      originated by an AS boundary router (ASBR).";
    reference "RFC2328";
  }

  identity NSSA_AS_EXTERNAL_LSA {
    base "OSPF_LSA_TYPE";
    description
      "Type 7 - NSSA_AS_EXTERNAL_LSA. This LSA type is used by
      systems within a not-so-stubby-area (NSSA) to inject external
      prefixes into the LSDB. They are translated to Type 5 LSAs
      at an ABR device.";
    reference "RFC3101";
  }

  identity OSPFV2_LINK_SCOPE_OPAQUE_LSA {
    base "OSPF_LSA_TYPE";
    description
      "Type 9 - OSPFV2_LINK_SCOPE_OPAQUE_LSA. This LSA type is used
      in OSPFv2 to distribute arbitrary information via the OSPF
      protocol. The contents is specific to the application defining
      the Opaque Type specified within the LSDB. LSAs with Type 9 have
      a scope of the link that they are being transmitted on (and the
      associated network or subnetwork).";
    reference "RFC5250";
  }

  identity OSPFV2_AREA_SCOPE_OPAQUE_LSA {
    base "OSPF_LSA_TYPE";
    description
      "Type 10 - OSPFV2_AREA_SCOPE_OPAQUE_LSA. This LSA type is used
      in OSPFv2 to distribute arbitrary information via the OSPF
      protocol. The contents is specific to the application defining
      the Opaque Type specified within the LSDB. LSAs with Type 10 have
      a scope of the area that they are transmitted within.";
    reference "RFC5250";
  }

  identity OSPFV2_AS_SCOPE_OPAQUE_LSA {
    base "OSPF_LSA_TYPE";
    description
      "Type 11 - OSPFV2_AS_SCOPE_OPAQUE_LSA. This LSA type is used
      in OSPFv2 to distribute arbitrary information via the OSPF
      protocol. The contents is specific to the application defining
      the Opaque Type specified within the LSDB. LSAs with Type 11
      have a scope of the autonomous system that they are transmitted
      within.";
    reference "RFC5250";
  }

  identity OSPFV3_INTER_AREA_PREFIX_LSA {
    base "OSPF_LSA_TYPE";
    description
      "Type 0x2003 - OSPFV3_INTER_AREA_PREFIX_LSA. This LSA is the IPv6
      equivalent of OSPF for IPv4's type 3 summary-LSAs. Originated by
      area border routers, they describe routes to IPv6 address prefixes
      that belong to other areas.";
    reference "RFC5340";
  }

  identity OSPFV3_INTER_AREA_ROUTER_LSA {
    base "OSPF_LSA_TYPE";
    description
      "Type 0x2004 - OSPFV3_INTER_AREA_ROUTER_LSA. This LSA is the IPv6
      equivalent of OSPF for IPv4's type 4 summary-LSAs. Originated by
      area border routers, they describe route to AS boundary router in
      other areas.";
    reference "RFC5340";
  }

  identity OSPFV3_LINK_LSA {
    base "OSPF_LSA_TYPE";
    description
      "Type 0x0008 - OSPFV3_LINK_LSA. A router originates a separate
      link-LSA for each attached physical link. This LSA is used in OSPFv3
      to distribute IPv6 addresses associated with the link and the
      collection of Options bits in the network-LSA originated by the
      Designated Router on the link. This LSA has link-local flooding scope
      and is never flooded beyond the associated link.";
    reference "RFC5340";
  }

  identity OSPFV3_INTRA_AREA_PREFIX_LSA {
    base "OSPF_LSA_TYPE";
    description
      "Type 0x2009 - OSPFV3_INTRA_AREA_PREFIX_LSA. This LSA is used to
      advertise one or more IPv6 address prefixes that are associated with
      a local router address, an attached stub network segment, or an
      attached transit network segment.";
    reference "RFC5340";
  }

  /*
   * Router LSA Type identity
   */
  identity ROUTER_LSA_TYPES {
    description
      "Sub-types of the router LSA";
  }

  identity ROUTER_LSA_P2P {
    base "ROUTER_LSA_TYPES";
    description
      "The LSA represents a point-to-point connection to another
      router";
  }

  identity ROUTER_LSA_TRANSIT_NETWORK {
    base "ROUTER_LSA_TYPES";
    description
      "The LSA represents a connection to a transit network";
  }

  identity ROUTER_LSA_STUB_NETWORK {
    base "ROUTER_LSA_TYPES";
    description
      "The LSA represents a connection to a stub network";
  }

  identity ROUTER_LSA_VIRTUAL_LINK {
    base "ROUTER_LSA_TYPES";
    description
      "The LSA represents a virtual link connection";
  }

  /*
   * Neighbor State identity
   */
  identity OSPF_NEIGHBOR_STATE {
    description
      "The state of an adjacency between the local system and a remote
      device";
  }

  identity NEIGHBOR_DOWN {
    base "OSPF_NEIGHBOR_STATE";
    description
      "The initial state of a neighbor, indicating that no recent
      information has been received from the neighbor.";
    reference "RFC2328";
  }

  identity NEIGHBOR_ATTEMPT {
    base "OSPF_NEIGHBOR_STATE";
    description
      "Utilised for neighbors that are attached to NBMA networks, it
      indicates that no information has been recently received from
      the neighbor but that Hello packets should be directly sent
      to that neighbor.";
    reference "RFC2328";
  }

  identity NEIGHBOR_INIT {
    base "OSPF_NEIGHBOR_STATE";
    description
      "Indicates that a Hello packet has been received from the
      neighbor but bi-directional communication has not yet been
      established. That is to say that the local Router ID does
      not appear in the list of neighbors in the remote system's
      Hello packet.";
    reference "RFC2328";
  }

  identity NEIGHBOR_TWO_WAY {
    base "OSPF_NEIGHBOR_STATE";
    description
      "Communication between the local and remote system is
      bi-directional such that the local system's Router ID is listed
      in the received remote system's Hello packet.";
    reference "RFC2328";
  }

  identity NEIGHBOR_EXSTART {
    base "OSPF_NEIGHBOR_STATE";
    description
      "An adjacency with the remote system is being formed. The local
      system is currently transmitting empty database description
      packets in order to establish the master/slave relationship for
      the adjacency.";
    reference "RFC2328";
  }

  identity NEIGHBOR_EXCHANGE {
    base "OSPF_NEIGHBOR_STATE";
    description
      "The local and remote systems are currently exchanging database
      description packets in order to determine which elements of
      their local LSDBs are out of date.";
    reference "RFC2328";
  }

  identity NEIGHBOR_LOADING {
    base "OSPF_NEIGHBOR_STATE";
    description
      "The local system is sending Link State Request packets to the
      remote system in order to receive the more recently LSAs that
      were discovered during the Exchange phase of the procedure
      establishing the adjacency.";
    reference "RFC2328";
  }

  identity NEIGHBOR_FULL {
    base "OSPF_NEIGHBOR_STATE";
    description
      "The neighboring routers are fully adjacent such that both
      LSDBs are synchronized. The adjacency will appear in Router and
      Network LSAs";
    reference "RFC2328";
  }

  /*
   * Network Type identity
   */
  identity OSPF_NETWORK_TYPE {
    description
      "Types of network that OSPF should consider attached to an
      interface";
  }

  identity POINT_TO_POINT_NETWORK {
    base "OSPF_NETWORK_TYPE";
    description
      "A interface that connects two routers.";
    reference "RFC2328";
  }

  identity BROADCAST_NETWORK {
    base "OSPF_NETWORK_TYPE";
    description
      "An interface that supports >2 attached routers which has the
      ability to address all connected systems via a single
      (broadcast) address.";
  }

  /*
   * OSPF Interface State identity
   */
  identity OSPF_INTERFACE_STATE {
    description
      "The state of an OSPF interface";
  }

  identity INTERFACE_DOWN {
    base "OSPF_INTERFACE_STATE";
    description
      "The initial state of an interface.";
    reference "RFC2328";
  }

  identity INTERFACE_LOOPBACK {
    base "OSPF_INTERFACE_STATE";
    description
      "Interface is a loopback interface.";
    reference "RFC2328";
  }

  identity INTERFACE_POINT_TO_POINT {
    base "OSPF_INTERFACE_STATE";
    description
      "Interface connects to a point-to-point network
       or a virtual-link.";
    reference "RFC2328";
  }

  identity INTERFACE_WAITING {
    base "OSPF_INTERFACE_STATE";
    description
      "The router is trying to determine the identity of
       the Designated Router and Backup Designated Router
       for the interface.";
    reference "RFC2328";
  }

  identity INTERFACE_DR {
    base "OSPF_INTERFACE_STATE";
    description
      "The router itself has been selected as the
       Desginated Router on the attached network.";
    reference "RFC2328";
  }

  identity INTERFACE_BACKUP {
    base "OSPF_INTERFACE_STATE";
    description
      "The router itself has been selected as the
       Backup Desginated Router on the attached network.";
    reference "RFC2328";
  }

  identity INTERFACE_DR_OTHER {
    base "OSPF_INTERFACE_STATE";
    description
      "The router itself has not been selected as either the
       Desginated Router or the Backup Designated Router
       on the attached network.";
    reference "RFC2328";
  }

  /*
   * OSPF route type identity
   */
  identity OSPF_ROUTE_TYPE {
    description
      "Base identity for an OSPF route type. This identity is intended
      to be used across both OSPFv2 and OSPFv3. Identity values that
      correspond to only one OSPF version are marked as such.";
  }

  identity OSPF_INVALID_ROUTE {
    base "OSPF_ROUTE_TYPE";
    description
      "OSPF unknown/invalid route type.";
  }

  identity OSPF_INTRA_AREA_ROUTE {
    base "OSPF_ROUTE_TYPE";
    description
      "OSPF intra-area route type.";
  }

  identity OSPF_INTER_AREA_ROUTE {
    base "OSPF_ROUTE_TYPE";
    description
      "OSPF inter-area route type.";
  }

  identity OSPF_EXTERNAL_TYPE1_ROUTE {
    base "OSPF_ROUTE_TYPE";
    description
      "OSPF external type 1 route type.";
  }

  identity OSPF_EXTERNAL_TYPE2_ROUTE {
    base "OSPF_ROUTE_TYPE";
    description
      "OSPF external type 1 route type.";
  }

  identity OSPF_NSSA_TYPE1_ROUTE {
    base "OSPF_ROUTE_TYPE";
    description
      "OSPF NSSA type 1 route type.";
  }

  identity OSPF_NSSA_TYPE2_ROUTE {
    base "OSPF_ROUTE_TYPE";
    description
      "OSPF NSSA type 2 route type.";
  }

  identity OSPF_INTRA_AREA_CONNECTED_ROUTE {
    base "OSPF_ROUTE_TYPE";
    description
      "OSPF intra-area connected route type.";
  }

  identity OSPF_EXTERNAL_TYPE1_REDIST_ROUTE {
    base "OSPF_ROUTE_TYPE";
    description
      "OSPF external type 1 redistributed route type.";
  }

  identity OSPF_EXTERNAL_TYPE2_REDIST_ROUTE {
    base "OSPF_ROUTE_TYPE";
    description
      "OSPF external type 1 redistributed route type.";
  }


  /*
   * OSPF SPF Trigger Type identity
   */
  identity OSPF_SPF_TRIGGER_TYPE {
    description
      "The type of event that triggers an SPF run";
  }

  identity SPF_TRIGGER_UNKNOWN {
    base "OSPF_SPF_TRIGGER_TYPE";
    description
      "Unknown trigger.";
  }

  identity SPF_TRIGGER_LSA_SELF_ORIG {
    base "OSPF_SPF_TRIGGER_TYPE";
    description
      "LSA self-origination.";
  }

  identity SPF_TRIGGER_REMOTE_LSA_CREATE {
    base "OSPF_SPF_TRIGGER_TYPE";
    description
      "Remote LSA creation.";
  }

  identity SPF_TRIGGER_REMOTE_LSA_UPDATE {
    base "OSPF_SPF_TRIGGER_TYPE";
    description
      "Remote LSA update.";
  }

  identity SPF_TRIGGER_LSA_MAXAGE {
    base "OSPF_SPF_TRIGGER_TYPE";
    description
      "LSA MaxAge.";
  }

  identity SPF_TRIGGER_ROUTE_UPDATE {
    base "OSPF_SPF_TRIGGER_TYPE";
    description
      "Route update.";
  }

  identity SPF_TRIGGER_REDIST_ROUTE_UPDATE {
    base "OSPF_SPF_TRIGGER_TYPE";
    description
      "Redistributed route update.";
  }

  identity SPF_TRIGGER_LSDB_CLEANUP {
    base "OSPF_SPF_TRIGGER_TYPE";
    description
      "LSDB cleanup.";
  }


  /*
   * OSPF SPF Delay State identity
   */
  identity OSPF_SPF_DELAY_SM_STATE {
    description
      "The state of SPF Delay state machine.";
  }

  identity SPF_DELAY_STATE_QUIET {
    base "OSPF_SPF_DELAY_SM_STATE";
    description
      "QUIET state.";
    reference "RFC8405";
  }

  identity SPF_DELAY_STATE_SHORT_WAIT {
    base "OSPF_SPF_DELAY_SM_STATE";
    description
      "SHORT_WAIT state.";
    reference "RFC8405";
  }

  identity SPF_DELAY_STATE_LONG_WAIT {
    base "OSPF_SPF_DELAY_SM_STATE";
    description
      "LONG_WAIT state.";
    reference "RFC8405";
  }

  /*
   * OSPF Authentication Type identity
   */
  identity OSPF_AUTH_TYPE {
    description
      "The type of OSPF authentication.";
  }

  identity OSPF_AUTH_NULL {
    base "OSPF_AUTH_TYPE";
    description
      "Null i.e. no authentication.";
    reference "RFC2328";
  }

  identity OSPF_AUTH_CRYPTO_KEY {
    base "OSPF_AUTH_TYPE";
    description
      "Cryptographic key based authentication.";
    reference "RFC2328";
  }

  /*
   * OSPF Crypto Algorithm identity
   */
  identity OSPF_CRYPTO_ALGO {
    description
      "The cryptogrphic algorithm used by OSPF.";
  }

  identity OSPF_CRYPTO_ALGO_MD5 {
    base "OSPF_CRYPTO_ALGO";
    description
      "MD5 cryptographic authentication.";
    reference "RFC2328";
  }

  /*
   * OSPF Route Flags
   */
  identity OSPF_ROUTE_FLAG {
    description "OSPF Route Flag";
  }

  identity INSTALLED {
    base OSPF_ROUTE_FLAG;
    description "Installed in L3RIB";
  }

  identity SUMMARY_AGGREGATE_CONTRIBUTOR {
    base OSPF_ROUTE_FLAG;
    description "Summary aggregate contributor";
  }

  identity REDISTRIBUTE_AGGREGATE_CONTRIBUTOR {
    base OSPF_ROUTE_FLAG;
    description "Redistribute aggregate contributor";
  }

  /*
   * OSPF Path Flags
   */
  identity OSPF_PATH_FLAG {
    description "OSPF Path Flag";
  }

  identity STALE {
    base OSPF_PATH_FLAG;
    description "Stale";
  }

  identity CONNECTED {
    base OSPF_PATH_FLAG;
    description "Interface connected";
  }

  identity REDISTRIBUTED {
    base OSPF_PATH_FLAG;
    description "Redistributed";
  }

  identity NO_UNICAST {
    base OSPF_PATH_FLAG;
    description "No Unicast";
  }

  identity SUMMARY_AGGREGATE_RANGE {
    base OSPF_PATH_FLAG;
    description "Summary aggregate range";
  }

  identity REDISTRIBUTE_AGGREGATE_RANGE {
    base OSPF_PATH_FLAG;
    description "Redistribute aggregate range";
  }

  identity SUMMARY_AGGREGATE_ADVERTISE {
    base OSPF_PATH_FLAG;
    description "Advertise summary aggregate";
  }

  identity REDISTRIBUTE_AGGREGATE_ADVERTISE {
    base OSPF_PATH_FLAG;
    description "Advertise redistribute aggregate";
  }
}
