submodule arcos-ospf-common {

  yang-version "1.1";

  belongs-to arcos-ospf {
    prefix "arc-ospf";
  }

  import ietf-yang-types { prefix "yang"; }
  import openconfig-types { prefix "oc-types"; }
  import arcos-ospf-types { prefix "arc-ospf-types"; }
  import arcos-system-types { prefix arc-sys-types; }

  description
    "This submodule provides OSPF configuration and operational
    state parameters that are common under one or more contexts.";


  /*
   * OSPF generic LSA key
   */
  grouping ospf-lsa-key-info {
    description
      "This grouping defines OSPF LSA key state from LSA header.";

    leaf lsa-type {
      type identityref {
        base "arc-ospf-types:OSPF_LSA_TYPE";
      }
      description
        "The type of LSA being described.";
    }

    leaf link-state-id {
      type yang:dotted-quad;
      description
        "The Link State ID for the specified LSA type. The exact
        defined value of the Link State ID is dependent on the LSA
        type.";
    }

    leaf advertising-router {
      type yang:dotted-quad;
      description
        "The router ID of the router that originated the LSA";
    }
  }

  /*
   * OSPF generic LSA instance
   */
  grouping ospf-lsa-instance-info {
    description
      "This grouping defines OSPF LSA instance information.";

    uses ospf-lsa-key-info;

    leaf age {
      type uint16;
      units seconds;
      description
        "The time since the LSA's generation in seconds";
    }

    leaf options {
      type uint8;
      description
        "The options field of the LSA; valid only for OSPFv2.";
    }

    leaf sequence-number {
      type int32;
      description
        "A signed 32-bit integer used to detect old and duplicate
        LSAs. The greater the sequence number the more recent the
        LSA.";
    }

    leaf checksum {
      type uint16;
      description
        "The checksum of the complete contents of the LSA excluding
        the age field.";
    }

    leaf length {
      type uint16;
      description
        "The length of the LSA.";
    }
  }


  /*
   * OSPF Authentication
   */
  grouping ospf-auth-config {
    description
      "This grouping describes OSPF authentication configuration.";

    leaf auth-type {
      type identityref {
        base "arc-ospf-types:OSPF_AUTH_TYPE";
      }
      description
        "The type of OSPF authentication configured.";
    }
  }

  grouping ospf-auth-state {
    description
      "This grouping describes OSPF authentication state.";

    leaf active-auth-type {
      type identityref {
        base "arc-ospf-types:OSPF_AUTH_TYPE";
      }
      description
        "The type of OSPF authentication in use.";
    }
  }

  grouping ospf-crypto-key-config {
    description
      "This grouping describes OSPF cryptographic key configuration.";

    leaf key-id {
      type uint32;
      description
        "The Key ID of the cryptographic key.";
    }

    leaf algorithm {
      type identityref {
        base "arc-ospf-types:OSPF_CRYPTO_ALGO";
      }
      description
        "The type of cryptographic algorithm.";
    }

    leaf key-string {
      type arc-sys-types:encrypted-string;
      description
        "The key string used to generate the crpytographic digest.";
    }
  }

  grouping ospf-crypto-key-state {
    description
      "This grouping describes OSPF cryptographic key state.";

    leaf is-valid {
      type boolean;
      description
        "Indicates if the cryptographic key config is complete and valid.";
    }
  }

  grouping ospf-auth-structure {
    description
      "This grouping describes OSPF authentication information.";

    container authentication {
      description
        "This container defines OSPF authentication information.";

      container config {
        description
          "This container describes OSPF authentication configuration.";

        uses ospf-auth-config;
      }

      container state {
        config false;
        description
          "This container describes OSPF authentication state.";

        uses ospf-auth-config;
        uses ospf-auth-state;
      }

      container crypto-key {
        description
          "This container describes a cryptographic key.";

        container config {
          description
            "This container defines cryptographic key configuration.";

          uses ospf-crypto-key-config;
        }

        container state {
          config false;
          description
            "This container defines cryptographic key state.";

          uses ospf-crypto-key-config;
          uses ospf-crypto-key-state;
        }
      }
    }
  }

  /*
   * OSPF BFD
   */
  grouping ospf-bfd-config {
    description
      "This grouping defines Bidirectionl-Forwarding-Detection
      configuration.";

    leaf enabled {
      type boolean;
      description
        "When set to true, BFD session will be created for OSPF neighbors.
        By default, BFD sesson is only created for neighbor in FULL state.";
    }

    reference "RFC5880: Bidirectional Forwarding Detection (BFD).";
  }

  grouping ospf-bfd-structure {
    description
      "This grouping defines interface BFD information.";

    container bfd {
      description
        "This container defines interface BFD information.";

      container config {
        description
          "This container defines BFD configuration parameters.";

        uses ospf-bfd-config;
      }

      container state {
        config false;
        description
          "This container defines BFD state information.";

        uses ospf-bfd-config;
      }
    }
  }

  /*
   * OSPF Auto-cost
   */
  grouping ospf-auto-cost-config {
    leaf enabled {
      type boolean;
      default true;
      description
        "Enable the calculation of metric based on interface bandwidth";
    }

    leaf reference-bandwidth {
      type uint64 {
        range "1 .. max";
      }
      default 3200;
      description
        "Specifiy bandwidth in Gbps";
    }
  }

  /*
   * OSPF Maintenance
   */
  grouping ospf-maint-router-lsa-config {
    description
      "This grouping defines maintenance mode Router LSA configuration.";

    leaf metric {
      type uint16;
      default 65535;
      description
        "The metric to be advertised in the LSA";
    }

    leaf set-link-metric {
      type boolean;
      description
        "Indicates if the configured (or default) metric should be
         advertised for non-stub links in the Router LSAs";
    }

    leaf set-stub-metric {
      type boolean;
      description
        "Indicates if the configured (or default) metric should be
         advertised for stub networks in the Router LSAs or
         Intra-Area-Prefix LSAs";
    }
  }

  grouping ospf-maint-summary-lsa-config {
    description
      "This grouping defines maintenance mode Summary LSAs configuration.";

    leaf metric {
      type uint32;
      default 16711680;
      description
        "The metric to be advertised in the LSA";
    }

    leaf set-metric {
      type boolean;
      description
        "Indicates if the configured (or default) metric should be
         advertised in the Summary LSAs";
    }
  }

  grouping ospf-maint-external-lsa-config {
    description
      "This grouping defines maintenance mode External LSA configuration.";

    leaf metric {
      type uint32;
      default 16711680;
      description
        "The metric to be advertised in the LSA";
    }

    leaf set-metric {
      type boolean;
      description
        "Indicates if the configured (or default) metric should be
         advertised in the External LSAs";
    }
  }

  grouping ospf-maint-trigger-config {
    description
      "This grouping defines maintenance mode trigger configuration.";

    leaf always {
      type boolean;
      description
        "Router is always in maintenance mode";
    }
  }

  grouping ospf-maint-structure {
    description
      "This grouping defines OSPF maintenance mode.";

    container router-lsa {
      description
        "This defines maintenance mode Router LSA config and state.";

      container config {
        description
          "This defines maintenance mode Router LSA config parameters.";

        uses ospf-maint-router-lsa-config;
      }

      container state {
        config false;
        description
          "This defines maintenance mode Router LSA state parameters.";

        uses ospf-maint-router-lsa-config;
      }
    }

    container summary-lsa {
      description
        "This defines maintenance mode Summary LSA config and state.";

      container config {
        description
          "This defines maintenance mode Summary LSA config parameters.";

        uses ospf-maint-summary-lsa-config;
      }

      container state {
        config false;
        description
          "This defines maintenance mode Summary LSA state parameters.";

        uses ospf-maint-summary-lsa-config;
      }
    }

    container external-lsa {
      description
        "This defines maintenance mode External LSA config and state.";

      container config {
        description
          "This defines maintenance mode External LSA config parameters.";

        uses ospf-maint-external-lsa-config;
      }

      container state {
        config false;
        description
          "This defines maintenance mode External LSA state parameters.";

        uses ospf-maint-external-lsa-config;
      }
    }

    container trigger {
      description
        "This defines maintenance mode triggers config and state.";

      container config {
        description
          "This defines maintenance mode triggers config parameters.";

        uses ospf-maint-trigger-config;
      }

      container state {
        config false;
        description
          "This defines maintenance mode triggers state parameters.";

        uses ospf-maint-trigger-config;
      }
    }

    container state {
      config false;
      description
        "This defines maintenance mode state.";

      leaf in-maintenance {
        type boolean;
        description
          "Indicates if OSPF is currently in maintenance mode";
      }

      leaf entry-trigger {
        type arc-ospf-types:ospf-maintenance-trigger-type;
        description
          "The current trigger for maintenance-mode entry.";
      }

      leaf entry-timestamp {
        type string;
        description
          "The timestamp of the current entry into maintenance mode.";
      }

      leaf previous-entry-trigger {
        type arc-ospf-types:ospf-maintenance-trigger-type;
        description
          "The most recent trigger for maintenance-mode entry.";
      }

      leaf previous-entry-timestamp {
        type string;
        description
          "The timestamp of the most recent entry into maintenance mode.";
      }

      leaf previous-exit-timestamp {
        type string;
        description
          "The timestamp of the most recent exit from maintenance mode.";
      }
    }
  }

  /*
   * Max-LSA
   */
  grouping ospf-max-lsa-config {
    description
      "This grouping defines Max-LSA configuration.";

    leaf lsa-limit {
      type uint32;
      description
        "Maximum number of remote LSAs allowed";
    }

    leaf warning-threshold {
      type uint8;
      description
        "Percentage threshold of lsa-limit at which to emit a warning";
    }

    leaf warning-only {
      type boolean;
      description
        "Indicates if lsa-limit should result in a warning only";
    }

    leaf avoid-down-state {
      type boolean;
      description
        "Indicates if DOWN state should be avoided";
    }

    leaf limit-monitor-time {
      type uint32;
      units seconds;
      description
        "Duration for monitoring the lsa-limit before moving from LIMIT to DOWN state";
    }

    leaf down-recovery-time {
      type uint32;
      description
        "Duration for waiting before recovering from DOWN state";
    }
  }

  grouping ospf-max-lsa-state {
    description
      "This grouping defines Max-LSA state.";

    leaf enabled {
      type boolean;
      description
        "Indicates if lsa-limit has been enabled";
    }

    leaf sm-state {
      type arc-ospf-types:ospf-max-lsa-sm-state-type;
      description
        "The Max-LSA state-machine state";
    }

    leaf remote-lsas {
      type uint32;
      description
        "Total number of remote LSAs in this OSPF instance";
    }

    leaf remote-lsas-ignored-limit {
      type uint64;
      description
        "Total number of remote LSA creations that were ignored
         due to reaching lsa-limit";
    }

    leaf normal-state-count {
      type uint64;
      description
        "Number of times the NORMAL state was entered";
    }

    leaf last-normal-state-timestamp {
      type string;
      description
        "The timestamp of the most recent entry into NORMAL state";
    }

    leaf limit-state-count {
      type uint64;
      description
        "Number of times the LIMIT state was entered";
    }

    leaf last-limit-state-timestamp {
      type string;
      description
        "The timestamp of the most recent entry into LIMIT state";
    }

    leaf down-state-count {
      type uint64;
      description
        "Number of times the DOWN state was entered";
    }

    leaf last-down-state-timestamp {
      type string;
      description
        "The timestamp of the most recent entry into DOWN state";
    }

    leaf monitor-timer-next-expiry-timestamp {
      type string;
      description
        "The future timestamp of the limit-monitor timer expiry.";
    }

    leaf monitor-timer-next-expiry-remaining-time {
      type uint32;
      description
        "The number of seconds left before the limit-monitor timer expires.";
    }

    leaf recovery-timer-next-expiry-timestamp {
      type string;
      description
        "The future timestamp of the down-recovery timer expiry.";
    }

    leaf recovery-timer-next-expiry-remaining-time {
      type uint32;
      description
        "The number of seconds left before the down-recovery timer expires.";
    }
  }

  grouping ospf-max-lsa-structure {
    description
      "This grouping defines OSPF Max-LSA.";

    container config {
      description
        "This defines Max-LSA config parameters.";

      uses ospf-max-lsa-config;
    }

    container state {
      config false;
      description
        "This defines Max-LSA state parameters.";

      uses ospf-max-lsa-config;
      uses ospf-max-lsa-state;
    }
  }


  /*
   * OSPF SNMP Config
   */
  grouping ospf-snmp-send-trap-config {
    description
      "This grouping defines OSPF SNMP trap generation configuration.";

    leaf if-state-change {
      type boolean;
      description
        "Indicates if IfStateChange trap can be generated";
    }

    leaf nbr-state-change {
      type boolean;
      description
        "Indicates if NbrStateChange trap can be generated";
    }

    leaf if-config-error {
      type boolean;
      description
        "Indicates if IfConfigError trap can be generated";
    }

    leaf if-auth-failure {
      type boolean;
      description
        "Indicates if IfAuthFailure trap can be generated";
    }

    leaf if-rx-bad-packet {
      type boolean;
      description
        "Indicates if IfRxBadPacket trap can be generated";
    }

    leaf tx-retransmit {
      type boolean;
      description
        "Indicates if TxRetransmit trap can be generated";
    }

    leaf originate-lsa {
      type boolean;
      description
        "Indicates if OriginateLsa trap can be generated";
    }

    leaf max-age-lsa {
      type boolean;
      description
        "Indicates if MaxAgeLsa trap can be generated";
    }

    leaf lsdb-approaching-overflow {
      type boolean;
      description
        "Indicates if LsdbApproachingOverflow trap can be generated";
    }

    leaf lsdb-overflow {
      type boolean;
      description
        "Indicates if LsdbOverflow trap can be generated";
    }
  }

  grouping ospf-snmp-structure {
    description
      "This grouping defines OSPF SNMP config and information.";

    container send-trap {
      description
        "This defines OSPF SNMP trap generation config and state.";

      container config {
        description
          "This defines OSPF SNMP trap generation config parameters.";

        uses ospf-snmp-send-trap-config;
      }

      container state {
        config false;
        description
          "This OSPF SNMP trap generation state parameters.";

        uses ospf-snmp-send-trap-config;
      }
    }
  }
}
