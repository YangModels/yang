module arcos-openconfig-bgp-policy-augments {
  yang-version 1.1;
  namespace "http://yang.arrcus.com/arcos/openconfig/bgp-policy/augments";
  prefix arc-oc-bgp-pol-aug;

  import arcos-openconfig-bgp-types {
    prefix arc-oc-bgp-types;
  }
  import openconfig-routing-policy {
    prefix oc-rpol;
  }
  import openconfig-bgp-policy {
    prefix oc-bgp-pol;
  }
  import openconfig-bgp-types {
    prefix oc-bgp-types;
  }
  import arcos-rov-types {
    prefix arc-rov-types;
  }

  organization
    "Arrcus, Inc.";
  contact
    "Arrcus, Inc.
     Customer Service
     Postal: 2077 Gateway Place
     San Jose, CA 95110
     Tel: +1 408 884-1965
     E-mail: yang-support@arrcus.com";
  description
    "This module defines augmentation for Arrcus
     implemention of the openconfig bgp-policy module.

     Copyright (c) 2016-2022 by Arrcus, Inc.
     All rights reserved.";

  revision 2022-04-22 {
    description
      "Add adjust-local-pref and adjust-med to bgp actions";
  }
  revision 2018-06-14 {
    description
      "Initial Revision
       * Add bgp large community
      ";
    reference
      "RFC 6020: YANG - A Data Modeling Language for the
       Network Configuration Protocol (NETCONF)";
  }

  grouping match-large-community-config {
    description
      "Configuration data for match conditions on large communities";
    leaf large-community-set {
      type leafref {
        path "/oc-rpol:routing-policy/oc-rpol:defined-sets/"
           + "oc-bgp-pol:bgp-defined-sets/arc-oc-bgp-pol-aug:large-community-sets/"
           + "arc-oc-bgp-pol-aug:large-community-set/arc-oc-bgp-pol-aug:large-community-set-name";
      }
      description
        "References a defined large community set";
    }
    uses oc-rpol:match-set-options-group;
  }

  grouping match-large-community-state {
    description
      "Operational state data for match conditions on large communities";
  }

  grouping match-large-community-top {
    description
      "Top-level grouping for match conditions on large communities";
    container match-large-community-set {
      description
        "Top-level container for match conditions on large communities.
         Match a referenced large-community-set according to the logic
         defined in the match-set-options leaf";
      container config {
        description
          "Configuration data for match conditions on large communities";
        uses match-large-community-config;
      }
      container state {
        config false;
        description
          "Operational state data ";
        uses match-large-community-config;
        uses match-large-community-state;
      }
    }
  }

  grouping community-set-reference-config {
    description
      "Configuration data for BGP community member set references for community-sets";
    leaf-list community-set-reference {
      type leafref {
        path "/oc-rpol:routing-policy/oc-rpol:defined-sets/" +
          "oc-bgp-pol:bgp-defined-sets/oc-bgp-pol:community-sets/" +
          "oc-bgp-pol:community-set/oc-bgp-pol:community-set-name";
      }
      max-elements 32;
      description
        "References to defined community sets that are included in current one";
    }
  }

  grouping ext-community-set-reference-config {
    description
      "Configuration data for BGP ext-community member set references for ext-community-sets";
    leaf-list ext-community-set-reference {
      type leafref {
        path "/oc-rpol:routing-policy/oc-rpol:defined-sets/" +
          "oc-bgp-pol:bgp-defined-sets/oc-bgp-pol:ext-community-sets/" +
          "oc-bgp-pol:ext-community-set/oc-bgp-pol:ext-community-set-name";
      }
      max-elements 32;
      description
        "References to defined ext-community sets that are included in current one";
    }
  }

  grouping large-community-set-config {
    description
      "Configuration data for BGP large community sets";
    leaf large-community-set-name {
      type string;
      mandatory true;
      description
        "name / label of the large community set -- this is used to
         reference the set in match conditions";
    }
    leaf-list large-community-member {
      type union {
        type arc-oc-bgp-types:bgp-std-large-community-type;
        type arc-oc-bgp-types:bgp-large-community-regexp-type;
      }
      max-elements 32;
      description
        "members of the large community set";
    }

    leaf-list large-community-set-reference {
      type leafref {
        path "/oc-rpol:routing-policy/oc-rpol:defined-sets/" +
          "oc-bgp-pol:bgp-defined-sets/arc-oc-bgp-pol-aug:large-community-sets/" +
          "arc-oc-bgp-pol-aug:large-community-set/arc-oc-bgp-pol-aug:large-community-set-name";
      }
      max-elements 32;
      description
        "References to defined large community sets that are included in current one";
    }
  }

  grouping large-community-set-state {
    description
      "Operational state data for BGP large community sets";
  }

  grouping large-community-set-top {
    description
      "Top-level grouping for BGP large community sets";
    container large-community-sets {
      description
        "Enclosing container for list of defined BGP large community sets";
      list large-community-set {
        key "large-community-set-name";
        description
          "List of defined BGP large community sets";
        leaf large-community-set-name {
          type leafref {
            path "../config/large-community-set-name";
          }
          description
            "Reference to list key";
        }
        container config {
          description
            "Configuration data for BGP large community sets";
          uses large-community-set-config;
        }
        container state {
          config false;
          description
            "Operational state data for BGP large community sets";
          uses large-community-set-config;
          uses large-community-set-state;
        }
      }
    }
  }

  grouping set-large-community-inline-config {
    description
      "Configuration data for inline specification of
       set-large-community action";
    /*
     * ARCOS
     */
    leaf-list large-communities {
      type arc-oc-bgp-types:bgp-std-large-community-type;
      max-elements 32;
      description
        "Set the large community values for the update inline
         with a list.";
    }
  }

  grouping set-large-community-inline-state {
    description
      "Operational state data or inline specification of
       set-large-community action";
  }

  grouping set-large-community-inline-top {
    description
      "Top-level grouping or inline specification of set-large-community
       action";
    container inline {
      /*
       * ARCOS
       */
      when "../config/method = 'INLINE'" {
        description
          "Active only when the set-community method is INLINE";
      }
      description
        "Set the extended community values for the action inline with
         a list.";
      container config {
        description
          "Configuration data or inline specification of
           set-large-community action";
        uses set-large-community-inline-config;
      }
      container state {
        config false;
        description
          "Operational state data or inline specification of
           set-large-community action";
        uses set-large-community-inline-config;
        uses set-large-community-inline-state;
      }
    }
  }

  grouping set-large-community-reference-config {
    description
      "Configuration data for referening a large community-set
       in the set-large-community action";
    leaf large-community-set-ref {
      type leafref {
        path "/oc-rpol:routing-policy/oc-rpol:defined-sets/"
           + "oc-bgp-pol:bgp-defined-sets/"
           + "arc-oc-bgp-pol-aug:large-community-sets/"
           + "arc-oc-bgp-pol-aug:large-community-set/"
           + "arc-oc-bgp-pol-aug:large-community-set-name";
      }
      description
        "References a defined large community set by
         name";
    }
  }

  grouping set-large-community-reference-state {
    description
      "Operational state data for referening an large
       community-set in the set-large-community action";
  }

  grouping set-large-community-reference-top {
    description
      "Top-level grouping for referening an large community-set
       in the set-community action";
    container reference {
      /*
       * ARCOS
       */
      when "../config/method = 'REFERENCE'" {
        description
          "Active only when the set-community method is REFERENCE";
      }
      description
        "Provide a reference to an large community set for the
         set-large-community action";
      container config {
        description
          "Configuration data for referening an large
           community-set in the set-large-community action";
        uses set-large-community-reference-config;
      }
      container state {
        config false;
        description
          "Operational state data for referening an large
           community-set in the set-large-community action";
        uses set-large-community-reference-config;
        uses set-large-community-reference-state;
      }
    }
  }

  grouping set-large-community-action-config {
    description
      "Configuration data for the set-large-community action";
    uses oc-bgp-pol:set-community-action-common;
  }

  grouping set-large-community-action-state {
    description
      "Operational state data for the set-large-community action";
  }

  grouping set-large-community-action-top {
    description
      "Top-level grouping for the set-large-community action";
    container set-large-community {
      description
        "Action to set the large community attributes of the
         route, along with options to modify how the community is
         modified. large communities may be set using an inline
         list OR a reference to an existing defined set (but not
         both).";
      container config {
        description
          "Configuration data for the set-large-community action";
        uses set-large-community-action-config;
      }
      container state {
        config false;
        description
          "Operational state data for the set-large-community action";
        uses set-large-community-action-config;
        uses set-large-community-action-state;
      }
      uses set-large-community-inline-top;
      uses set-large-community-reference-top;
    }
  }

  grouping set-community-additional-action-top {
    description
      "Top-level grouping for the set-community-additional action.
       This allows for adding and deleting communities in the same
       statement when used together with set-community. The two
       actions are functionally equivalent.";

    container set-community-additional {
      description
        "Action to add or remove community attributes of the
        route, along with options to modify how the community is
        modified. Communities may be set using an inline
        list OR a reference to an existing defined set (but not
        both). When used together with set-community, allows for
        adding and deleting communities in the same statement.";

      container config {
        description
          "Configuration data for the set-community-additional action";

        uses oc-bgp-pol:set-community-action-config;
      }

      container state {

        config false;

        description
          "Operational state data for the set-community action";

        uses oc-bgp-pol:set-community-action-config;
        uses oc-bgp-pol:set-community-action-state;
      }
      uses oc-bgp-pol:set-community-inline-top;
      uses oc-bgp-pol:set-community-reference-top;
    }
  }

  grouping set-ext-community-additional-action-top {
    description
      "Top-level grouping for the set-ext-community-additional action.
       This allows for adding and deleting ext-communities in the same
       statement when used together with set-ext-community. The two
       actions are functionally equivalent.";

    container set-ext-community-additional {
      description
        "Action to add or remove ext-community attributes of the
        route, along with options to modify how the community is
        modified. Ext-communities may be set using an inline
        list OR a reference to an existing defined set (but not
        both). When used together with set-ext-community, allows for
        adding and deleting ext-communities in the same statement.";

      container config {
        description
          "Configuration data for the set-ext-community action";

        uses oc-bgp-pol:set-ext-community-action-config;
      }

      container state {

        config false;

        description
          "Operational state data for the set-ext-community action";

        uses oc-bgp-pol:set-ext-community-action-config;
        uses oc-bgp-pol:set-ext-community-action-state;
      }
      uses oc-bgp-pol:set-ext-community-inline-top;
      uses oc-bgp-pol:set-ext-community-reference-top;
    }
  }

  grouping set-large-community-additional-action-top {
    description
      "Top-level grouping for the set-large-community-additional action.
       This allows for adding and deleting large-communities in the same
       statement when used together with set-large-community. The two
       actions are functionally equivalent.";

    container set-large-community-additional {
      description
        "Action to add or remove Large community attributes of the
        route, along with options to modify how the community is
        modified. Large communities may be set using an inline
        list OR a reference to an existing defined set (but not
        both). When used together with set-large-community, allows for
        adding and deleting large communities in the same statement.";

      container config {
        description
          "Configuration data for the set-large-community action";

        uses set-large-community-action-config;
      }

      container state {

        config false;

        description
          "Operational state data for the set-large-community action";

        uses set-large-community-action-config;
        uses set-large-community-action-state;
      }
      uses set-large-community-inline-top;
      uses set-large-community-reference-top;
    }
  }

  grouping as-path-set-reference-config {
    description
      "Configuration data for BGP as-path-set member set references for as-path-sets";
    leaf-list as-path-set-reference {
      type leafref {
        path "/oc-rpol:routing-policy/oc-rpol:defined-sets/" +
          "oc-bgp-pol:bgp-defined-sets/oc-bgp-pol:as-path-sets/" +
          "oc-bgp-pol:as-path-set/oc-bgp-pol:as-path-set-name";
      }
      max-elements 32;
      description
        "References to defined as-path-sets that are included in current one";
    }
  }

  /* augment statements */

  augment "/oc-rpol:routing-policy/oc-rpol:defined-sets/oc-bgp-pol:bgp-defined-sets" {
    description
      "adds BGP large communities set to bgp-defined-set container";
    uses large-community-set-top;
  }

  augment "/oc-rpol:routing-policy/oc-rpol:policy-definitions"
        + "/oc-rpol:policy-definition/oc-rpol:statements/oc-rpol:statement"
        + "/oc-rpol:conditions/oc-bgp-pol:bgp-conditions" {
    description
      "adds BGP large community set to bgp-match-conditions";
    uses match-large-community-top;
  }

  augment "/oc-rpol:routing-policy/oc-rpol:policy-definitions"
        + "/oc-rpol:policy-definition/oc-rpol:statements/oc-rpol:statement"
        + "/oc-rpol:actions/oc-bgp-pol:bgp-actions" {
    description
      "adds BGP large community set to bgp-actions";
    uses set-large-community-action-top;
  }

  augment "/oc-rpol:routing-policy/oc-rpol:policy-definitions" +
  "/oc-rpol:policy-definition/oc-rpol:statements/oc-rpol:statement" +
  "/oc-rpol:actions/oc-bgp-pol:bgp-actions" {
    description "adds BGP large community set to bgp-actions";

    uses set-community-additional-action-top;
    uses set-ext-community-additional-action-top;
    uses set-large-community-additional-action-top;
  }

  augment "/oc-rpol:routing-policy/oc-rpol:defined-sets" +
          "/oc-bgp-pol:bgp-defined-sets/oc-bgp-pol:community-sets" +
          "/oc-bgp-pol:community-set/oc-bgp-pol:config" {

    uses community-set-reference-config;
  }

  augment "/oc-rpol:routing-policy/oc-rpol:defined-sets" +
          "/oc-bgp-pol:bgp-defined-sets/oc-bgp-pol:community-sets" +
          "/oc-bgp-pol:community-set/oc-bgp-pol:state" {

    uses community-set-reference-config;
  }

  augment "/oc-rpol:routing-policy/oc-rpol:defined-sets" +
          "/oc-bgp-pol:bgp-defined-sets/oc-bgp-pol:ext-community-sets" +
          "/oc-bgp-pol:ext-community-set/oc-bgp-pol:config" {

    uses ext-community-set-reference-config;
  }

  augment "/oc-rpol:routing-policy/oc-rpol:defined-sets" +
          "/oc-bgp-pol:bgp-defined-sets/oc-bgp-pol:ext-community-sets" +
          "/oc-bgp-pol:ext-community-set/oc-bgp-pol:state" {

    uses ext-community-set-reference-config;
  }

  augment "/oc-rpol:routing-policy/oc-rpol:defined-sets" +
          "/oc-bgp-pol:bgp-defined-sets/oc-bgp-pol:as-path-sets" +
          "/oc-bgp-pol:as-path-set/oc-bgp-pol:config" {

    uses as-path-set-reference-config;
  }

  augment "/oc-rpol:routing-policy/oc-rpol:defined-sets" +
          "/oc-bgp-pol:bgp-defined-sets/oc-bgp-pol:as-path-sets" +
          "/oc-bgp-pol:as-path-set/oc-bgp-pol:state" {

    uses as-path-set-reference-config;
  }

  typedef bgp-set-aigp-type {
    type union {
      type uint32;
      type enumeration {
        enum IGP {
          description
            "set the AIGP metric value to the IGP cost toward the
             next hop for the route";
        }
      }
    }
    description
      "Type definition for specifying how the BGP AIGP can
       be set in BGP policy actions. The two choices are to set
       the value directly and set it to the IGP cost (predefined value).";
  }

  grouping set-aigp-top {
    leaf set-aigp {
      type bgp-set-aigp-type;
      description
        "set the AIGP metric";
    }
  }

  augment "/oc-rpol:routing-policy/oc-rpol:policy-definitions"
        + "/oc-rpol:policy-definition/oc-rpol:statements/oc-rpol:statement"
        + "/oc-rpol:actions/oc-bgp-pol:bgp-actions/oc-bgp-pol:config" {
    description
      "BGP AIGP metric set in bgp-actions";
    uses set-aigp-top;
  }

  augment "/oc-rpol:routing-policy/oc-rpol:policy-definitions"
        + "/oc-rpol:policy-definition/oc-rpol:statements/oc-rpol:statement"
        + "/oc-rpol:actions/oc-bgp-pol:bgp-actions/oc-bgp-pol:state" {
    description
      "BGP AIGP metric set in bgp-actions";
    uses set-aigp-top;
  }

  grouping set-srindex-top {
    leaf set-prefix-sid-index {
      type uint32 {
        range "0..1048575";
      }
      description 
        "set the prefix-sid-index";
    }
  }

  augment "/oc-rpol:routing-policy/oc-rpol:policy-definitions" +
          "/oc-rpol:policy-definition/oc-rpol:statements/oc-rpol:statement" +
          "/oc-rpol:actions/oc-bgp-pol:bgp-actions/oc-bgp-pol:config" {
    description 
      "BGP Segment routing  prefix-sid index set in bgp-actions";
    uses set-srindex-top;
  }

  augment "/oc-rpol:routing-policy/oc-rpol:policy-definitions" +
          "/oc-rpol:policy-definition/oc-rpol:statements/oc-rpol:statement" +
          "/oc-rpol:actions/oc-bgp-pol:bgp-actions/oc-bgp-pol:state" {
    description 
      "BGP Segment routing  prefix-sid index set in bgp-actions";
    uses set-srindex-top;
  }

  grouping test-afi-safi-top {
    leaf-list afi-safi-eq {
      type identityref {
        base oc-bgp-types:AFI_SAFI_TYPE;
      }
      max-elements 1;
      description
        "List of address families which the NLRI needs to be in";
    }
  }

  augment "/oc-rpol:routing-policy/oc-rpol:policy-definitions" +
          "/oc-rpol:policy-definition/oc-rpol:statements/oc-rpol:statement" +
          "/oc-rpol:conditions/oc-bgp-pol:bgp-conditions/oc-bgp-pol:config" {
    description "BGP AFI SAFI test in bgp-conditions";

    uses test-afi-safi-top;
  }

  augment "/oc-rpol:routing-policy/oc-rpol:policy-definitions" +
          "/oc-rpol:policy-definition/oc-rpol:statements/oc-rpol:statement" +
          "/oc-rpol:conditions/oc-bgp-pol:bgp-conditions/oc-bgp-pol:state" {
    description "BGP AFI SAFI test in bgp-conditions";

    uses test-afi-safi-top;
  }

  grouping set-afi-safi-top {
    leaf-list afi-safi {
      type identityref {
        base oc-bgp-types:AFI_SAFI_TYPE;
      }
      max-elements 1;
      description
        "List of address families which the NLRI may be redistributed";
    }
  }

  augment "/oc-rpol:routing-policy/oc-rpol:policy-definitions" +
          "/oc-rpol:policy-definition/oc-rpol:statements/oc-rpol:statement" +
          "/oc-rpol:actions/oc-bgp-pol:bgp-actions/oc-bgp-pol:config" {
    description "BGP AFI SAFI set in bgp-actions";

    uses set-afi-safi-top;
  }

  augment "/oc-rpol:routing-policy/oc-rpol:policy-definitions" +
          "/oc-rpol:policy-definition/oc-rpol:statements/oc-rpol:statement" +
          "/oc-rpol:actions/oc-bgp-pol:bgp-actions/oc-bgp-pol:state" {
    description "BGP AFI SAFI set in bgp-actions";

    uses set-afi-safi-top;
  }

  grouping attr-code-eq-top {
    description
      "Configuration data for filtering attr-code";
    leaf-list attr-code-eq {
      type uint8 {
        range "1..max";
      }
      max-elements 8;
      description
        "attribute code to filter";
    }
  }

  grouping add-path-flag-eq-top {
    description
      "Configuration data for selecting paths based on path flags";
    leaf add-path-flag-eq {
      type identityref {
        base arc-oc-bgp-types:ADD_PATHS_OPTIONS;
      }
      description
        "Select for add-path if path flags contains this flag";
    }
  }

  grouping rov-state-eq-top {
    description
      "Configuration data for filtering based on ROV state";
    leaf rov-state-eq {
      type identityref {
        base arc-rov-types:ROV_STATE;
      }
      description
        "ROV state to filter";
    }
  }

  augment "/oc-rpol:routing-policy/oc-rpol:policy-definitions"
        + "/oc-rpol:policy-definition/oc-rpol:statements/oc-rpol:statement"
        + "/oc-rpol:conditions/oc-bgp-pol:bgp-conditions/oc-bgp-pol:config" {
    description
      "Select BGP path attribute codes from list; Select based on add-path flag";
    uses attr-code-eq-top;
    uses add-path-flag-eq-top;
    uses rov-state-eq-top;
  }

  augment "/oc-rpol:routing-policy/oc-rpol:policy-definitions"
        + "/oc-rpol:policy-definition/oc-rpol:statements/oc-rpol:statement"
        + "/oc-rpol:conditions/oc-bgp-pol:bgp-conditions/oc-bgp-pol:state" {
    description
      "Select BGP path attribute codes from list; Select based on add-path flag";
    uses attr-code-eq-top;
    uses add-path-flag-eq-top;
    uses rov-state-eq-top;
  }

  grouping adjustment-params {
    description
      "Adjustment params: offset, maximum, minimum, and default for uint32 range";
    leaf offset {
      type int64 {
        range "-42949672295..4294967295";
      }
      description
        "Offset value for the adjustment. This is int64 but the adjustment
         result is capped by maximum and minimum, which are uint32";
    }
    leaf maximum {
      type uint32;
      must "not(../minimum) or (current() > ../minimum)" {
        error-message "Value for maximum must be larger than value of minimum";
      }
      description
        "Maximum result value after the offset is applied. Results higher than
         this value will be changed to the configured value";
    }
    leaf minimum {
      type uint32;
      must "not(../maximum) or (current() < ../maximum)" {
        error-message "Value for minimum must be smaller than value of maximum";
      }
      description
        "Minimum result value after the offset is applied. Results lower than
         this value will be changed to the configured value";
    }
    leaf default {
      type uint32;
      description
        "Default value if not previously set. This value will be used before
         the offset is applied. If not specified, offset adjustment will not
         occur if value not previously set.";
    }
  }

  grouping adjustment-config-and-state {
    description
      "Adjustment configs and states";
    container config {
      must "boolean(offset) or (not(maximum) and not(minimum) and not(default))" {
        error-message "Please configure offset first.";
      }
      description
        "Adjust configs with specified offset, limits, and default";
      uses adjustment-params;
    }
    container state {
      config false;
      description
        "Adjust states with specified offset, limits, and default";
      uses adjustment-params;
    }
  }

  grouping set-adjust-med-top {
    container adjust-med {
      description
        "Adjust MED with specified offset, limits, and default";
      uses adjustment-config-and-state;
    }
  }

  grouping set-adjust-local-pref-top {
    container adjust-local-pref {
      description
        "Adjust Local Pref with specified offset, limits, and default";
      uses adjustment-config-and-state;
    }
  }

  grouping set-drop-attr-top {
    leaf-list drop-attr {
      type uint8 {
        range "4..13 | 16..max";
      }
      max-elements 8;
      description
        "drop attributes with specified attr code";
    }
  }

  augment "/oc-rpol:routing-policy/oc-rpol:policy-definitions"
        + "/oc-rpol:policy-definition/oc-rpol:statements/oc-rpol:statement"
        + "/oc-rpol:actions/oc-bgp-pol:bgp-actions/oc-bgp-pol:config" {
    description
      "BGP drop attribute in bgp-actions";
    uses set-drop-attr-top;
  }

  augment "/oc-rpol:routing-policy/oc-rpol:policy-definitions"
        + "/oc-rpol:policy-definition/oc-rpol:statements/oc-rpol:statement"
        + "/oc-rpol:actions/oc-bgp-pol:bgp-actions/oc-bgp-pol:state" {
    description
      "BGP drop attribute in bgp-actions";
    uses set-drop-attr-top;
  }

  augment "/oc-rpol:routing-policy/oc-rpol:policy-definitions"
        + "/oc-rpol:policy-definition/oc-rpol:statements/oc-rpol:statement"
        + "/oc-rpol:actions/oc-bgp-pol:bgp-actions" {
    description
      "BGP adjust MED and Local Pref values in bgp-actions";
    uses set-adjust-med-top;
    uses set-adjust-local-pref-top;
  }
}
