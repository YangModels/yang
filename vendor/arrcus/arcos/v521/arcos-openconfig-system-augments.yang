module arcos-openconfig-system-augments {
  yang-version 1.1;
  namespace "http://yang.arrcus.com/arcos/openconfig/system/augments";
  prefix arc-oc-sys-aug;

  import openconfig-system {
    prefix oc-sys;
  }

  import openconfig-interfaces {
    prefix oc-if;
  }

  import openconfig-system-logging {
    prefix oc-sys-logging;
  }

  import openconfig-network-instance {
    prefix oc-ni;
  }

  import arcos-platform {
    prefix arc-platform;
  }

  import arcos-features {
    prefix arc-features;
  }

  import arcos-version {
    prefix arc-version;
  }

  import ietf-yang-types {
    prefix yang;
  }

  import ietf-inet-types {
    prefix inet;
  }

  import openconfig-inet-types {
    prefix oc-inet;
  }

  import arcos-system-management {
    prefix arc-sys-mgmt;
  }

  import arcos-system-types {
    prefix arc-sys-types;
  }

  import arcos-system-logging-types {
    prefix arc-sys-log-types;
  }

  import arcos-bgp-debug {
    prefix arc-bgp-dbg;
  }

  import openconfig-types {
    prefix oc-types;
  }

  organization
    "Arrcus, Inc.";

  contact
    "Arrcus, Inc.
     2077 Gateway Place
     Suite 400
     San Jose, CA 95110

     E-mail: yang-support@arrcus.com";

  description
    "This module defines ArcOS augments to the
     OpenConfig system module.

     Copyright (c) 2016-2022 by Arrcus, Inc.
     All rights reserved.";

  revision 2023-04-19 {
    description
      "Added support for configuring listen-interface and network instance for grpc server.
       Removed leaf permit-root-login.";
  }


  revision 2022-10-10 {
    description
      "Added support for configuring CLI idle-timeout";
  }

  revision 2022-09-01 {
    description
      "Added LDP to system logging component list";
  }

  revision 2022-06-29 {
    description
      "Added NTP Authentication Key support";
  }

  revision "2022-03-03" {
    description
      "Added support for SNMP in a non-default VRF";
  }

  revision "2022-03-02" {
    description
      "Added support for SSH in a non-default VRF";
  }

  grouping source-top {
    leaf source-interface {
      type leafref {
        path "/oc-if:interfaces/oc-if:interface/oc-if:config/oc-if:name";
      }
      description "Use IP address of this interface as source address";
    }

    leaf network-instance {
      type oc-ni:network-instance-ref;
      description
        "The network instance (VRF) to use for connecting to server.
         The above 'source-interface', if configured, must belong
         to this network instance. If no 'source-interface' is configured
         then the source interface and therefore the source IP address will
         be chosen automatically from within this network-instance";
    }
  }

  grouping aaa-server-group-state {
    container state {
      config false;
      description "State across all server groups";

      container authentication-statistics {
        description "Statistics for Remote Authentication";

        leaf accepts {
          type uint64;
          description "Number of authentication attempts that were successful";
        }
        leaf rejects {
          type uint64;
          description "Number of authentication attempts that were denied";
        }
      }

      container authorization-statistics {
        description "Statistics for Remote Authorization";
        leaf allows {
          type uint64;
          description "Number of authorization requests that were successful";
        }
        leaf denies {
          type uint64;
          description "Number of authorization requests that were denied";
        }
      }

      container accounting-statistics {
        description "Statistics for Remote Accounting";
        leaf successes {
          type uint64;
          description "Number of accounting messages that were successfully sent";
        }
        leaf failures {
          type uint64;
          description "Number of accounting messages that failed";
        }
      }
    }
  }

  grouping ntp-top {
    choice listen-type {
      leaf listen-interface {
        type leafref {
          path "/oc-if:interfaces/oc-if:interface/oc-if:config/oc-if:name";
        }
        description
           "Interface to use for sending and receiving NTP packets.
           Only one of 'listen-interface' or 'network-instance' must be
           configured.";
      }

      leaf network-instance {
        type oc-ni:network-instance-ref;
        description
          "The network instance (VRF) to use for communicating to NTP server.
           Only one of 'listen-interface' or 'network-instance' must be
           configured.";
      }
    }
  }

  grouping ntp-server-key {
    leaf key-id {
      type leafref {
        path "/oc-sys:system/oc-sys:ntp/oc-sys:ntp-keys/oc-sys:ntp-key/oc-sys:key-id";
      }
      description
        "Integer identifier used by the client and server to
        designate a secret key.  The client and server must use
        the same key id.";
    }
  }

  grouping ntp-server-state {
    leaf reach {
      type uint8;
      description
        "This is a 8-bit octal value that shows the success/failure of the
         connection attempts to reach the peer.";
    }

    leaf time-since-last-response {
      type union {
        type string {
          length "1";
          pattern "-";
        }
        type uint64;
      }
      units seconds;
      description
        "Time since the last response was received. Default unit is seconds,
         or it will be suffixed with m for minutes, h for hours and d for days.";
    }

    leaf association-status {
      type enumeration {
        enum SYNC_PPS {
          description
            "Selected for synchronization, PPS signal is in use.";
        }
        enum SYNC_SOURCE {
          description
            "Selected for synchronization.";
        }
        enum CANDIDATE {
          description
            "The peer is a survivor and a candidate for the combining algorithm.";
        }
        enum SELECTED {
          description
            "The peer is a survivor, but not among the first six peers
             sorted by synchronization distance.";
        }
        enum OUTLYER {
          description
            "The peer is discarded by the clustering algorithm as an outlyer.";
        }
        enum EXCESS {
          description
            "The peer is discarded as not among the first ten peers sorted by
             synchronization distance and so is probably a poor candidate for
             further consideration.";
        }
        enum FALSE_TICK {
          description
            "The peer is discarded by the intersection algorithm as a
             falseticker.";
        }
        enum REJECT {
          description
            "The peer is discarded as unreachable, synchronized to this server
             (synch loop) or outrageous synchronization distance.";
        }
      }
      description
        "Status of the NTP server in the clock selection process.";
    }
  }

  grouping system-logging-config {
    description
      "Configuration data for system logging";

    leaf timestamp-format {
      type identityref {
        base arc-sys-log-types:LOG_TIMESTAMP_FORMAT;
      }
      default arc-sys-log-types:TRADITIONAL;
      description
        "System logging timestamp format";
    }
  }

  grouping logging-remote-config {

    leaf source-interface {
      type oc-if:base-interface-ref;
      must "(not(boolean(../oc-sys:source-address)))" {
        error-message "source-address and source-interface " +
                      "are mutually exclusive";
      }
      description
        "The interface to bind to when sending syslog packets. The
         network instance will be automatically derived from the
         source interface";
    }

    leaf network-instance {
      type oc-ni:network-instance-ref;
      description
        "The network instance to use while sending to syslog host. The
         host stack will automatically choose the source interface
         and therefore the source IP address";
    }

    leaf facility-override {
      type identityref {
        base oc-sys-logging:SYSLOG_FACILITY;
      }
      description
        "Override the syslog facility level to the log server";
    }
  }

  grouping syslog-monitor-config {
    description
      "Configuration data for monitor logging";
    leaf severity {
      type oc-sys-logging:syslog-severity;
      default ERROR;
      description
        "Specifies that only messages of the given severity (or
        greater severity) for the corresponding component are logged";
    }
  }

  grouping syslog-monitor-state {
    description
      "Operational state data for monitor logging";
  }

  grouping syslog-monitor-top {
    description
      "Top-level grouping for monitor logging data";

    container monitor {
      description
        "Top-level container for data related to monitor-based
        logging";

      container config {
        description
          "Configuration data for monitor logging";

        uses syslog-monitor-config;
      }

      container state {

        config false;

        description
          "Operational state data for monitor logging";

        uses syslog-monitor-config;
        uses syslog-monitor-state;
      }
    }
  }

  grouping syslog-filter-config {
    description
      "Configuration data for syslog message filtering";
    container drop {
      description
        "Container for Drop messages which match";
      list contains {
        key "substring";
        leaf substring {
          type string {
            length "1..256";
          }
          description "specifies the substring to match";
        }
      }

      list regex {
        key "regex";
        leaf regex {
          type string {
            length "1..256";
          }
          description "specifies the regex expression to match";
        }
      }
    }

    container redirect {
      description
        "Container for Redirect messages which match";
      list contains {
        key "substring filename";
        leaf substring {
          type string {
            length "1..256";
          }
          description "specifies the substring to match";
        }

        leaf filename {
          type string {
            length "1..64";
          }
          description "specifies the filename (in /var/log) to redirect messages to";
        }
      }

      list regex {
        key "regex filename";
        leaf regex {
          type string {
            length "1..256";
          }
          description "specifies the regex expression to match";
        }

        leaf filename {
          type string {
            length "1..64";
          }
          description "specifies the filename to redirect messages to";
        }
      }
    }
  }

  grouping syslog-filter-top {
    description
      "Top-level grouping for syslog message filtering";

    container filter {
      description
        "Top-level container for data related to message filtering";

      container config {
        description
          "Configuration data for message filtering";

        uses syslog-filter-config;
      }

      container state {

        config false;

        description
          "Operational state data for message filtering";

        uses syslog-filter-config;
      }
    }
  }

  grouping syslog-component-config {
    description
      "Configuration data for components";

    leaf severity {
      type oc-sys-logging:syslog-severity;
      default DEBUG;
      description
        "Specifies that only messages of the given severity (or
        greater severity) for the corresponding component are logged";
    }
  }

  grouping syslog-component-state {
    description
      "Operational state data for components";
  }

  grouping syslog-component-adjmgr-top {
    container ADJMGR {
      description
        "Top-level container for data related to component ADJMGR
        logging";

      container config {
        description
          "Configuration data for component ADJMGR";

        uses syslog-component-config;
      }

      container state {
        config false;
        description
          "Operational state data for component ADJMGR";

        uses syslog-component-config;
        uses syslog-component-state;
      }
    }
  }

  grouping syslog-component-l2rib-top {
    container L2RIB {
      description
        "Top-level container for data related to component L2RIB
        logging";

      container config {
        description
          "Configuration data for component L2RIB";

        uses syslog-component-config;
      }

      container state {
        config false;
        description
          "Operational state data for component L2RIB";

        uses syslog-component-config;
        uses syslog-component-state;
      }
    }
  }

  grouping syslog-component-bfd-top {
    container BFD {
      description
        "Top-level container for data related to component BFD
        logging";

      container config {
        description
          "Configuration data for component BFD";

        uses syslog-component-config;
      }

      container state {
        config false;
        description
          "Operational state data for component BFD";

        uses syslog-component-config;
        uses syslog-component-state;
      }
    }
  }

  grouping syslog-component-bgp-top {
    container BGP {
      description
        "Top-level container for data related to component BGP
        logging";

      container config {
        description
          "Configuration data for component BGP";

        uses syslog-component-config;
      }

      container state {
        config false;
        description
          "Operational state data for component BGP";

        uses syslog-component-config;
        uses syslog-component-state;
      }
    }
  }

  grouping syslog-component-dpal-top {
    container DPAL {
      description
        "Top-level container for data related to component DPAL
        logging";

      container config {
        description
          "Configuration data for component DPAL";

        uses syslog-component-config;
      }

      container state {
        config false;
        description
          "Operational state data for component DPAL";

        uses syslog-component-config;
        uses syslog-component-state;
      }
    }
  }

  grouping syslog-component-fib-top {
    container FIB {
      description
        "Top-level container for data related to component FIB
        logging";

      container config {
        description
          "Configuration data for component FIB";

        uses syslog-component-config;
      }

      container state {
        config false;
        description
          "Operational state data for component FIB";

        uses syslog-component-config;
        uses syslog-component-state;
      }
    }
  }

  grouping syslog-component-ifmgr-top {
    container IFMGR {
      description
        "Top-level container for data related to component IFMGR
        logging";

      container config {
        description
          "Configuration data for component IFMGR";

        uses syslog-component-config;
      }

      container state {
        config false;
        description
          "Operational state data for component IFMGR";

        uses syslog-component-config;
        uses syslog-component-state;
      }
    }
  }

  grouping syslog-component-isis-top {
    container ISIS {
      description
        "Top-level container for data related to component ISIS
        logging";

      container config {
        description
          "Configuration data for component ISIS";

        uses syslog-component-config;
      }

      container state {
        config false;
        description
          "Operational state data for component ISIS";

        uses syslog-component-config;
        uses syslog-component-state;
      }
    }
  }

  grouping syslog-component-ldp-top {
    container LDP {
      description
        "Top-level container for data related to component LDP
        logging";
      
      container config {
        description
          "Configuration data for component LDP";

        uses syslog-component-config;
      }

      container state {
        config false;
        description
          "Operational state data for component LDP";

        uses syslog-component-config;
        uses syslog-component-state;
      }
    }
  }

  grouping syslog-component-ospf-top {
    container OSPF {
      description
        "Top-level container for data related to component OSPF
        logging";

      container config {
        description
          "Configuration data for component OSPF";

        uses syslog-component-config;
      }

      container state {
        config false;
        description
          "Operational state data for component OSPF";

        uses syslog-component-config;
        uses syslog-component-state;
      }
    }
  }

  grouping syslog-component-ospf3-top {
    container OSPF3 {
      description
        "Top-level container for data related to component OSPF3
        logging";

      container config {
        description
          "Configuration data for component OSPF3";

        uses syslog-component-config;
      }

      container state {
        config false;
        description
          "Operational state data for component OSPF3";

        uses syslog-component-config;
        uses syslog-component-state;
      }
    }
  }

  grouping syslog-component-pltmgr-top {
    container PLTMGR {
      description
        "Top-level container for data related to component PLTMGR
        logging";

      container config {
        description
          "Configuration data for component PLTMGR";

        uses syslog-component-config;
      }

      container state {
        config false;
        description
          "Operational state data for component PLTMGR";

        uses syslog-component-config;
        uses syslog-component-state;
      }
    }
  }

  grouping syslog-component-rib-top {
    container RIB {
      description
        "Top-level container for data related to component RIB
        logging";

      container config {
        description
          "Configuration data for component RIB";

        uses syslog-component-config;
      }

      container state {
        config false;
        description
          "Operational state data for component RIB";

        uses syslog-component-config;
        uses syslog-component-state;
      }
    }
  }

  grouping syslog-component-eventmgr-top {
    container EVENTMGR {
      description
        "Top-level container for data related to component EVENTMGR
        logging";

      container config {
        description
          "Configuration data for component EVENTMGR";

        uses syslog-component-config;
      }

      container state {
        config false;
        description
          "Operational state data for component EVENTMGR";

        uses syslog-component-config;
        uses syslog-component-state;
      }
    }
  }

  grouping syslog-component-gnmi-top {
    container GNMI {
      description
        "Top-level container for data related to component gNMI Server
        logging";

      container config {
        description
          "Configuration data for component gNMI";

        uses syslog-component-config;
      }

      container state {
        config false;
        description
          "Operational state data for component gNMI";

        uses syslog-component-config;
        uses syslog-component-state;
      }
    }
  }

  grouping syslog-component-sidmgr-top {
    container SIDMGR {
      description
        "Top-level container for data related to component SIDMGR
        logging";

      container config {
        description
          "Configuration data for component SIDMGR";

        uses syslog-component-config;
      }

      container state {
        config false;
        description
          "Operational state data for component SIDMGR";

        uses syslog-component-config;
        uses syslog-component-state;
      }
    }
  }

  grouping syslog-component-top {
    container component {
      description
        "Top-level container for data related to component-based
        logging";

      uses syslog-component-adjmgr-top;
      uses syslog-component-bfd-top;
      uses syslog-component-bgp-top;
      uses syslog-component-dpal-top;
      uses syslog-component-fib-top;
      uses syslog-component-ifmgr-top;
      uses syslog-component-isis-top;
      uses syslog-component-ldp-top;
      uses syslog-component-ospf-top;
      uses syslog-component-ospf3-top;
      uses syslog-component-pltmgr-top;
      uses syslog-component-l2rib-top;
      uses syslog-component-rib-top;
      uses syslog-component-eventmgr-top;
      uses syslog-component-gnmi-top;
      uses syslog-component-sidmgr-top;
    }
  }

  grouping alias-cmd-top {
    list alias {
      key "name";
      description "List of alias commands";

      leaf name {
        type string {
          length "1..64";
        }
        description "Name of alias command";
      }

      leaf command {
        type string {
          length "1..512";
        }
        description "Actual command to be executed";
      }
    }
  }

  grouping bash-alias-top {

    description
      "Top-level grouping for aliases for shell commands";

    container bash-alias {

      container config {
        uses alias-cmd-top;
      }

      container state {
        config false;
        uses alias-cmd-top;
      }
    }
  }

  grouping system-cli-config {
    description
      "Configuration data for system command line
       interface parameters";

    leaf oper-prompt {
      type string;
      default "\\u@\\H\\M# ";
      description
        "Command line prompt used in operational mode";
    }

    leaf config-prompt {
      type string;
      default "\\u@\\H(\\m)# ";
      description
        "Command line prompt used in configuration mode";
    }
    leaf idle-timeout {
      type uint16;
      units minutes;
      default "30";
      description
        "Maximum idle time before terminating a CLI session. Default
         is 30 minutes. 0 means no timeout. Will be silently
         capped to 49 days 17 hours. This configuration parameter takes
         effect only for new sessions.";
    }
  }

  grouping system-cli-top {
    description
      "Top-level grouping for system command line
       interface parameters";

    container cli {
      description
        "Top-level container for command line interface
         parameters";

      container config {
        description
          "Configuration data for system command line
           interface parameters";

        uses system-cli-config;
      }

      container state {
        config false;

        description
          "Operational state data for system command line
           interface parameters";

        uses system-cli-config;
      }
    }
  }

  grouping crontab-entry-top {
    list crontab-entry {
      key "name";
      description "List of crontab entries";

      leaf name {
        type string {
          length "1..64";
        }
        description "Name of crontab entry";
      }

      leaf user {
        type string {
          length "1..16";
        }
        description "Username under which to run this command";
      }

      leaf timespec {
        type string {
          length "1..64";
        }
        description "cron crontab(5) time specification";
      }

      leaf command {
        type string {
          length "1..512";
        }
        description "Actual command to be executed";
      }
    }
  }

  grouping crontab-top {

    description
      "Top-level grouping for crontab entries";

    container crontab {

      container config {
        uses crontab-entry-top;
      }

      container state {
        config false;
        uses crontab-entry-top;
      }
    }
  }

  grouping daemon-config {

    leaf name {
      type string {
        length "1..64";
      }
      description
        "Name of daemon command";
    }

    leaf command {
      type string {
        length "1..512";
      }
      description
        "Actual command to be executed";
    }

    leaf enabled {
      type boolean;
      description
        "Daemon should be running";
    }
  }

  grouping daemon-state {
    leaf pid {
      // POSIX pid_t is signed 32-bit on Linux...this year
      type int32;
      description
        "Daemon process ID, zero if none";
    }
  }

  grouping user-daemon-top {

    description
      "Top-level grouping for user-specified daemons to be run under spyder";

    container user-daemon {

      container config {
        list daemon {
          key "name";
          description
            "List of daemon commands";

          uses daemon-config;
        }
      }

      container state {
        config false;

        list daemon {
          key "name";
          description
            "List of daemon commands";

          uses daemon-config;
          uses daemon-state;
        }
      }
    }
  }

  grouping icmp-cfg-top {
    leaf source-interface {
      type leafref {
        path "/oc-if:interfaces/oc-if:interface/oc-if:config/oc-if:name";
      }
      description "The interface to bind to when sending ICMP error packets.";
    }
  }

  grouping icmp-top {

    description
      "Top-level grouping for ICMP configuration";

    container icmp {

    description "ICMP configuration options";

      container config {
        uses icmp-cfg-top;
      }

      container state {
        config false;
        uses icmp-cfg-top;
      }
    }
  }

  grouping system-ztp-counters {
    leaf attempts {
      type uint32;
      description
        "Number of ZTP attempts.";
    }
  }

  grouping system-ztp-intf-dhcp-counters {
    container counters {
      description
      "Interface ZTP DHCP request counters ";
      leaf dhcpv4-attempts {
        type uint32;
        description
          "DHCP resolution attempts on interface.";
      }
      leaf dhcpv6-attempts {
        type uint32;
        description
          "DHCPv6 resolution attempts on interface.";
      }
    }
  }

  grouping system-ztp-intf-dhcp-resp-state {
    container response {
      description
        "Interface ZTP DHCP response information";
      leaf ipv4-address {
        type string;
        description
          "IPv4 Address assigned by DHCP server";
      }

      leaf dhcpv4-config-url {
        type string;
        description
          "Configuration file URL to be used by ZTP";
      }

      leaf dhcpv4-script-url {
        type string;
          description
          "Script file URL to be used by ZTP";
      }

      leaf ipv6-address {
        type string;
        description
          "IPv6 Address assigned by DHCPv6 server";
      }

      leaf dhcpv6-config-url {
        type string;
        description
          "Configuration file URL to be used by ZTP";
      }

      leaf dhcpv6-script-url {
        type string;
        description
          "Configuration file URL to be used by ZTP";
      }
    }
  }

  grouping system-ztp-intf-state {

    container dhcp {
      description
        "Per interface ZTP DHCP state parameters";
      config false;
      uses system-ztp-intf-dhcp-counters;
      uses system-ztp-intf-dhcp-resp-state;
    }
  }

  grouping system-ztp-state {
    leaf enabled {
      type boolean;
      description
        "ZTP Enabled/Disabled.";
    }

    leaf process-state {
      type string;
      description
        "Current ZTP Process state.";
    }

    leaf remaining-restart-time {
      type uint16;
      units "seconds";
      description
        "Remaining time in seconds before spyder restart.";
    }

    leaf interface {
      type string;
      description
        "Interface name";
    }

    leaf address {
      type string;
      description
        "IPv4/IPv6 Address assigned by DHCP server";
    }

    leaf url {
      type string;
      description
        "Configuration/Script file URL to be used by ZTP";
    }
  }

  grouping system-ztp-interfaces-top {
    container interfaces {
      config false;
      description
        "Interface ZTP DHCP state parameters";
      list interface {
        key "name";
        description
          "List of interfaces on which DHCP requests are being sent";

        leaf name {
          type string;
          description
            "Interface name";
        }

        container state {
          uses system-ztp-intf-state;
        }
      }
    }
  }

  grouping system-ztp-top {
    description
      "Top-level grouping for ZTP state";

    container ztp {
      description
        "ZTP state attributes.";

      container state {
        config false;
        uses system-ztp-state;

        container counters {
          uses system-ztp-counters;
        }
      }
      uses system-ztp-interfaces-top;
    }
  }

  grouping aaa-authentication-session-state {
    description
      "State data for users sessions";

    leaf sno {
      type uint32;
      description
        "S.No. for this user";
    }

    leaf user {
      type string;
      description
        "Username";
    }

    leaf tty {
      type string;
      description
        "TTY for this user";
    }

    leaf from {
      type string;
      description
        "IP address of the user";
    }

    leaf login {
      type string;
      description
        "Login time for this user";
    }

    leaf idle {
      type string;
      description
        "Idle time for this user";
    }
  }

  grouping aaa-authentication-user-sessions-top {
    description
      "Top-level grouping for local users";

    container user-sessions {
      config false;

      description
        "Enclosing container list of local users-sessions";

      list session {
        key "sno";
        description
          "Serial Number";

          uses aaa-authentication-session-state;
      }
    }
  }

  grouping system-snmp-server-common {
    leaf enable {
      type boolean;
      default false;
      description
        "Enables the SNMP server. The SNMP server is disabled by
        default";
    }

    leaf-list protocol-version {
      type enumeration {
        enum V2C {
          description
            "Enable the SNMP agent for protocol version 2c";
        }
        enum V3 {
          description
            "Enable the SNMP agent for protocol version 3";
        }
      }
      default "V2C";
      description
        "A list of SNMP protocol versions that the agent supports";
    }

    leaf network-instance {
      type oc-ni:network-instance-ref;
      description
        "The network instance (VRF) on which the SNMP server should listen.
         All the 'listen-addresses', if configured, must belong to this
         network instance.";
    }

    leaf port {
      type oc-inet:port-number;
      default 161;
      description
        "UDP port on which the SNMP server should listen";
    }

    leaf contact {
      type string;
      description
        "SNMPv2-MIB sysContact";
    }

    leaf location {
      type string;
      description
        "SNMPv2-MIB sysLocation";
    }

    leaf engine-id {
      type union {
        type enumeration {
          enum SYSTEM_MAC_ADDRESS {
            value 3;
            description
              "Derive the SNMPv3 engine-id from the global system
               MAC address";
          }
        }
        type yang:hex-string;
      }
      default "SYSTEM_MAC_ADDRESS";
      description
        "The SNMPv3 engine-id suffix.  This can either be derived by the system
         or specified as a valid hexidecimal string.";
    }
  }

  grouping system-snmp-server-config {
    description
      "Configuration data for the SNMP server";

    uses system-snmp-server-common;

    leaf-list listen-addresses {
      type union {
        type inet:ip-address;
        type enumeration {
          enum ANY {
            description
             "The SNMP master agent should listen on any address
              bound to an interface on the system.";
          }
        }
        type string;
      }
      default "ANY";
      must "(not(../listen-addresses = 'ANY' and count(../listen-addresses) > 1))" {
        error-message "'ANY' and IP addresses are mutually exclusive";
      }
      description
        "The IP addresses that the SNMP master agent should
         listen on. This may be an IPv4 or an IPv6 address or interface name";
    }
  }
  grouping system-snmp-server-state {
    description
      "State data for the SNMP server";

    uses system-snmp-server-common;

    leaf-list listen-addresses {
      type union {
        type inet:ip-address;
        type enumeration {
          enum ANY {
            description
             "The SNMP master agent should listen on any address
              bound to an interface on the system.";
          }
        }
        type string;
      }
      description
        "The IP addresses that the SNMP master agent should
         listen on. This may be an IPv4 or an IPv6 address or interface name";
    }
  }

  grouping system-snmp-server-target-parameters-config {
    description
      "Configuration data for SNMP target parameters";

    leaf name {
      type string;
      description
        "Unique identitifer for a group of SNMP target
         parameters";
    }

    leaf security-model {
      type enumeration {
        enum V2C {
          value 2;
          description
            "Use the SNMPv2c security model";
        }
        enum USM {
          value 3;
          description
            "Use the USM (SNMPv3) security model";
        }
      }
      default "V2C";
      description
        "The security model in use per SNMP-TARGET-MIB";
      reference
        "RFC3413 - Simple Network Management Protocol (SNMP)
         applications";
    }

    leaf security-level {
      when "../security-model = 'USM'";
      type enumeration {
        enum NONE {
          description
            "No authentication or privacy is used (noAuthNoPriv)";
        }
        enum AUTH {
          description
            "Authentication without privacy is used (authNoPriv)";
        }
        enum PRIV {
          description
            "Authentication and privacy is used (authPriv)";
        }
      }
      default "NONE";
      description
        "The security level in use per SNMP-TARGET-MIB";
      reference
        "RFC3413 - Simple Network Management Protocol (SNMP)
         applications";
    }

    leaf security-name {
      when "../security-model = 'USM'";
      type leafref {
        path "../../../../usm/local-engine/users/user/username";
      }
      description
        "Reference to a SNMPv3 USM username";
    }

    leaf message-processing-model {
      when "../security-model = 'USM'";
      type enumeration {
        enum V2C {
          value 1;
          description
            "SNMP v2c message processing model";
        }
        enum V3 {
          value 3;
          description
            "SNMP v3 message processing model";
        }
      }
      default "V2C";
      description
        "The message processing model when generating SNMP
         notifications";
    }
  }

  grouping system-snmp-server-target-parameters-top {
    description
      "Top-level grouping for SNMP target parameters";

    container target-parameters {
      description
        "Enclosing container for SNMP target parameter configuration
         and operational state";

      list target-parameter {
        key "name";
        description
          "List of SNMP target parameters";

        leaf name {
          type leafref {
            path "../config/name";
          }
          description
            "Reference to the name list key";
        }

        container config {
          description
            "Configuration data for SNMP target parameters";

          uses system-snmp-server-target-parameters-config;
        }

        container state {
          config false;
          description
            "Operational state data for SNMP target parameters";

          uses system-snmp-server-target-parameters-config;
        }
      }
    }
  }

  grouping system-snmp-server-target-config {
    description
      "Configuration parameters for the SNMP target destinations";

    leaf name {
      type string;
      description
        "Unique identifier for the SNMP target";
    }

    leaf enable {
      type boolean;
      default true;
      description
        "Enables/disables the SNMP target.  The target is
         enabled by default";
    }

    leaf address {
      type inet:ip-address;
      description
        "IP address of the SNMP target destination";
    }

    leaf port {
      type oc-inet:port-number;
      default 162;
      description
        "Protocol (udp or tcp) port number for the
         SNMP target destination";
    }

    leaf target-parameters {
      type leafref {
        path "../../../../target-parameters/target-parameter/name";
      }
      description
        "Target parameters associated with the SNMP target
         destination";
    }

  }

  grouping system-snmp-server-target-top {
    description
      "Top-level grouping for SNMP server target data";

    container targets {
      description
        "Enclosing container for SNMP target configuration and
         operational state";

      list target {
        key "name";
        description
          "List of SNMP targets";

        leaf name {
          type leafref {
            path "../config/name";
          }
          description
            "Reference to the name list key";
        }

        container config {
          description
            "Top-level config container for SNMP targets";

          uses system-snmp-server-target-config;
        }

        container state {
          config false;
          description
            "Top-level operational state container for SNMP
             targets";

          uses system-snmp-server-target-config;
        }
      }
    }
  }

  grouping system-snmp-server-communities-config {
    description
      "Configuration data for SNMP communities";

    leaf name {
      type string;
      description
        "A SNMP community name as defined in RFC1157";
    }
  }

  grouping system-snmp-server-communities-top {
    description
      "Top-level grouping for SNMP server communities data";

    container communities {
      list community {
        key "name";
        description
          "List of SNMP community names";

        leaf name {
          type leafref {
            path "../config/name";
          }
          description
            "Reference to the SNMP community name list key";
        }

        container config {
          description
            "Configuration data for SNMP communities";

          uses system-snmp-server-communities-config;
        }

        container state {
          config false;

          description
            "Operational state data for SNMP communities";

          uses system-snmp-server-communities-config;
        }
      }
    }
  }

  grouping system-snmp-server-usm-authentication-config {
    description
      "Top-level grouping for SNMP server USM authentication
       configuration";

    leaf protocol {
      type identityref {
        base arc-sys-types:SNMP_AUTH_TYPE;
      }
      default arc-sys-types:SNMP_AUTH_NONE;
      description
        "The protocol/hash algorithm for USM authentication";

      must "derived-from-or-self(current(), 'arc-sys-types:SNMP_AUTH_NONE') or " +
           "(not(derived-from-or-self(current(), 'arc-sys-types:SNMP_AUTH_NONE')) and " +
           "boolean(../key))" {
        error-message
          "An authentication key must be configured when a authentication " +
          "protocol is specified";
      }
    }

    leaf key {
      when "../protocol != 'arc-sys-types:SNMP_AUTH_NONE'";
      type union {
        type yang:hex-string;
        type arc-sys-types:encrypted-string;
      }
      description
        "An authentication passphrase supplied as clear-text or a
         pre-computed authentication key hash";
    }
  }

  grouping system-snmp-server-usm-authentication-top {
    description
      "Top-level grouping for SNMP server USM authentication
       data";

    container authentication {
      description
        "Top-level container for SNMP server USM authentication";

      container config {
        description
          "Configuration data for SNMP USM authentication";

        uses system-snmp-server-usm-authentication-config;
      }

      container state {
        config false;

        description
          "Operational state data for SNMP USM authentication";

        uses system-snmp-server-usm-authentication-config;
      }
    }
  }

  grouping system-snmp-server-usm-privacy-config {
    description
      "Top-level grouping for SNMP server USM privacy
       configuration";

    leaf protocol {
      type identityref {
        base arc-sys-types:SNMP_PRIV_TYPE;
      }
      default arc-sys-types:SNMP_PRIV_NONE;
      description
        "The protocol/cipher for USM privacy";

      must "derived-from-or-self(current(), 'arc-sys-types:SNMP_PRIV_NONE') or " +
           "(not(derived-from-or-self(current(), 'arc-sys-types:SNMP_PRIV_NONE')) and " +
           "boolean(../key))" {
        error-message
          "A privacy key must be configured when a privacy protocol is " +
          "specified";
      }
      must "derived-from-or-self(current(), 'arc-sys-types:SNMP_PRIV_NONE') or " +
           "(not(derived-from-or-self(current(), 'arc-sys-types:SNMP_PRIV_NONE')) and " +
           "../../../authentication/config/protocol != 'arc-sys-types:SNMP_AUTH_NONE')" {
        error-message
          "An authentication protocol must be configured when a privacy " +
          "protocol is used";
      }
    }

    leaf key {
      when "../protocol != 'arc-sys-types:SNMP_PRIV_NONE'";
      type union {
        type yang:hex-string;
        type arc-sys-types:encrypted-string;
      }
      description
        "A privacy passphrase supplied as clear-text or a
         pre-computed privacy key hash";
    }
  }

  grouping system-snmp-server-usm-privacy-top {
    description
      "Top-level grouping for SNMP server USM privacy data";

    container privacy {
      description
        "Top-level container for SNMP server USM privacy";

      container config {
        description
          "Configuration data for SNMP USM privacy";

        uses system-snmp-server-usm-privacy-config;
      }

      container state {
        config false;

        description
          "Operational state data for SNMP USM privacy";

        uses system-snmp-server-usm-privacy-config;
      }
    }
  }

  grouping system-snmp-server-usm-user-config {
    description
      "Top-level grouping for SNMP server USM user configuration";

    leaf username {
      type string;
      description
        "SNMPv3 User-based Security Model username";
    }
  }

  grouping system-snmp-server-usm-top {
    description
      "Top-level grouping for SNMP server User-based Security Model
       data";

    container usm {
      description
        "Enclosing container for defining SNMP server User-based
         Security Model parameters";

      container local-engine {
        description
          "Enclosing container for defining USM parameters
           pertaining to the local-engine";

        container users {
          description
            "Enclosing container list of SNMP USM users";

          list user {
            key "username";

            leaf username {
              type leafref {
                path "../config/username";
              }
              description
                "References the configured username for the user";
            }

            container config {
              description
                "Configuration data for SNMP User-based Security Model
                 users";

              uses system-snmp-server-usm-user-config;
            }

            container state {
              config false;

              description
                "Operational state data for SNMP User-based Security
                 Model users";

              uses system-snmp-server-usm-user-config;
            }

            uses system-snmp-server-usm-authentication-top;
            uses system-snmp-server-usm-privacy-top;
          }
        }
      }
    }
  }

  grouping snmp-agent-state {
    description
      "Grouping for SNMP agent state";

    leaf active {
      type boolean;
      default false;
      description
        "Actual state of SNMP agent";
    }
  }

  grouping system-snmp-server-top {
    description
      "Top-level grouping for system SNMP server data";

    container snmp-server {
      description
        "Top-level container for the SNMP server";

      container config {
        description
          "Configuration data for the system SNMP server";

        uses system-snmp-server-config;
      }

      container state {
        config false;

        description
          "Operational state data for the system SNMP server";

        uses system-snmp-server-state;
        uses snmp-agent-state;
      }

      uses system-snmp-server-communities-top;
      uses system-snmp-server-target-top;
      uses system-snmp-server-target-parameters-top;
      uses system-snmp-server-usm-top;
    }
  }

  grouping system-restconf-server-common {
    description
      "Configuration data for system RESTCONF configuration";

    leaf enable {
      type boolean;
      default false;
      description
        "Enables the RESTCONF server.  The RESTCONF server
         is disabled by default.";
    }

    leaf port {
      type oc-inet:port-number;
      default 8009;
      description
        "TCP port on which the RESTCONF server should listen";
    }

    leaf transport-security {
      type boolean;
      default true;
      description
        "Enables RESTCONF transport security (TLS/SSL).
         Transport-security is enabled by default.";
    }
  }

  grouping system-restconf-server-config {

    uses system-restconf-server-common;

    leaf-list listen-addresses {
      type union {
        type inet:ip-address;
        type enumeration {
          enum ANY {
            description
              "The RESTCONF server should listen on any address
               bound to an interface on the system.";
          }
        }
      }
      default "ANY";
      must "(not(../listen-addresses = 'ANY' and count(../listen-addresses) > 1))" {
        error-message "'ANY' and IP addresses are mutually exclusive";
      }
      description
        "The IP addresses that the RESTCONF server should listen
         on.  This may be an IPv4, IPv6 address or 'ANY'";
    }

  }

  grouping system-restconf-server-state {

    uses system-restconf-server-common;

    leaf-list listen-addresses {
      type union {
        type inet:ip-address;
        type enumeration {
          enum ANY {
            description
              "The RESTCONF server should listen on any address
               bound to an interface on the system.";
          }
        }
      }
      default "ANY";
      description
        "The IP addresses that the RESTCONF server should listen
         on.  This may be an IPv4, IPv6 address or 'ANY'";
    }

  }

  grouping system-restconf-server-top {
    description
      "Top-level grouping for RESTCONF server data";

    container restconf-server {
      description
        "Top-level container for RESTCONF server";

      container config {
        uses system-restconf-server-config;
      }

      container state {
        config false;
        uses system-restconf-server-state;
      }

      uses arc-sys-mgmt:system-tls-top;
    }
  }

  grouping system-netconf-server-transport-common-config {
    description
      "Common configuration data for NETCONF transports";

    leaf enable {
      type boolean;
      default false;
      description
        "Enables the NETCONF server per transport.  The
         NETCONF server is disabled by default across all
         supported transports.";
    }

    leaf port {
      type oc-inet:port-number;
      description
        "TCP port on which the NETCONF server should listen.
         The default for SSHv2 transport is 830 while the
         default for TLS transport is 6513.";
    }

    leaf timeout {
      type uint16;
      units seconds;
      default 0;
      description
        "Sets the idle timeout in seconds on terminal connections
         to the system for the NETCONF protocol.  The default value
         is 0 which indicates no idle timeout";
    }
  }

  grouping system-netconf-server-transport-config {
    description
      "Configuration data for NETCONF transport protocols";

    container transport {
      description
        "Top-level container for NETCONF transport protocols";

      container ssh {
        description
          "Top-level container for NETCONF over SSHv2 data";

        container config {
          description
            "Configuration data for NETCONF over SSHv2";

          uses system-netconf-server-transport-common-config {
            refine port {
              default 830;
            }
          }
        }
        container state {
          config false;

          description
            "Operational state data for NETCONF over SSHv2";

          uses system-netconf-server-transport-common-config {
            refine port {
              default 830;
            }
          }
        }
      }
    }
  }

  grouping system-netconf-server-config {
    description
      "Configuration data for the NETCONF server";

    leaf enable {
      type boolean;
      default false;
      description
        "Enables the NETCONF server. The NETCONF server is disabled by
         default.";
    }
  }

  grouping system-netconf-server-top {
    description
      "Top-level grouping for system NETCONF server data";

    container netconf-server {
      description
        "Top-level container for the NETCONF server";

      container config {
        description
          "Configuration data for the system NETCONF server";

        uses system-netconf-server-config;
      }

      container state {
        config false;

        description
          "Operational state data for the system NETCONF server";

        uses system-netconf-server-config;
      }

      uses system-netconf-server-transport-config;
    }
  }

  grouping system-ssh-server-sftp-config {
    description
      "Configuration data for the SFTP server";

    leaf enable {
      type boolean;
      default false;
      description
        "Enables the SFTP server.  The SFTP server is disabled by
         default.";
    }
  }

  grouping system-ssh-server-sftp-top {
    description
      "Top-level grouping for system SFTP server data";

    container sftp {
      description
        "Top-level container for the SFTP server";

      container config {
        description
          "Configuration data for the system SFTP server";

        uses system-ssh-server-sftp-config;
      }

      container state {
        config false;

        description
          "Operational state data for the system SFTP server";

        uses system-ssh-server-sftp-config;
      }
    }
  }

  grouping system-ssh-server-common {
    description
      "Configuration data for system ssh configuration";

    leaf-list ciphers {
      ordered-by user;
      type arc-sys-types:ssh-cipher-suite;
      default "CHACHA20_POLY1305@OPENSSH.COM";
      default "AES128_CTR";
      default "AES192_CTR";
      default "AES256_CTR";
      default "AES128_GCM@OPENSSH.COM";
      default "AES256_GCM@OPENSSH.COM";
      description
        "Set the list of cipher suites allowed";
    }

    leaf-list macs {
      ordered-by user;
      type arc-sys-types:ssh-mac-suite;
      default "UMAC_64_ETM@OPENSSH.COM";
      default "UMAC_128_ETM@OPENSSH.COM";
      default "HMAC_SHA2_256_ETM@OPENSSH.COM";
      default "HMAC_SHA2_512_ETM@OPENSSH.COM";
      default "HMAC_SHA1_ETM@OPENSSH.COM";
      default "UMAC_64@OPENSSH.COM";
      default "UMAC_128@OPENSSH.COM";
      default "HMAC_SHA2_256";
      default "HMAC_SHA2_512";
      default "HMAC_SHA1";
      description
        "Specifies the available MAC (message authentication code)
        algorithms";
    }

    leaf max-auth-tries {
      type uint16;
      default 6;
      description
        "Limit on the number of authentication attempts per connection.";
    }

    leaf permit-root-login {
      type boolean;
      default false;
      description
        "Allow root user to login via SSH";
    }

    leaf network-instance {
      type oc-ni:network-instance-ref;
      description
        "The network instance (VRF) to use for listening to incoming SSH
         connections. All the 'listen-addresses', if configured, must belong
         to this network instance.";
    }

    leaf login-timeout {
      type uint32;
      units seconds;
      default 120;
      description
        "Login timeout for unauthenticated sessions";
    }

    leaf port {
      type oc-inet:port-number;
      default 22;
      description
        "TCP port on which the SSH server should listen";
    }

    leaf pubkey-authentication {
      type boolean;
      default true;
      description
        "Allow public key authentication for SSH";
    }
  }

  grouping system-ssh-server-config {

    uses system-ssh-server-common;

    leaf-list listen-addresses {
      type union {
        type inet:ip-address;
        type enumeration {
          enum ANY {
            description
              "The SSH daemon should listen on any address
               bound to an interface on the system.";
          }
        }
      }
      default "ANY";
      must "(not(../listen-addresses = 'ANY' and count(../listen-addresses) > 1))" {
        error-message "'ANY' and IP addresses are mutually exclusive";
      }
      description
        "The IP addresses that the SSH server should listen
         on.  This may be an IPv4, IPv6 address or 'ANY'";
    }
  }

  grouping system-ssh-server-state {

    uses system-ssh-server-common;

    leaf-list listen-addresses {
      type union {
        type inet:ip-address;
        type enumeration {
          enum ANY {
            description
              "The SSH daemon should listen on any address
               bound to an interface on the system.";
          }
        }
      }
      default "ANY";

      description
        "The IP addresses that the SSH server should listen
         on.  This may be an IPv4, IPv6 address or 'ANY'";
    }
  }

  grouping system-console-port-config {

    leaf permit-root-login {
      type boolean;
      default true;
      description
        "Allow root user to login via console port";
    }

    leaf permit-non-root-login {
      type boolean;
      default true;
      description
        "Allow all non-root users to login via console port";
    }

    leaf baud-rate {
      type enumeration {
        enum 1200 {
          value 1200;
        }
        enum 2400 {
          value 2400;
        }
        enum 4800 {
          value 4800;
        }
        enum 9600 {
          value 9600;
        }
        enum 19200 {
          value 19200;
        }
        enum 38400 {
          value 38400;
        }
        enum 57600 {
          value 57600;
        }
        enum 115200 {
          value 115200;
        }
      }
      default 115200;
      units bps;
      description
        "Set baud rate";
    }
    leaf idle-timeout {
      type uint64;
      default 300;
      units seconds;
      description
        "Set console idle-timeout in Seconds";
    }
  }

  grouping system-console-port-top {

    container console-port {
      description
        "Top-level grouping for console port parameters";

      container config {
        uses system-console-port-config;
      }

      container state {
        config false;
        uses system-console-port-config;
      }
    }
  }

  grouping system-ports-top {

    container ports {
      description
        "Top-level grouping for different types of ports";

      uses system-console-port-top;
    }
  }

  grouping system-aaa-admin-user-config {
    leaf ssh-key {
      type string;
      description
        "SSH public key for the admin (root) user";
    }
  }

   grouping system-maintenance-mode-state {
     leaf maintenance-mode-state {
       type identityref {
         base arc-sys-types:MM_STATE;
       }
       description
         "Current maintenance mode state";
     }

     leaf last-state-change-time {
       type yang:date-and-time;
       description
         "Indicates the last time the maintenance mode state was updated.";
     }
  }

  grouping system-maintenance-mode-stats {
    description
      "Client specific counters";

    uses system-maintenance-mode-state ;

    leaf enable-requests-sent {
      type yang:counter32;
      description
        "Number of reqs to enable maintenance-mode sent";
    }

    leaf disable-requests-sent {
      type yang:counter32;
      description
        "Number of reqs to disable maintenance-mode sent";
    }

    leaf registration-requests-received {
      type yang:counter32;
      description
        "Number of registration requests received";
   }

    leaf deregistration-requests-received {
      type yang:counter32;
      description
        "Number of deregistration requests received";
    }

    leaf start-profiling-sent {
      type yang:counter32;
      description
        "Number of maintenance-mode acknowledgement messages sent";
    }

    leaf enable-acks-received {
      type yang:counter32;
      description
        "Number of start maintenance-mode acknowledgement messages received";
    }

   leaf disable-acks-received {
      type yang:counter32;
      description
        "Number of maintenance-mode stop acknowledgement messages received";
    }
    leaf completed-received {
      type yang:counter32;
      description
        "Number of maintenance-mode completed messages received";
    }

    leaf failed-received {
      type yang:counter32;
      description
        "Number of maintenance-mode failed messages received";
    }
  }

  grouping system-maintenance-mode-heuristics {
    leaf target-traffic-absolute {
      type uint16;
         default 10;
         description
           "Avg Traffic (in KBps) per interface below which to declare maintenance-mode is effectively active";
     }
     leaf target-traffic-percentage {
       type uint8;
       default 10;
       description
         "Per interface percentage average traffic below which to declare maintenance-mode is effectively active";
     }
  }
  grouping system-maintenance-mode-config {
    description
      "grouping for SYSMGR MM config";

      leaf activation-timer {
        type uint32;
        default 300;
        description
          "activation timer value in seconds";
      }
      uses system-maintenance-mode-heuristics;
      leaf enable {
        type boolean;
              default false;
        description
          "maintenance mode config";
      }
      leaf activation-mode {
         when "../enable = 'true'" {
           description
             "Set activation mode only when enable is true";
         }
         type identityref {
            base arc-sys-types:MM_ACTIVATION_MODE;
         }
         description
            "mode used to activate MM";
      }
  }

  grouping system-maintenance-mode-client-state {
    leaf name {
      type string;
        description
          "Name of SYSMGR client";
    }
    uses system-maintenance-mode-stats;
  }
  grouping system-maintenance-mode-client-top {
    container clients {
      config false;
      list client {
        key "name";
        description
          "The list of SYSMGR clients.";

        leaf name {
          type leafref {
            path "../state/name";
          }
          description
            "Name of SYSMGR client";
        }
        container state {
          uses system-maintenance-mode-client-state;
        }
      }
   }
 }
  grouping system-maintenance-mode-top {
    container maintenance-mode {
      description
        "Sysmgr related config";
      container config {
        uses system-maintenance-mode-config;
      }
      container state {
        config false;
        uses system-maintenance-mode-config;
        uses system-maintenance-mode-state;
      }
      uses system-maintenance-mode-client-top;
    }
 }

   grouping system-stateful-restart-state {
     leaf stateful-restart-state {
       type string;
       description
         "Current stateful-restart state";
     }
     leaf last-stateful-restart-state {
       type string;
       description
         "Last restart state";
     }
     leaf last-stateful-restart-time {
        type yang:date-and-time;
        description
          "Indicates the last time the stateful restart was executed.";
     }
     leaf last-stateful-restart-duration {
       type uint32;
       description
         "Total time in seconds for the stateful restart to complete";
     }
     leaf num-stateful-restart-requests {
       type uint32;
       description
         "Total number of stateful restarts requested";
     }
     leaf num-stateful-restart-pre-abort-fails {
       type uint32;
       description
         "Total number of stateful restarts failed prior to warmboot";
     }
     leaf num-stateful-restart-post-abort-fails {
       type uint32;
       description
         "Total number of stateful restarts failed post warmboot";
     }
     leaf remaining-client-wait-time {
      type uint16;
      units "seconds";
      description
        "Remaining wait time for all clients to respond.";
     }
     leaf last-start-type {
       type last-start-type;
       description
         "Type of last ArcOS startup";
     }
  }

  grouping system-stateful-restart-client-state {
    leaf name {
      type string;
        description
          "Name of SYSMGR client";
    }

    leaf stateful-restart-client-state {
      type string;
        description
          "Stateful Restart state of SYSMGR client";
    }
    leaf pre-restart-error {
        type boolean;
        description
          "Client Errored Pre Restart";
    }
    leaf post-restart-error {
        type boolean;
        description
          "Client Errored Post Restart";
    }
  }

  grouping system-stateful-restart-client-top {
    container clients {
      config false;
      list client {
        key "name";
        description
          "The list of SYSMGR clients.";

        leaf name {
          type leafref {
            path "../state/name";
          }
          description
            "Name of SYSMGR client";
        }
        container state {
          uses system-stateful-restart-client-state;
        }
      }
    }
  }

  grouping system-stateful-restart-top {
    container stateful-restart {
      description
        "Stateful-Restart Information";
      container state {
        config false;
        uses system-stateful-restart-state;
      }
      uses system-stateful-restart-client-top;
    }
  }

  grouping rib-config {
    description
      "Configuration parameters relating to RIB
       for a particular address family.";
    leaf address-family {
      type identityref {
        base oc-types:ADDRESS_FAMILY;
      }
      description
        "The address family of entries that are described by the
          RIB.";
    }
    leaf rnh-resolution-via-aggregate-route {
      type boolean;
      description
        "Per AFI control to allow or disallow rnh resolution via
         aggregate routes.";
    }
    leaf rnh-resolution-via-default-route {
      type boolean;
      description
        "Per AFI control to allow or disallow rnh resolution via
         default routes.";
    }
  }

  grouping rib-top {
    description
        "System-wide RIB parameters.";
    list rib {
      // min-elements 2; minimum (mandatory node) cannot be set on augments.
      key "address-family";
      description
        "An individual routing table associated with a
          an address family.";
      leaf address-family {
        type leafref {
          path "../config/address-family";
        }
        description
          "Reference to the address family with which the RIB is
            associated";
      }
      container config {
        uses rib-config;
      }
      container state {
        config false;
        uses rib-config;
      }
    }
  }

 grouping system-interface-global-config {
   leaf load-interval {
     type uint16 {
       range 5..300;
     }
     default 30;
     description
       "Global interface counter load-interval in seconds";
   }
 }

 grouping system-interface-global-top {
   container interface-global {
     description
       "Global interface parameters";

     container config {
       uses system-interface-global-config;
     }

     container state {
       config false;
       uses system-interface-global-config;
     }
   }
 }

  grouping tech-support-debug-top {
    description
      "Top-level grouping for tech-support debugs";

    container tech-support {
      config false;
      uses arc-bgp-dbg:bgp-show-debug-top;
    }
  }

  grouping software-upgrade-info-state {
    description
      "Top-level grouping for software upgrade info state
       data nodes";

    leaf package {
      type string {
        length "1..31";
      }
      description
        "Package name";
    }

    leaf running-version {
      type string {
        length "1..31";
      }
      description
        "Package current version";
    }

    leaf upgrade-version {
      type string {
        length "1..31";
      }
      description
        "Package upgrade version";
    }
  }

  grouping software-upgrade-info-top {
    container software {
      config false;
      description
        "Software";

      container upgrade {
        config false;
        description
          "Upgrade Software";

        container info {
        config false;
        description
          "Upgrade Software information";

          list upgrade-bundle-tag {
            key "tag";
              leaf tag {
                type string {
                length "1..128";
                }
              }

              list package-versions {
                key "package";
                description
                  "Package information";

                uses software-upgrade-info-state;

              }
            description "tag-value";
          }
        }
      }
    }
  }

  augment "/oc-sys:system/oc-sys:ntp/oc-sys:config" {
     uses ntp-top;
  }

  augment "/oc-sys:system/oc-sys:ntp/oc-sys:state" {
     uses ntp-top;
  }

  augment "/oc-sys:system/oc-sys:ntp/oc-sys:servers/oc-sys:server/oc-sys:config" {
     uses ntp-server-key;
  }

  augment "/oc-sys:system/oc-sys:ntp/oc-sys:servers/oc-sys:server/oc-sys:state" {
     uses ntp-server-key;
  }

  augment "/oc-sys:system/oc-sys:ntp" {
    list status {
      config false;

      key address;
      leaf address {
        type oc-inet:host;
        description
          "The address or hostname of the NTP server.";
      }
      uses oc-sys:system-ntp-server-state;
      uses ntp-server-state;
    }
  }

  augment "/oc-sys:system/oc-sys:logging" {
    uses arc-sys-mgmt:audit-log-top;
  }

  augment "/oc-sys:system/oc-sys:logging/oc-sys:remote-servers" +
          "/oc-sys:remote-server/oc-sys:config" {
     uses logging-remote-config;
  }

  augment "/oc-sys:system/oc-sys:logging/oc-sys:remote-servers" +
          "/oc-sys:remote-server/oc-sys:state" {
     uses logging-remote-config;
  }

  augment "/oc-sys:system/oc-sys:logging" {
    container config {
      description
        "Configuration data for system logging";

      uses system-logging-config;
    }

    container state {
      config false;

      description
        "Operational state data for system logging";

      uses system-logging-config;
    }

    uses syslog-monitor-top;
    uses syslog-component-top;
    uses syslog-filter-top;
  }

  augment "/oc-sys:system" {
     uses bash-alias-top;
     uses system-ports-top;
     uses crontab-top;
     uses icmp-top {
      when "/arc-features:features/arc-features:feature[arc-features:name='arc-features:ARCOS_ICMP_SRC_REWRITE']" +
           "/arc-features:supported = 'true'";
      }
     uses user-daemon-top;
     uses system-cli-top;
     uses rib-top;
     uses system-interface-global-top;
     uses system-maintenance-mode-top;
     uses system-netconf-server-top;
     uses system-restconf-server-top;
     uses system-stateful-restart-top;
     uses system-snmp-server-top;
     uses arc-version:version-top;
     uses system-ztp-top;
     uses tech-support-debug-top;
     uses software-upgrade-info-top {
       when "(/arc-platform:platform/arc-platform:deployment-type = 'arc-platform:DISTRIBUTED')";
     }
  }

  augment "/oc-sys:system/oc-sys:state" {
    leaf uptime {
      type string;
      description
        "System Uptime value";
    }
  }

  augment "/oc-sys:system/oc-sys:aaa/oc-sys:authentication" {
     uses aaa-authentication-user-sessions-top;
  }

  augment "/oc-sys:system/oc-sys:ssh-server/oc-sys:config" {
     uses system-ssh-server-config;
  }

  augment "/oc-sys:system/oc-sys:ssh-server/oc-sys:state" {
     uses system-ssh-server-state;
  }

  augment "/oc-sys:system/oc-sys:ssh-server" {
    uses system-ssh-server-sftp-top;
  }

  augment "/oc-sys:system/oc-sys:aaa/oc-sys:authentication/oc-sys:admin-user" +
          "/oc-sys:config" {
    uses system-aaa-admin-user-config;
  }

  augment "/oc-sys:system/oc-sys:aaa/oc-sys:authentication/oc-sys:admin-user" +
          "/oc-sys:state" {
    uses system-aaa-admin-user-config;
  }

  augment "/oc-sys:system/oc-sys:aaa/oc-sys:server-groups" +
          "/oc-sys:server-group/oc-sys:config" {
    uses source-top;
  }

  augment "/oc-sys:system/oc-sys:aaa/oc-sys:server-groups" +
          "/oc-sys:server-group/oc-sys:state" {
    uses source-top;
  }

  augment "/oc-sys:system/oc-sys:aaa/oc-sys:server-groups" {
    uses aaa-server-group-state;
  }

  augment "/oc-sys:system/oc-sys:grpc-server" {
    uses arc-sys-mgmt:system-tls-top;
  }

  augment "/oc-sys:system/oc-sys:grpc-server" {
    uses arc-sys-mgmt:system-clients-top ;
  }

  augment "/oc-sys:system/oc-sys:grpc-server" {
    container summary {
      leaf bgp {
         type boolean;
         default false;
         description "enable BGP grpc";
      }
      leaf dpal {
         type boolean;
         default false;
         description "enable DPAL grpc";
      }
      leaf isis {
         type boolean;
         default false;
         description "enable ISIS grpc";
      }
      leaf pltfmgr {
         type boolean;
         default false;
         description "enable PLTMGR grpc";
      }
    }
  }

  augment "/oc-sys:system/oc-sys:grpc-server/oc-sys:config" {
    leaf listen-interface {
      type leafref {
        path "/oc-if:interfaces/oc-if:interface/oc-if:config/oc-if:name";
      }
      description "Use IP address of this interface as source address";
    }
    leaf network-instance {
      type oc-ni:network-instance-ref;
      description
        "The network instance (VRF) to use for connecting to gRPC server";
    }
  }

  augment "/oc-sys:system/oc-sys:grpc-server/oc-sys:state" {
    leaf listen-interface {
      type leafref {
        path "/oc-if:interfaces/oc-if:interface/oc-if:config/oc-if:name";
      }
      description "IP address of this interface is used as source address";
    }
    leaf network-instance {
      type oc-ni:network-instance-ref;
      description
        "The network instance (VRF) used for connecting to gRPC server";
    }
  }

  grouping system-aaa-radius-server-config {
    leaf dead-time {
      type uint16 {
        range 1..600;
      }
      default 5;
      units minutes;
      description
        "Amount of time in minutes to wait before trying an
         unresponsive server again";
    }
  }

  grouping system-aaa-radius-server-state {
    leaf oper-status {
      type enumeration {
        enum UP {
          description
            "RADIUS server is reachable and responsive";
        }
        enum DOWN {
          description
            "RADIUS server is not reachable or is non-responsive";
        }
      }
    }
  }

  typedef last-start-type {
    type enumeration {
      enum "NORMAL_START" {
        value 1;
      }
      enum "PENDING_HITLESS_RESTART" {
        value 2;
      }
      enum "FAILED_HITLESS_RESTART" {
        value 3;
      }
      enum "SUCCESSFUL_HITLESS_RESTART" {
        value 4;
      }
    }
  }

  augment "/oc-sys:system/oc-sys:aaa/oc-sys:server-groups" +
          "/oc-sys:server-group/oc-sys:servers/oc-sys:server" +
          "/oc-sys:radius/oc-sys:config" {
    uses system-aaa-radius-server-config;
  }

  augment "/oc-sys:system/oc-sys:aaa/oc-sys:server-groups" +
          "/oc-sys:server-group/oc-sys:servers/oc-sys:server" +
          "/oc-sys:radius/oc-sys:state" {
    uses system-aaa-radius-server-config;
    uses system-aaa-radius-server-state;
  }
}
