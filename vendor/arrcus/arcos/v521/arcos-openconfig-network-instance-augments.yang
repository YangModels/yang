module arcos-openconfig-network-instance-augments {
  yang-version 1.1;
  namespace "http://yang.arrcus.com/arcos/openconfig/network-instance/augments";
  prefix arc-oc-netinst-aug;

  import openconfig-network-instance {
    prefix oc-netinst;
  }

  import openconfig-interfaces {
    prefix oc-if;
  }

  import openconfig-aft {
    prefix oc-aft;
  }

  import openconfig-aft-types {
    prefix oc-aftt;
  }

  import arcos-aft-types {
    prefix arc-aft-types;
  }

  import ietf-inet-types {
    prefix inet;
  }

  import arcos-mpls-ldp {
    prefix arc-mpls-ldp;
  }

  organization
    "Arrcus, Inc.";

  contact
    "Arrcus, Inc.
     2077 Gateway Place
     Suite 400
     San Jose, CA 95110

     E-mail: yang-support@arrcus.com";

  description
    "This module contains definitions for the
      ArcOS Network instance augments.

     Copyright (c) 2016-2022 by Arrcus, Inc.
     All rights reserved.";

  revision 2023-03-29 {
    description "Add l2ni config for mac-limit, pkt-action";
  }
  
    grouping ip-tunnel-state {
    description
      "Operational state parameters for IP tunnels";
    list tunnels {
      key tunnel-id;
      description
        "List of IP tunnels";

      leaf tunnel-id {
        type uint32;
        description
          "Tunnel identifier";
      }

      container state {
        leaf tunnel-type {
          type oc-aftt:encapsulation-header-type;
          description
            "Type of IP tunnel";
        }

        leaf src-ip-address {
          type inet:ip-address;
          description
            "Source IP address of tunnel";
        }

        leaf dst-ip-address {
          type inet:ip-address;
          description
            "Destination IP address of tunnel";
        }

        leaf-list sid-list {
          type inet:ipv6-address-no-zone;
          description
            "The list of SIDs added to SRv6 tunnel header";
        }

        leaf-list hw-id-list {
          type uint32;
          description
            "The list of ASIC specific IDs";
        }

        leaf ing-ucast-packets {
          type uint64;
          description
            "Destination ingress packets of ucast";
        }

        leaf ing-mcast-packets {
          type uint64;
          description
            "Destination ingress packets of mcast";
        }

        leaf ing-bcast-packets {
          type uint64;
          description
            "Destination ingress packets of bcast";
        }

        leaf egr-ucast-packets {
          type uint64;
          description
            "Destination egress packets of ucast";
        }

        leaf egr-mcast-packets {
          type uint64;
          description
            "Destination egress packets of mcast";
        }

        leaf egr-bcast-packets {
          type uint64;
          description
            "Destination egress packets of bcast";
        }

        leaf ing-ucast-bytes {
          type uint64;
          description
            "Destination ingress bytes of ucast";
        }

        leaf ing-mcast-bytes {
          type uint64;
          description
            "Destination ingress bytes of mcast";
        }

        leaf ing-bcast-bytes {
          type uint64;
          description
            "Destination ingress bytes of bcast";
        }

        leaf egr-ucast-bytes {
          type uint64;
          description
            "Destination egress bytes of ucast";
        }

        leaf egr-mcast-bytes {
          type uint64;
          description
            "Destination egress bytes of mcast";
        }

        leaf egr-bcast-bytes {
          type uint64;
          description
            "Destination egress bytes of bcast";
        }
      }

      uses oc-aft:aft-common-nhop-structural;
    }
  }

  grouping ip-tunnel-state-units {
    description
      "Per forwarding unit view of ip tunnels";

    container ip-tunnels-units {
      config false;
      description
        "Per forwarding unit view of ip tunnels";

      list ip-tunnel-unit-entry {
        key "unit-id";
        description
          "List of forwarding units";

        leaf unit-id {
          type uint32;
          description
            "Uniquely identifies a forwarding unit";
        }

        uses ip-tunnel-state;
      }
    }
  }

  grouping l2ni-mac-table-state-top {
    description
      "Top-level grouping for MAC table state list";


    container mac-table-state {
      config false;

      description
        "Table of learned or statically configured MAC addresses and
        corresponding VLANs in the bridge domain";

      container entries {
        description
          "Enclosing container for list of MAC table entries";

        list entry {
          key "mac-address";
          description
            "List of learned MAC addresses";

          leaf mac-address {
            type leafref {
              path "../state/mac-address";
            }
            description
              "Reference to mac-address list key";
          }

          container state {


            description
              "Operational state data for MAC table entries";

            uses oc-netinst:l2ni-mac-table-config;
            uses oc-netinst:l2ni-mac-table-state;
            leaf nexthop-ecmp-id {
              type uint32;
              description 
                "Ecmp id of the nexthop";
            }
            leaf nexthop-tunnel-id {
              type leafref {
                path "/oc-netinst:network-instances/oc-netinst:network-instance/" +
                     "arc-oc-netinst-aug:ip-tunnels/arc-oc-netinst-aug:tunnels/" +
                     "arc-oc-netinst-aug:tunnel-id";
                }
              description
                "ID of tunnel that nexthop recurses over";
             }
          }
          container interface {
            description
              "Reference to the base and/or subinterface for the
              MAC table entry";

            uses oc-if:interface-ref;
          }
        }
      }
    }
  }

  grouping fdb-units-top {
    description
      "Top-level grouping for MAC table state list per unit";


    container fdb-units {
      config false;

      description
        "Table of learned or statically configured MAC addresses and
        corresponding VLANs in the bridge domain per asic unit";

      list fdb-unit-entry {
        key "unit-id";
        description
          "List of learned MAC addresses";

        leaf unit-id {
          type uint32;
          description
            "Device unit number";
        }
        uses l2ni-mac-table-state-top;
      }
    }
  }
  identity MAC_LIMIT_PACKET_ACTION_TYPE {
    description "Base identity for Mac limit packet action type.";
  }

  identity FLOOD_ACTION {
    base MAC_LIMIT_PACKET_ACTION_TYPE;
    description "Flood unknown Destination Mac packets.";
  }

  identity DROP_ACTION {
    base MAC_LIMIT_PACKET_ACTION_TYPE;
    description "Drop all packets.";
  }

  grouping l2ni-fdb-mac-config {
    description
      "Parameters relating to FDB behaviour relating to MAC
      addresses";

    leaf maximum-entries {
      type uint16 {
        range 1..65535;
      }
      default 65535;
      description
        "The maximum number of MAC address entries that should be
        accepted into the FDB";
    }
    leaf packet-action {
      type identityref {
        base MAC_LIMIT_PACKET_ACTION_TYPE;
      }
      default FLOOD_ACTION;
      description
        "Packet action when number of learnt mac entries exceed the configured limit";
    }
  }

  grouping l2ni-fdb-mac-top {
    container config {
      description
        "Configuration parameters relating to the FDB";
      uses l2ni-fdb-mac-config;
    }
  }

  augment "/oc-netinst:network-instances/oc-netinst:network-instance" {
    container ip-tunnels {
      config false;
      description
        "Operation state parameters for IP tunnels";
      uses ip-tunnel-state;
    }
  }

  augment "/oc-netinst:network-instances/oc-netinst:network-instance" {
    uses ip-tunnel-state-units;
  }

  augment "/oc-netinst:network-instances/oc-netinst:network-instance" +
          "/arc-oc-netinst-aug:ip-tunnels/arc-oc-netinst-aug:tunnels" +
          "/arc-oc-netinst-aug:next-hops/arc-oc-netinst-aug:next-hop" +
          "/arc-oc-netinst-aug:state" {
    leaf nexthop-type {
      type arc-aft-types:dpal-nexthop-type;
      description
        "nexthop type";
    }
  }

  augment "/oc-netinst:network-instances/oc-netinst:network-instance" +
          "/arc-oc-netinst-aug:ip-tunnels-units" +
          "/arc-oc-netinst-aug:ip-tunnel-unit-entry/arc-oc-netinst-aug:tunnels" +
          "/arc-oc-netinst-aug:next-hops/arc-oc-netinst-aug:next-hop" +
          "/arc-oc-netinst-aug:state" {
    leaf nexthop-type {
      type arc-aft-types:dpal-nexthop-type;
      description
        "nexthop type";
    }
  }

  augment "/oc-netinst:network-instances/oc-netinst:network-instance/oc-netinst:fdb" {
    uses l2ni-fdb-mac-top;
    uses l2ni-mac-table-state-top;
  }

  augment "/oc-netinst:network-instances/oc-netinst:network-instance" {
    uses fdb-units-top;
  }

  augment "/oc-netinst:network-instances/oc-netinst:network-instance" +
          "/oc-netinst:mpls/oc-netinst:signaling-protocols/oc-netinst:ldp" +
          "/oc-netinst:global" {
    uses arc-mpls-ldp:mpls-ldp-fec-filter;
    uses arc-mpls-ldp:mpls-ldp-transport-address-config;
    uses arc-mpls-ldp:mpls-ldp-max-local-binding-config;
  }

  augment "/oc-netinst:network-instances/oc-netinst:network-instance" +
          "/oc-netinst:mpls/oc-netinst:signaling-protocols/oc-netinst:ldp" +
          "/oc-netinst:neighbors/oc-netinst:neighbor" {
    uses arc-mpls-ldp:mpls-ldp-max-remote-binding-config;
  }

  augment "/oc-netinst:network-instances/oc-netinst:network-instance" +
          "/oc-netinst:mpls/oc-netinst:signaling-protocols/oc-netinst:ldp" {
    uses arc-mpls-ldp:mpls-ldp-sessions;
    uses arc-mpls-ldp:mpls-ldp-label-mapping;
    uses arc-mpls-ldp:mpls-ldp-hello-adjacency;
  }

  grouping mpls-icmp-tunnelling {
    description
    "Enable/disable ICMP Tunnelling";

    leaf icmp-tunnelling {
      type boolean;
      default true;
      description
        "Enable/Disable ICMP Tunnelling.";
    }
  }
  augment "/oc-netinst:network-instances/oc-netinst:network-instance" +
          "/oc-netinst:mpls/oc-netinst:global/oc-netinst:config" {
    uses mpls-icmp-tunnelling;
  }
}
