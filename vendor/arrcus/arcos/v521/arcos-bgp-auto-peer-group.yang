module arcos-bgp-auto-peer-group {
  yang-version 1.1;
  namespace "http://yang.arrcus.com/arcos/bgp/auto-peer-group";
  prefix arc-bgp-auto-peer-grp;

  import openconfig-types {
    prefix oc-types;
  }

  import ietf-inet-types {
    prefix oc-inet;
  }

  import arcos-bgp-types {
    prefix arc-bgp-types;  
  }

  import arcos-openconfig-bgp-types {
    prefix arc-oc-bgp-types;
  }

  import openconfig-interfaces {
    prefix oc-if;
  }

  organization
    "Arrcus, Inc.";

  contact
    "Arrcus, Inc.
     Customer Service
     Postal: 2077 Gateway Place
     San Jose, CA 95110
     Tel: +1 408 884-1965
     E-mail: yang-support@arrcus.com";

  description
    "This module defines Arrcus implemention
     of the BGP auto-peer-group module.

     Copyright (c) 2016-2022 by Arrcus, Inc.
     All rights reserved.";

  revision 2022-03-16 {
    description
      "Adding accumulative and periodic counters
       for performance monitoring";
  }

  grouping auto-peer-group {
    description
      "Parameters related to a BGP group";
    leaf index {
      type uint32;
      description
        "peer-group index";
    }

    leaf session-type {
      type string;
      description
        "peer-group type";
    }

    leaf name {
      type string;
      description
        "Name of the BGP peer-group";
    }

    leaf neighbor-count {
      type uint32;
      description
        "Number of neighbors in peer-group";
    }

    leaf in-use {
      type boolean;
      description
        "peer-group in use";
    }

    leaf route-reflector-client {
      type boolean;
      description
        "peer-group is RR client";
    }

    leaf route-server-client {
      type boolean;
      description
        "peer-group is route server client";
    }

    leaf as-type {
      type arc-bgp-types:bgp-as-type;
      description
        "peer-group AS type.";
    }
    leaf local-as {
      type oc-inet:as-number;
      description
        "peer-group local AS number";
    }
    leaf add-paths {
      type boolean;
      description
        "peer-group add-paths support.";
    }
    leaf add-paths-send {
      type identityref {
        base "arc-oc-bgp-types:ADD_PATHS_OPTIONS";
      }
      description
        "peer-group add-paths send option.";
    }
    leaf remove-private-as {
      type boolean;
      description
        "peer-group remove-private-as support.";
    }
    leaf replace-private-as {
      type boolean;
      description
        "peer-group replace-private-as support.";
    }
    leaf aigp {
      type boolean;
      description
        "peer-group AIGP metric support.";
    }
    leaf graceful-shutdown-enable {
      type boolean;
      description
        "peer-group graceful-shutdown enable support.";
    }
    leaf graceful-shutdown-local-preference {
      type boolean;
      description
        "peer-group graceful-shutdown local preference support.";
    }
    leaf graceful-shutdown-med {
      type boolean;
      description
        "peer-group graceful-shutdown MED support.";
    }
    leaf send-tracker-sid {
      type boolean;
      description
        "The peer is designated for sending tracker-sid.";
    }
    leaf slow-peer {
      type boolean;
      description
        "The peer is designated as slow peer.";
    }
    leaf version {
      type uint32;
      description
        "peer-group version.";
    }
    leaf nlri-sent {
      type uint32;
      description
        "peer-group prefix sent count.";
    }
    leaf unreach-nlri-sent {
      type uint32;
      description
        "peer-group unreachable prefix sent count.";
    }
    leaf labels-sent {
      type uint32;
      description
        "peer-group labels sent count.";
    }
    leaf export-policy {
      type string;
      description
        "peer-group export policy.";
    }
    leaf-list neighbors {
      type union {
        type oc-inet:ip-address;
	//        type leafref {
	//          path "/oc-if:interfaces/oc-if:interface/oc-if:name";
	//        }
      }
      description
       "Neighbors in this peer-group";
    }
    leaf updates-sent {
      type uint32;
      description
        "Total number of update messages sent.";
    }
    leaf pending-updates {
      type uint32;
      description
        "Total number of outstanding update messages.";
    }
    leaf update-delays {
      type uint32;
      description
        "Total number of delays due to too many outstanding updates.";
    }
    leaf extended-nexthop-encoding-capability {
      type arc-bgp-types:bgp-capability-state;
      description
        "Extended Next Hop Encoding Capability state";
    }
    leaf neighbor-type {
      type identityref {
        base "oc-types:ADDRESS_FAMILY";
      }
      description
        "Neighbor type i.e IPV4 or IPV6";
    }
    leaf next-hop-type {
      type arc-bgp-types:bgp-next-hop-type;
      description
        "peer-group next-hop type i.e SELF or UNCHANGED.";
    }

    uses pg-stats-counters-group;
  }

  grouping pg-stats-counters-group {
    container accu-stats-counters {
      description
        "Accumulative stats counters for this peer-group.";
      uses pg-stats-counters;
    }
    container peri-stats-counters {
      description
        "Periodic stats counters (reset every 30s) for this peer-group.";
      uses pg-stats-counters;
    }
  }

  grouping pg-stats-counters {
    leaf update-triggers {
      type uint64;
      description
        "Number of update triggers.";
    }
    leaf update-runs {
      type uint64;
      description
        "Number of update runs.";
    }
    leaf update-paths-processed {
      type uint64;
      description
        "Number of update paths processed.";
    }
    leaf update-paths-sent {
      type uint64;
      description
        "Number of update paths sent.";
    }
    leaf update-paths-wdn {
      type uint64;
      description
        "Number of update paths withdrawn.";
    }
    leaf update-paths-skipped {
      type uint64;
      description
        "Number of update paths skipped.";
    }
    leaf update-paths-deleted {
      type uint64;
      description
        "Number of update paths deleted.";
    }
    leaf update-paths-relabeled {
      type uint64;
      description
        "Number of update paths relabeled.";
    }
  }

  grouping bgp-auto-peer-group-list {
    description
      "The list of BGP peer groups";

    container auto-peer-groups {
      config false;
      list auto-peer-group {
        key "index session-type";
        description
          "List of BGP peer-groups configured on the local system -
          uniquely identified by peer-group name";

        uses auto-peer-group;
      }
    }
  }
}
