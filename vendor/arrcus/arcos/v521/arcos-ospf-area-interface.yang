submodule arcos-ospf-area-interface {

  yang-version "1.1";

  belongs-to arcos-ospf {
    prefix "arc-ospf";
  }

  import ietf-yang-types { prefix "yang"; }
  import ietf-inet-types { prefix "inet"; }
  import openconfig-interfaces { prefix "oc-if"; }
  import arcos-ospf-types { prefix "arc-ospf-types"; }

  // Include submodules
  include arcos-ospf-common;
  include arcos-ospf-statistics;

  description
    "This submodule provides OSPF configuration and operational
    state parameters that are specific to the interface context";

  grouping ospf-area-interface-config {
    description
      "Configuration parameters for an OSPF interface";

    leaf id {
      type string;
      description
        "An operator-specified string utilised to uniquely
        reference this interface";
    }

    leaf network-type {
      type identityref {
        base "arc-ospf-types:OSPF_NETWORK_TYPE";
      }
      description
        "The type of network that OSPF should use for the specified
        interface.";
    }

    leaf priority {
      type uint8;
      description
        "The local system's priority to become the designated
        router";
    }

    leaf metric {
      type arc-ospf-types:ospf-metric;
      description
        "The metric for the interface";
    }

    leaf passive {
      type boolean;
      description
        "When this leaf is set to true, the interface should be
        advertised within the OSPF area but OSPF adjacencies should
        not be established over the interface";
    }
  }

  grouping ospf-area-interface-state {
    description
      "Operation state parameters of an OSPF interface";

    leaf interface-up {
      type boolean;
      description
        "Indicates if this interface is up.";
    }

    leaf interface-state {
      type identityref {
        base "arc-ospf-types:OSPF_INTERFACE_STATE";
      }
      description
        "The state of the interface.";
    }

    leaf local-ip-address {
      type inet:ip-address;
      description
        "The IP address of this interface.";
    }

    leaf dr-router-id {
      type yang:dotted-quad;
      description
        "The router-id of the designated router for this interface.";
    }

    leaf dr-ip-address {
      type inet:ip-address;
      description
        "The IP address of the designated router for this interface.";
    }

    leaf bdr-router-id {
      type yang:dotted-quad;
      description
        "The router-id of the backup designated router for this
        interface.";
    }

    leaf bdr-ip-address {
      type inet:ip-address;
      description
        "The IP address of the backup designated router for this
        interface.";
    }

    leaf mtu {
      type uint32;
      description
        "The MTU of the interface.";
    }

    leaf speed {
      type uint64;
      units Mbps;
      description
        "Interface speed in Mbps.";
    }

    leaf neighbor-count {
      type uint32;
      description
        "The number of neighbors under this interface";
    }

    leaf exchange-neighbor-count {
      type uint32;
      description
        "The number of neighbors under this interface that are in
         EXCHANGE state";
    }

    leaf loading-neighbor-count {
      type uint32;
      description
        "The number of neighbors under this interface that are in
         LOADING state";
    }

    leaf full-neighbor-count {
      type uint32;
      description
        "The number of neighbors under this interface that are in
         FULL state";
    }
  }

  grouping ospf-area-interface-timers-config {
    description
      "Configuration parameters relating to per-interface OSPF
      timers";

    leaf dead-interval {
      type uint32;
      units seconds;
      description
        "The number of seconds that the local system should let
        elapse before declaring a silent router down";
      reference "RFC2328";
    }

    leaf hello-interval {
      type uint32;
      units seconds;
      description
        "The number of seconds the local system waits between the
        transmission of subsequent Hello packets";
    }

    leaf retransmission-interval {
      type uint32;
      units seconds;
      description
        "The number of seconds that the local system waits before
        retransmitting an unacknowledged LSA.";
    }

    leaf transmission-delay {
      type uint32;
      units seconds;
      default 1;
      description
        "The estimated number of seconds it takes to transmit a Link State
         Update packet over this interface.";
    }
  }

  grouping ospf-area-interface-neighbor-state {
    description
      "Operational state parameters relating an individual neighbor
      system on an interface within an OSPF area";

    leaf neighbor-router-id {
      type yang:dotted-quad;
      description
        "The router-id of the neighboring router.";
    }

    leaf neighbor-ip-address {
        type inet:ip-address;
        description
          "The IP address of the remote system.";
    }

    leaf adjacency-state {
      type identityref {
        base "arc-ospf-types:OSPF_NEIGHBOR_STATE";
      }
      description
        "The state of the adjacency with the neighbor.";
    }

    leaf optional-capabilities {
      type yang:hex-string;
      description
        "The optional capabilities field received in the Hello
        message from the neighbor";
    }

    leaf priority {
      type uint8;
      description
        "The remote system's priority to become the designated router";
    }
  }

  grouping ospf-area-interface-neighbor-ext-state {
    description
      "Additional operational state relating an individual neighbor
      system on an interface within an OSPF area";

    leaf last-established-exstart-timestamp {
      type string;
      description
        "The timestamp of the last transition to EXSTART state.";
    }

    leaf last-established-full-timestamp {
      type string;
      description
        "The timestamp of the last transition to FULL state.";
    }

    leaf next-dead-timer-expiry-timestamp {
      type string;
      description
        "The future timestamp of the dead timer expiry.";
    }

    leaf next-dead-timer-expiry-remaining-time {
      type uint32;
      description
        "The number of seconds left before the dead timer expires.";
    }

    leaf last-dead-timer-expiry-timestamp {
      type string;
      description
        "The timestamp of the last time the dead timer expired.";
    }

    leaf deletion-remaining-time {
      type uint32;
      description
        "The number of seconds left before a dormant neighbor in
         DOWN state is deleted from the system. This field is
         applicable when the neighbor is is in DOWN state.";
    }
  }

  grouping ospf-area-interface-structure {
    description
      "Structural grouping for configuration and operational state
      parameters that relate to an interface";

    container interfaces {
      description
        "Enclosing container for a list of interfaces enabled within
        this area";

      list interface {
        key "id";

        description
          "List of interfaces which are enabled within this area";

        leaf id {
          type leafref {
            path "../config/id";
          }
          description
            "A pointer to the identifier for the interface.";
        }

        uses oc-if:interface-ref;

        container config {
          description
            "Configuration parameters for the interface on which
            OSPF is enabled";

          uses ospf-area-interface-config;
        }

        container state {
          config false;
          description
            "Operational state parameters for the interface on which
            OSPF is enabled";

          uses ospf-area-interface-config;
          uses ospf-area-interface-state;
        }

        uses ospf-bfd-structure;

        container timers {
          description
            "Timers relating to OSPF on the interface";

          container config {
            description
              "Configuration parameters for OSPF timers on the
              interface";

            uses ospf-area-interface-timers-config;
          }

          container state {
            config false;
            description
              "Operational state parameters for OSPF timers on
              the interface";

            uses ospf-area-interface-timers-config;
          }
        }

        container statistics {
          config false;
          description
            "Interface statistics";

          uses ospf-pkt-statistics-structure;
          uses ospf-interface-lsa-statistics-structure;
        }

        container neighbors {
          config false;

          description
            "Enclosing container for the list of neighbors that
            an adjacency has been established with on the interface";

          list neighbor {
            key "neighbor-router-id";

            description
              "A neighbor with which an OSPF adjacency has been
              established within this area";

            leaf neighbor-router-id {
              type leafref {
                path "../state/neighbor-router-id";
              }
              description
                "Reference to the router ID of the adjacent system";
            }

            container state {
              description
                "Operational state parameters relating to the adjacent system";

              uses ospf-area-interface-neighbor-state;
              uses ospf-area-interface-neighbor-ext-state;
            }
          }
        }
      }
    }
  }
}
