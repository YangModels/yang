module arcos-datapath-queues {
  yang-version 1.1;
  namespace "http://yang.arrcus.com/arcos/datapath/queues";
  prefix arcos-dp-queues;

  import openconfig-interfaces { prefix "oc-if"; }

  organization
    "Arrcus, Inc.";
  contact
    "Arrcus, Inc.
     2077 Gateway Place
     San Jose, CA 95110
     Tel: +1 (408) 884-1965
     E-mail: eng@arrcus.com";
  description
    "YANG data-model for datapath queues";
  revision "2022-03-18" {
    description
      "Enable support for WRED drop counts";
  }

  grouping voq-top {
    description
      "Grouping of voq operational data per interface.";

    container queues {
      config false;
      description
        "Enclosing container for the list of interface references.";

      list interface {
        key "ifname";

        description
          "The list of interfaces with voqs associated";

        leaf ifname {
          type leafref {
            path "/oc-if:interfaces/oc-if:interface/oc-if:config/oc-if:name";
          }
          description
            "The interface name key for interface list";
        }

        container state {
          config false;
          description
            "Operational state parameters relating to the voq
            entries for an interface";

          uses voq-interfaces-state;
        }
      }
    }
  }

  grouping voq-interfaces-state {
    description
      "Voq information for an interface";

    container voqs {
      config false;
      description
        "The list of voqs that are present on an interface.";

      list voq {
        key "id";

        description
          "A voq associated with an interface on an instance";

        leaf id {
          type leafref {
            path "../state/id";
          }
          description
            "A unique index identifying the voq entry";
        }

        container state {
          config false;
          description
            "Operational state parameters relating to the voq";

          uses voq-state;
        }
      }
    }
  }

  grouping queue-stats-top {
    leaf queue-txcount {
      type uint64;
      description
        "Number of packets successfully transmitted out of a queue";
    }
    leaf queue-txbytes {
      type uint64;
      description
        "Number of bytes successfully transmitted out of a queue";
    }
    leaf queue-dropcount {
      type uint64;
      description
        "Number of packets dropped from a queue.
         Drops could be as a result of dropping descipline or
         could be as a result of unavailabilty of buffers";
    }
    leaf queue-dropbytes {
      type uint64;
      description
        "Number of bytes dropped from a queue.
         Drops could be as a result of dropping descipline or
         could be as a result of unavailabilty of buffers";
    }
    leaf wred-dropped-packets {
      type uint64;
      description
        "Number of packets that were dropped by wred algorithm.";
    }
  }

  grouping voq-state {
    description
      "Parameters relating to a voq within the entry";

    leaf id {
      type uint64;
      description
        "A unique index identifying the voq.";
    }

    uses queue-stats-top;

  }
  uses voq-top;
}
