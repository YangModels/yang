module arcos-interfaces-breakout {
  yang-version 1.1;
  namespace "http://yang.arrcus.com/arcos/interfaces/breakout";
  prefix arc-if-brkout;

  container break-out {
    description
        "Configure physical port break-out";
    list slot {
      key "slot-id";
        description "List of slots configured for breakout";
      leaf slot-id {
        type uint32;
        description "slot number";
      }
      list ports {
       description "port number to break-out";
       key "port";
        leaf port {
          type uint16;
          description "port number";
        }
        leaf mode {
          type enumeration {
            enum 10gx4 {
              value 1;
            }
            enum 25gx4 {
              value 2;
            }
            enum 40gx2 {
              value 3;
            }
            enum 50gx2 {
              value 4;
            }
            enum 10gx8 {
              value 5;
            }
            enum 25gx8 {
              value 6;
            }
            enum 50gx4 {
              value 7;
            }
            enum 100gx4 {
              value 8;
            }
            enum 100gx2 {
              value 9;
            }
            enum 200gx2 {
              value 10;
            }
          }
          mandatory true;
          description "breakout type(speed x number of ports)";
        }
      }
    }
  }
}
