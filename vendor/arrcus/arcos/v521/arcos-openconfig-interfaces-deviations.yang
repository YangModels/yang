module arcos-openconfig-interfaces-deviations {
  yang-version 1.1;
  namespace "http://yang.arrcus.com/arcos/openconfig/interfaces/deviations";
  prefix arc-oc-if-dev;

  import openconfig-interfaces {
    prefix oc-if;
  }

  import openconfig-if-ethernet {
    prefix oc-eth;
  }

  import openconfig-vlan {
    prefix oc-vlan;
  }

  import openconfig-vlan-types {
    prefix oc-vlan-types;
  }

  import openconfig-if-aggregate {
    prefix oc-lag;
  }

  import ietf-yang-types {
    prefix yang;
  }

  import iana-if-type {
    prefix ianaift;
  }

  import arcos-features {
    prefix arc-features;
  }

  organization
    "Arrcus, Inc.";
  contact
    "Arrcus, Inc.
     2077 Gateway Place
     Suite 400
     San Jose, CA 95110
     E-mail: yang-support@arrcus.com";
  description
    "This module defines deviations statements for the
     for OpenConfig interfaces module.
     Copyright (c) 2016-2023 by Arrcus, Inc.
     All rights reserved.";

  revision 2023-03-13 {
    description
      "enable interface index range to 9999";
  }


  deviation "/oc-if:interfaces/oc-if:interface/oc-if:subinterfaces/oc-if:subinterface" {
    deviate add {
      max-elements 2000;
    }
    description
      "restricted to user configurable max vlans";
  }
  
  deviation "/oc-if:interfaces/oc-if:interface/oc-if:subinterfaces/oc-if:subinterface" {
    deviate add {
      must "index = 0 or "
         + "/arc-features:features/arc-features:feature[arc-features:name='arc-features:ARCOS_SUBIF']"
         + "/arc-features:supported = 'true'" {
        error-message "Tagged sub-interfaces not suported on this platform";
      }
    }
    description
      "restricted to physical l3 interface";
  }

  deviation "/oc-if:interfaces/oc-if:interface/oc-if:hold-time" {
    deviate not-supported;
    description
      "Not supported in this release";
  }

  deviation "/oc-if:interfaces/oc-if:interface/oc-if:config/oc-if:enabled" {
    deviate replace {
      default "false";
    }
  }

  deviation "/oc-if:interfaces/oc-if:interface/oc-if:config" +
            "/oc-if:description" {
    deviate replace {
      type string {
        length "1..254";
      }
    }
  }

  deviation "/oc-if:interfaces/oc-if:interface/oc-if:state" +
            "/oc-if:description" {
    deviate replace {
      type string {
        length "1..254";
      }
    }
  }

  deviation "/oc-if:interfaces/oc-if:interface/oc-if:subinterfaces" +
            "/oc-if:subinterface/oc-if:config/oc-if:description" {
    deviate replace {
      type string {
        length "1..254";
      }
    }
  }

  deviation "/oc-if:interfaces/oc-if:interface/oc-if:subinterfaces" +
            "/oc-if:subinterface/oc-if:state/oc-if:description" {
    deviate replace {
      type string {
        length "1..254";
      }
    }
  }

  deviation "/oc-if:interfaces/oc-if:interface/oc-if:config/oc-if:mtu" {
    deviate add {
      must "current()/../oc-if:type != 'ianaift:l3ipvlan'" {
        error-message "MTU Not supported on SVI in this release";
      }
    }

    deviate replace {
      type uint16 {
        range "1280..9214";
      }
    }
  }

  deviation "/oc-if:interfaces/oc-if:interface/oc-if:subinterfaces/"
          + "oc-if:subinterface/oc-if:config/oc-if:index" {
    deviate replace {
      type uint32 {
        range "0..9999";
      }
    }
  }

  deviation "/oc-if:interfaces/oc-if:interface/oc-if:subinterfaces/"
          + "oc-if:subinterface/oc-if:config/oc-if:enabled" {
    deviate add {
      must "current()/../index != 0 or current() = 'true'" {
        error-message "Disabling of subinterface 0 must be controlled via the main interface";
      }
    }
  }

  deviation "/oc-if:interfaces/oc-if:interface/oc-if:state/oc-if:last-change" {
    deviate replace {
      type yang:date-and-time;
    }
    description
      "Date and time of the last state change of the interface
       (e.g., up-to-down transition)";
  }

  deviation "/oc-if:interfaces/oc-if:interface/oc-if:subinterfaces/"
          + "oc-if:subinterface/oc-if:state/oc-if:last-change" {
    deviate replace {
      type yang:date-and-time;
    }
    description
      "Date and time of the last state change of the interface
       (e.g., up-to-down transition)";
  }
}
