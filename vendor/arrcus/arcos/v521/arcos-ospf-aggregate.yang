submodule arcos-ospf-aggregate {
  yang-version "1.1";

  belongs-to arcos-ospf {
    prefix "arc-ospf";
  }

  import openconfig-routing-policy { prefix oc-rpol; }
  import arcos-ospf-types { prefix "arc-ospf-types"; }
  import ietf-inet-types  { prefix "inet"; }

  description
    "This submodule provides OSPF configuration and operational
    state parameters that are related to OSPF aggregate redistribute
    and summary funcationality.";

  grouping ospf-aggregate-redist-config {

    leaf tag {
        type uint32;
        description
          "value to match with redistributed route tag.";
    }
  }

  grouping ospf-aggregate-config {

    leaf prefix {
      type inet:ip-prefix;
      description
        "IP network address to aggregate";
    }

    leaf advertise {
      type arc-ospf-types:ospf-aggregate-advertisement;
      default AGGREGATE_ADVERTISE;
      description
        "Advertise/Suppress aggregated addresses from advertising";
    }

    leaf import-policy {
      type leafref {
        path "/oc-rpol:routing-policy/oc-rpol:policy-definitions/" +
          "oc-rpol:policy-definition/oc-rpol:config/oc-rpol:name";
      }
      description
        "Policy name to filter the contributor routes for generating
        the aggregate";
    }
  }

  grouping ospf-redistribute-aggregates-structure {
    description
      "structural grouping for configuration and operational
      state parameters relating to OSPF redistribute aggregates";

    container redistribute-aggregates {
      description "Aggregate the redistribute prefixes";

      list redistribute-aggregate {
        key "prefix";

        description "Aggregate the redistributed routes";

        leaf prefix {
          type leafref {
            path "../config/prefix";
          }
          description "Network prefix to aggregate";
        }
        container config {
          uses ospf-aggregate-config;
        }
        container state {
          config false;
          uses ospf-aggregate-config;
        }
      }
    }
  }

  grouping ospf-summary-aggregates-structure {
    description
      "structural grouping for configuration and operational
      state parameters relating to OSPF summary aggregates";

    container summary-aggregates {
      description "Aggregate the summary prefixes";

      list summary-aggregate {
        key "prefix";

        description "Aggregate the intra-area routes";

        leaf prefix {
          type leafref {
            path "../config/prefix";
          }
          description "Network prefix to aggregate";
        }
        container config {
          uses ospf-aggregate-config;
        }
        container state {
          config false;
          uses ospf-aggregate-config;
        }
      }
    }
  }
}
