module arcos-openconfig-spanning-tree-deviations {
  yang-version 1.1;
  namespace "http://yang.arrcus.com/arcos/openconfig/spanning-tree/deviations";
  prefix arc-oc-stp-dev;

  import openconfig-spanning-tree {
    prefix oc-stp;
  }

  import openconfig-vlan-types {
    prefix oc-vlan-types;
  }

  organization
    "Arrcus, Inc.";

    contact
        "Email: eng@arrcus.com";

  description
    "This module defines deviation statements for Arrcus
     implemention of the openconfig-spanning-tree module.";

    revision 2018-08-14 {
        description "ArcOS release 2.2.1";
    }


  revision 2017-07-05 {
    description
      "Initial Revision
      ";

    reference
      "RFC 6020: YANG - A Data Modeling Language for the
       Network Configuration Protocol (NETCONF)";
  }



  deviation "/oc-stp:stp/oc-stp:global/oc-stp:config/oc-stp:enabled-protocol" {
    deviate not-supported;
    description "Not supported in this release";
  }
  deviation "/oc-stp:stp/oc-stp:global/oc-stp:state/oc-stp:enabled-protocol" {
    deviate not-supported;
    description "Not supported in this release";
  }

  deviation "/oc-stp:stp/oc-stp:global/oc-stp:config/oc-stp:bpdu-filter" {
    deviate not-supported;
    description "Not supported in this release";
  }
  deviation "/oc-stp:stp/oc-stp:global/oc-stp:state/oc-stp:bpdu-filter" {
    deviate not-supported;
    description "Not supported in this release";
  }

  deviation "/oc-stp:stp/oc-stp:global/oc-stp:config/oc-stp:bpduguard-timeout-recovery" {
    deviate not-supported;
    description "Not supported in this release";
  }
  deviation "/oc-stp:stp/oc-stp:global/oc-stp:state/oc-stp:bpduguard-timeout-recovery" {
    deviate not-supported;
    description "Not supported in this release";
  }

  deviation "/oc-stp:stp/oc-stp:global/oc-stp:config/oc-stp:etherchannel-misconfig-guard" {
    deviate not-supported;
    description "Not supported in this release";
  }
  deviation "/oc-stp:stp/oc-stp:global/oc-stp:state/oc-stp:etherchannel-misconfig-guard" {
    deviate not-supported;
    description "Not supported in this release";
  }

  deviation "/oc-stp:stp/oc-stp:global/oc-stp:config/oc-stp:loop-guard" {
    deviate not-supported;
    description "Not supported in this release";
  }
  deviation "/oc-stp:stp/oc-stp:global/oc-stp:state/oc-stp:loop-guard" {
    deviate not-supported;
    description "Not supported in this release";
  }

  deviation "/oc-stp:stp/oc-stp:rstp" {
    deviate not-supported;
    description "Not supported in this release";
  }

  deviation "/oc-stp:stp/oc-stp:mstp" {
    deviate not-supported;
    description "Not supported in this release";
  }

  deviation "/oc-stp:stp/oc-stp:rapid-pvst/oc-stp:state/oc-stp:vlan" +
            "/oc-stp:bridge-address" {
    deviate replace {
      type string;
    }
    description "Currently deviate to string type because confd otherwise
                 takes it as binary type";
  }

  deviation "/oc-stp:stp/oc-stp:rapid-pvst/oc-stp:state/oc-stp:vlan" +
            "/oc-stp:designated-root-address" {
    deviate replace {
      type string;
    }
    description "Currently deviate to string type because confd otherwise
                 takes it as binary type";
  }

  deviation "/oc-stp:stp/oc-stp:rapid-pvst/oc-stp:state/oc-stp:vlan" +
            "/oc-stp:interface/oc-stp:designated-root-address" {
    deviate replace {
      type string;
    }
    description "Currently deviate to string type because confd otherwise
                 takes it as binary type";
  }

  deviation "/oc-stp:stp/oc-stp:rapid-pvst/oc-stp:state/oc-stp:vlan" +
            "/oc-stp:interface/oc-stp:designated-bridge-address" {
    deviate replace {
      type string;
    }
    description "Currently deviate to string type because confd otherwise
                 takes it as binary type";
  }

  deviation "/oc-stp:stp/oc-stp:rapid-pvst/oc-stp:vlan/oc-stp:vlan-id" {
    deviate replace {
      type oc-vlan-types:vlan-id;
    }
    description "deviate vlan id to vlan-types";
  }

  deviation "/oc-stp:stp/oc-stp:rapid-pvst/oc-stp:vlan/oc-stp:config/oc-stp:vlan-id" {
    deviate not-supported;
    description "Not supported in this release";
  }

  deviation "/oc-stp:stp/oc-stp:rapid-pvst/oc-stp:state/oc-stp:vlan" +
            "/oc-stp:hold-time" {
    deviate not-supported;
    description "Not supported in this release";
  }

  deviation "/oc-stp:stp/oc-stp:rapid-pvst/oc-stp:vlan/oc-stp:config/" +
            "oc-stp:forwarding-delay" {
    deviate add {
      must "2 * (current() - 1) >=  current()/../max-age" {
        error-message "Forwarding-delay must satisfy the following " + 
                      "relationship with max-age: " +
                      "2 * (Bridge Forward Delay - 1) >= Bridge Max Age";
      }
    }
  }

  deviation "/oc-stp:stp/oc-stp:rapid-pvst/oc-stp:vlan/oc-stp:config/" +
            "oc-stp:max-age" {
    deviate add {
      must "2 * (current()/../forwarding-delay - 1) >= current()" {
        error-message "Max-age must satisfy the following " + 
                      "relationship with forwarding-delay: " +
                      "2 * (Bridge Forward Delay - 1) >= Bridge Max Age";
      }
    }
  }
}
