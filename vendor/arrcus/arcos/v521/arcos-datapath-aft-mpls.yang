submodule arcos-datapath-aft-mpls {
  yang-version "1.1";

  belongs-to "arcos-datapath-aft" {
    prefix "arcos-dp-aft";
  }

  import openconfig-mpls-types { prefix "oc-mpls-types"; }

  // Include common cross-AFT groupings from the common submodule.
  include arcos-datapath-aft-common;

  organization
    "XXXXX";

  contact
    "XXXXX";

  description
    "Submodule containing definitions of groupings for the abstract
    forwarding table for MPLS label forwarding.";

  grouping aft-mpls-structural {
    description
      "Structural grouping defining the schema for the MPLS
      abstract forwarding table.";

    list label-entry {
      key "label";

      description
        "List of the MPLS entries within the abstract
        forwarding table. This list is keyed by the top-most MPLS
        label.";

      leaf label {
        type leafref {
          path "../state/label";
        }
        description
          "Reference to the top-most MPLS label matched by the
          entry.";
      }

      container state {
        config false;
        description
          "Operational state parameters for the MPLS AFT
          entry.";
        uses aft-mpls-entry-config;
        uses aft-mpls-entry-state;
      }

    }
  }

  grouping aft-mpls-entry-config {
    description
      "Configuration parameters for the MPLS entry.";

    leaf label {
        type oc-mpls-types:mpls-label;
        description
          "The top-most MPLS label that should be matched to
          utilise the AFT entry.";
    }
  }

  grouping aft-mpls-entry-state {
    description
      "Operational state parameters for the MPLS entry.";
    uses aft-common-entry-state;
    leaf vrf {
      type string;
      description
        "A reference to the VRF in use for the entry";
    }
  }
}
