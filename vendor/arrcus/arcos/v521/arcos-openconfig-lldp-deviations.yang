module arcos-openconfig-lldp-deviations {
  yang-version 1.1;
  namespace "http://yang.arrcus.com/arcos/openconfig/lldp/deviations";
  prefix arc-oc-lldp-dev;

  import openconfig-lldp {
    prefix oc-lldp;
  }

  import openconfig-lldp-types {
    prefix oc-lldp-types;
  }

  import openconfig-yang-types {
    prefix oc-yang;
  }

  import ietf-inet-types {
    prefix inet;
  }

  deviation "/oc-lldp:lldp/oc-lldp:config/oc-lldp:enabled" {
    deviate not-supported;
    description "Not Supported in this release";
  }

  deviation "/oc-lldp:lldp/oc-lldp:config/oc-lldp:chassis-id" {
    deviate not-supported;
    description "Not Supported in this release";
  }

  deviation "/oc-lldp:lldp/oc-lldp:config/oc-lldp:chassis-id-type" {
    deviate not-supported;
    description "Not Supported in this release";
  }

  deviation "/oc-lldp:lldp/oc-lldp:state/oc-lldp:chassis-id" {
    deviate not-supported;
    description "Not Supported in this release";
  }

  deviation "/oc-lldp:lldp/oc-lldp:state/oc-lldp:chassis-id-type" {
    deviate not-supported;
    description "Not Supported in this release";
  }

  deviation "/oc-lldp:lldp/oc-lldp:config/oc-lldp:suppress-tlv-advertisement" {
    deviate not-supported;
    description "Not Supported in this release";
  }

  deviation "/oc-lldp:lldp/oc-lldp:state/oc-lldp:enabled" {
    deviate not-supported;
    description "Not Supported in this release";
  }

  deviation "/oc-lldp:lldp/oc-lldp:state/oc-lldp:suppress-tlv-advertisement" {
    deviate not-supported;
    description "Not Supported in this release";
  }

  deviation "/oc-lldp:lldp/oc-lldp:interfaces/oc-lldp:interface/" +
            "oc-lldp:neighbors/oc-lldp:neighbor/oc-lldp:state/" +
            "oc-lldp:age" {
      deviate replace {
        type string;
      }
  }

  deviation "/oc-lldp:lldp/oc-lldp:interfaces/oc-lldp:interface/" +
            "oc-lldp:neighbors/oc-lldp:neighbor/oc-lldp:state/" +
            "oc-lldp:last-update" {
    deviate not-supported;
    description "Not Supported in this release";
  }

  deviation "/oc-lldp:lldp/oc-lldp:interfaces/oc-lldp:interface/" +
            "oc-lldp:neighbors/oc-lldp:neighbor/oc-lldp:config" {
    deviate not-supported;
    description "Not Supported in this release";
  }

  deviation "/oc-lldp:lldp/oc-lldp:interfaces/oc-lldp:interface/" +
            "oc-lldp:neighbors/oc-lldp:neighbor/oc-lldp:custom-tlvs" {
    deviate not-supported;
    description "Not Supported in this release";
  }

  deviation "/oc-lldp:lldp/oc-lldp:interfaces/oc-lldp:interface/" +
            "oc-lldp:neighbors/oc-lldp:neighbor/oc-lldp:custom-tlvs/" +
            "oc-lldp:tlv" {
    deviate not-supported;
    description "Not Supported in this release";
  }

  deviation "/oc-lldp:lldp/oc-lldp:interfaces/oc-lldp:interface/" +
            "oc-lldp:neighbors/oc-lldp:neighbor/oc-lldp:custom-tlvs/" +
            "oc-lldp:tlv/oc-lldp:type" {
    deviate not-supported;
    description "Not Supported in this release";
  }

  deviation "/oc-lldp:lldp/oc-lldp:interfaces/oc-lldp:interface/" +
            "oc-lldp:neighbors/oc-lldp:neighbor/oc-lldp:custom-tlvs/" +
            "oc-lldp:tlv/oc-lldp:oui" {
    deviate not-supported;
    description "Not Supported in this release";
  }

  deviation "/oc-lldp:lldp/oc-lldp:interfaces/oc-lldp:interface/" +
            "oc-lldp:neighbors/oc-lldp:neighbor/oc-lldp:custom-tlvs/" +
            "oc-lldp:tlv/oc-lldp:oui-subtype" {
    deviate not-supported;
    description "Not Supported in this release";
  }

  deviation "/oc-lldp:lldp/oc-lldp:interfaces/oc-lldp:interface/" +
            "oc-lldp:neighbors/oc-lldp:neighbor/oc-lldp:custom-tlvs/" +
            "oc-lldp:tlv/oc-lldp:config" {
    deviate not-supported;
    description "Not Supported in this release";
  }

  deviation "/oc-lldp:lldp/oc-lldp:interfaces/oc-lldp:interface/" +
            "oc-lldp:neighbors/oc-lldp:neighbor/oc-lldp:custom-tlvs/" +
            "oc-lldp:tlv/oc-lldp:state" {
    deviate not-supported;
    description "Not Supported in this release";
  }

  deviation "/oc-lldp:lldp/oc-lldp:interfaces/oc-lldp:interface/" +
            "oc-lldp:neighbors/oc-lldp:neighbor/oc-lldp:custom-tlvs/" +
            "oc-lldp:tlv/oc-lldp:state/oc-lldp:type" {
    deviate not-supported;
    description "Not Supported in this release";
  }

  deviation "/oc-lldp:lldp/oc-lldp:interfaces/oc-lldp:interface/" +
            "oc-lldp:neighbors/oc-lldp:neighbor/oc-lldp:custom-tlvs/" +
            "oc-lldp:tlv/oc-lldp:state/oc-lldp:oui" {
    deviate not-supported;
    description "Not Supported in this release";
  }

  deviation "/oc-lldp:lldp/oc-lldp:interfaces/oc-lldp:interface/" +
            "oc-lldp:neighbors/oc-lldp:neighbor/oc-lldp:custom-tlvs/" +
            "oc-lldp:tlv/oc-lldp:state/oc-lldp:oui-subtype" {
    deviate not-supported;
    description "Not Supported in this release";
  }

  deviation "/oc-lldp:lldp/oc-lldp:interfaces/oc-lldp:interface/" +
            "oc-lldp:neighbors/oc-lldp:neighbor/oc-lldp:custom-tlvs/" +
            "oc-lldp:tlv/oc-lldp:state/oc-lldp:value" {
    deviate not-supported;
    description "Not Supported in this release";
  }

  deviation "/oc-lldp:lldp/oc-lldp:interfaces/oc-lldp:interface/" +
            "oc-lldp:neighbors/oc-lldp:neighbor/oc-lldp:capabilities/" +
            "oc-lldp:capability/oc-lldp:config" {
    deviate not-supported;
    description "Not Supported in this release";
  }

  deviation "/oc-lldp:lldp/oc-lldp:config/oc-lldp:hello-timer" {
    deviate replace {
      type uint64 {
        range "5..65534";
      }
    }
  }
}
