module arcos-vrrp-debug {
  yang-version 1.1;
  namespace "http://yang.arrcus.com/arcos/vrrp/debug";
  prefix arc-vrrp-dbg;

  import arcos-debug {
    prefix arc-dbg;
  }

  grouping vrrp-debug-filters {
    uses arc-dbg:intf-match-filter {
      when "item-name = 'packet'";
    }

    uses arc-dbg:ip-address-match-filter {
      when "item-name = 'packet'";
    }

    uses arc-dbg:ip-prefix-match-filter {
      when "item-name = 'rib'";
    }
  }

  grouping vrrp-debug-top {
    container vrrp {
      description
        "VRRP related debug information.";
      config false;

      uses arc-dbg:debug-component-top;
    }
  }

  augment "/arc-dbg:debug/arc-dbg:debug-attach-points" {
    uses vrrp-debug-top {
      when "arc-dbg:component = 'vrrp'" {
        description
          "Include VRRP debug information under global debug attach-point list";
      }
      description
        "Debug information related to a specific instance of VRRP.";
    }
  }

  augment "/arc-dbg:debug/arc-dbg:debug-attach-points/arc-vrrp-dbg:vrrp" +
          "/arc-vrrp-dbg:component-debug-items" {
    uses vrrp-debug-filters;
  }
}
