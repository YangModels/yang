submodule arcos-ospfv3-common {

  yang-version "1.1";

  belongs-to arcos-ospfv3 {
    prefix "arc-ospfv3";
  }

  import ietf-yang-types { prefix "yang"; }
  import openconfig-types { prefix "oc-types"; }
  import arcos-ospf-types { prefix "arc-ospf-types"; }

  description
    "This submodule provides OSPFv3 configuration and operational
    state parameters that are common under one or more contexts.";

  /*
   * OSPFv3 packet Option bits
   */
  grouping ospfv3-packet-options {
    description
      "OSPFv3 packet Options field";

    container options {
      leaf v6-bit {
        type boolean;
        description
          "If this bit is clear, the router/link should be excluded from IPv6
           routing calculations";
      }

      leaf e-bit {
        type boolean;
        description
          "This bit describes the way AS-external-LSAs are flooded";
      }

      leaf n-bit {
        type boolean;
        description
          "This bit describes whether or not the router is attached to an
           NSSA";
      }

      leaf r-bit {
        type boolean;
        description
          "This bit describes whether the originator is an active router";
      }
    }
  }

  /*
   * OSPF Maintenance
   */
  grouping ospfv3-maint-router-lsa-config {
    description
      "This grouping defines maintenance mode OSFPv3 Router LSA configuration.";

    leaf reset-v6-bit {
      type boolean;
      description
        "Indicates if the V6-bit in the Options field of Router LSA
         should be reset to 0";
    }

    leaf reset-r-bit {
      type boolean;
      description
        "Indicates if the R-bit in the Options field of Router LSA
         should be reset to 0";
    }
  }
}
