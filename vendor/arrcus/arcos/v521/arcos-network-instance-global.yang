module arcos-network-instance-global {
  yang-version 1.1;
  namespace "http://yang.arrcus.com/arcos/network-instance-global";
  prefix arc-ni-gbl;


  container network-instance-global {
    description
      "Global parameters related to any network-instance";

    container fdb {
      description
        "Global MAC FDB configuration";
      leaf mac-aging-time {
        type uint16;
        units seconds;
        description
          "The number of seconds of inactivity after which the entry
          in any FDB is timed out.";
      }
    }
  }
}
