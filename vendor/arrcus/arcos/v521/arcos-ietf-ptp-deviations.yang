/**
 * Filename: arcos-ietf-ptp-deviations.yang
 *
 * Description:
 * YANG data-model for Arcos PTP deviations
 *
 * Copyright 2022-2022 by Arrcus, Inc.
 * All rights reserved.
 */

module arcos-ietf-ptp-deviations {
  yang-version 1.1;
  namespace "http://yang.arrcus.com/arcos/ietf/ptp/deviations";
  prefix arc-ietf-ptp-dev;

  import ietf-ptp {
    prefix ptp;
  }

  import arcos-ietf-ptp-types {
    prefix arc-ptp-types;
  }

  import openconfig-interfaces {
    prefix oc-if;
  }

  import tailf-common {
    prefix tailf;
  }


  organization 
    "Arrcus, Inc";

  contact
    "Arrcus, Inc.
     2077 Gateway Place 
     Suite 400
     San Jose, CA 95110
     E-mail: yang-support@arrcus.com";

  description
    "This module lists arrcus ptp deviation related information.
     Copyright (c) 2022-2022 by Arrcus, Inc.
     All rights reserved.";

  revision 2023-03-15 {
    description
      "Add subinterface support to portDS underlying-interface";
  }

  revision 2023-02-20 {
    description
      "Deviate slave-only default false as according to IEEE-1588";
  }

  revision 2023-01-30 {
    description
      "Deviate time-source for readability. Moves from type uint8 to an enum
       based on IEEE-1588";
  }

  revision 2022-11-18 {
    description
      "Enabled profile, BC and GM support";

    reference
      "RFC 8575: YANG Data Model for the Precision Time Protocol (PTP)";
  }

  revision 2022-08-08 {
    description
      "Initial revision.";

    reference
      "RFC 8575: YANG Data Model for the Precision Time Protocol (PTP)";
  }

  deviation "/ptp:ptp/ptp:transparent-clock-port-ds-list" {
    deviate not-supported;
    description "Not Supported in this release";
  }


  deviation "/ptp:ptp/ptp:transparent-clock-default-ds/ptp:number-ports" {
    deviate not-supported;
    description "Not Supported in this release";
  }

  deviation "/ptp:ptp/ptp:transparent-clock-default-ds/ptp:primary-domain" {
    deviate not-supported;
    description "Not Supported in this release";
  }

  deviation "/ptp:ptp/ptp:transparent-clock-default-ds/ptp:delay-mechanism" {
    deviate replace {
      type arc-ptp-types:arc-dm-enum;
    }
  }

  deviation "/ptp:ptp/ptp:instance-list/ptp:port-ds-list/ptp:underlying-interface" {
    deviate not-supported;
    description "Replaced within arcos-ietf-ptp-augments";
  }
  
  deviation "/ptp:ptp/ptp:instance-list/ptp:default-ds/ptp:clock-identity" {
    deviate replace {
      type tailf:hex-list;
    }
  }
  deviation "/ptp:ptp/ptp:instance-list/ptp:parent-ds/ptp:parent-port-identity/ptp:clock-identity" {
    deviate replace {
      type tailf:hex-list;
    }
  }
  deviation "/ptp:ptp/ptp:instance-list/ptp:parent-ds/ptp:grandmaster-identity" {
    deviate replace {
      type tailf:hex-list;
    }
  }
  deviation "/ptp:ptp/ptp:transparent-clock-default-ds/ptp:clock-identity" {
    deviate replace {
      type tailf:hex-list;
    }
  }
  deviation "/ptp:ptp/ptp:instance-list/ptp:default-ds/ptp:clock-identity" {
    deviate replace {
      type tailf:hex-list;
    }
  }

  /* Time Source Types. Enum is defined accordance to values in IEEE-1588 */
  deviation "/ptp:ptp/ptp:instance-list/ptp:time-properties-ds/ptp:time-source" {
    deviate replace {
      type enumeration {
        enum ATOMIC_CLOCK {
          value 16;
        }
        enum GPS {
          value 32;
        }
        enum TERRESTRIAL_RADIO {
          value 48;
        }
        enum PTP {
          value 64;
        }
        enum NTP {
          value 80;
        }
        enum HAND_SET {
          value 96;
        }
        enum OTHER {
          value 144;
        }
        enum INTERNAL_OSCILLATOR {
          value 160;
        }
      }
    }
  }

  deviation "/ptp:ptp/ptp:instance-list" {
    deviate add {
      max-elements 1;
    }
    description "MAX one profile is supported.";
  }

  deviation "/ptp:ptp/ptp:instance-list/ptp:default-ds/ptp:two-step-flag" {
    deviate add {
      default false;
    }
  }
  deviation "/ptp:ptp/ptp:instance-list/ptp:default-ds/ptp:slave-only" {
    deviate add {
      default false;
    }
  }
}
