module arcos-openconfig-acl-augments-deviations {
  yang-version 1.1;
  namespace "http://yang.arrcus.com/arcos/openconfig/acl/augments/deviations";
  prefix arc-oc-acl-aug-dev;

  import openconfig-acl {
    prefix oc-acl;
  }

  import arcos-openconfig-acl-augments {
    prefix arc-oc-acl-aug;
  }

  import openconfig-interfaces {
    prefix oc-if;
  }

  deviation "/oc-acl:acl/arc-oc-acl-aug:system-defined/arc-oc-acl-aug:acl-set" +
            "/arc-oc-acl-aug:acl-entries/arc-oc-acl-aug:acl-entry" +
            "/arc-oc-acl-aug:input-interface" {
    deviate not-supported;
    description "Do not support input-interface in this release";
  }

  deviation "/oc-acl:acl/arc-oc-acl-aug:bgp-flowspec/arc-oc-acl-aug:acl-set" +
            "/arc-oc-acl-aug:acl-entries/arc-oc-acl-aug:acl-entry" +
            "/arc-oc-acl-aug:input-interface" {
    deviate not-supported;
    description "Do not support input-interface in this release";
  }


  deviation "/oc-acl:acl/arc-oc-acl-aug:bgp-flowspec/arc-oc-acl-aug:acl-set" +
            "/arc-oc-acl-aug:acl-entries/arc-oc-acl-aug:acl-entry/arc-oc-acl-aug:config" +
            "/arc-oc-acl-aug:sequence-id" {
    deviate replace {
      type uint64;
    }
    description "increase to uint64 from uint32";
  }

  deviation "/oc-acl:acl/arc-oc-acl-aug:bgp-flowspec/arc-oc-acl-aug:acl-set" +
            "/arc-oc-acl-aug:acl-entries/arc-oc-acl-aug:acl-entry/arc-oc-acl-aug:state" +
            "/arc-oc-acl-aug:sequence-id" {
    deviate replace {
      type uint64;
    }
    description "increase to uint64 from uint32";
  }

  deviation "/oc-acl:acl/arc-oc-acl-aug:system-defined/arc-oc-acl-aug:acl-set" +
            "/arc-oc-acl-aug:acl-entries/arc-oc-acl-aug:acl-entry/arc-oc-acl-aug:config" +
            "/arc-oc-acl-aug:sequence-id" {
    deviate replace {
      type uint64;
    }
    description "increase to uint64 from uint32";
  }

  deviation "/oc-acl:acl/arc-oc-acl-aug:system-defined/arc-oc-acl-aug:acl-set" +
            "/arc-oc-acl-aug:acl-entries/arc-oc-acl-aug:acl-entry/arc-oc-acl-aug:state" +
            "/arc-oc-acl-aug:sequence-id" {
    deviate replace {
      type uint64;
    }
    description "increase to uint64 from uint32";
  }

  deviation "/oc-acl:acl/arc-oc-acl-aug:bgp-flowspec/arc-oc-acl-aug:acl-set" +
            "/arc-oc-acl-aug:acl-entries/arc-oc-acl-aug:acl-entry" +
            "/arc-oc-acl-aug:transport/arc-oc-acl-aug:config" {
    deviate not-supported;
    description "Deviate out config container from flowspec";
  }

  deviation "/oc-acl:acl/arc-oc-acl-aug:bgp-flowspec/arc-oc-acl-aug:acl-set" +
            "/arc-oc-acl-aug:acl-entries/arc-oc-acl-aug:acl-entry" +
            "/arc-oc-acl-aug:ipv6/arc-oc-acl-aug:config" {
    deviate not-supported;
    description "Deviate out config container from flowspec";
  }

  deviation "/oc-acl:acl/arc-oc-acl-aug:bgp-flowspec/arc-oc-acl-aug:acl-set" +
            "/arc-oc-acl-aug:acl-entries/arc-oc-acl-aug:acl-entry" +
            "/arc-oc-acl-aug:ipv4/arc-oc-acl-aug:config" {
    deviate not-supported;
    description "Deviate out config container from flowspec";
  }

  deviation "/oc-acl:acl/arc-oc-acl-aug:bgp-flowspec/arc-oc-acl-aug:acl-set" +
            "/arc-oc-acl-aug:acl-entries/arc-oc-acl-aug:acl-entry" +
            "/arc-oc-acl-aug:l2/arc-oc-acl-aug:config" {
    deviate not-supported;
    description "Deviate out config container from flowspec";
  }




  deviation "/oc-acl:acl/arc-oc-acl-aug:system-defined/arc-oc-acl-aug:acl-set" +
            "/arc-oc-acl-aug:acl-entries/arc-oc-acl-aug:acl-entry" +
            "/arc-oc-acl-aug:transport/arc-oc-acl-aug:config" {
    deviate not-supported;
    description "Deviate out config container from system-defined";
  }

  deviation "/oc-acl:acl/arc-oc-acl-aug:system-defined/arc-oc-acl-aug:acl-set" +
            "/arc-oc-acl-aug:acl-entries/arc-oc-acl-aug:acl-entry" +
            "/arc-oc-acl-aug:ipv6/arc-oc-acl-aug:config" {
    deviate not-supported;
    description "Deviate out config container from system-defined";
  }

  deviation "/oc-acl:acl/arc-oc-acl-aug:system-defined/arc-oc-acl-aug:acl-set" +
            "/arc-oc-acl-aug:acl-entries/arc-oc-acl-aug:acl-entry" +
            "/arc-oc-acl-aug:ipv4/arc-oc-acl-aug:config" {
    deviate not-supported;
    description "Deviate out config container from system-defined";
  }

  deviation "/oc-acl:acl/arc-oc-acl-aug:system-defined/arc-oc-acl-aug:acl-set" +
            "/arc-oc-acl-aug:acl-entries/arc-oc-acl-aug:acl-entry" +
            "/arc-oc-acl-aug:l2/arc-oc-acl-aug:config" {
    deviate not-supported;
    description "Deviate out config container from system-defined";
  }

  /*
   * For now block co-existence of main-interface and sub-interface ACLs
   */
  deviation "/oc-if:interfaces/oc-if:interface/oc-if:subinterfaces" +
            "/oc-if:subinterface/arc-oc-acl-aug:acl-service-policies" {
    deviate add {
      must "(boolean(current()/../../../arc-oc-acl-aug:acl-service-policies) != 'true')" {
        error-message "co-existence of interface and subinterface ACL, under same interface, not supported";
      }
    }
  }
}
