module arcos-bgp {
  yang-version 1.1;
  namespace "http://yang.arrcus.com/arcos/bgp";
  prefix arc-bgp;

  import arcos-common-types {
    prefix arc-common-types;
  }

  import arcos-bgp-types {
    prefix arc-bgp-types;
  }

  import openconfig-bgp-types {
    prefix oc-bgp-types;
  }

  import openconfig-network-instance {
    prefix oc-ni;
  }

  import ietf-inet-types {
    prefix oc-inet;
  }

  import openconfig-interfaces {
    prefix oc-if;
  }

  organization
    "Arrcus, Inc.";

  contact
    "Email: yang-support@arrcus.com";

  description
    "ArcOS BGP Data Model";

  revision 2019-08-20 {
    description "ArcOS 3.3.1";
  }


  grouping network-instance-options {
    leaf network-instance {
      description
        "ALL network-instances or the name or one network-instance";
      type union {
        type enumeration {
          enum ALL {
            description
              "All network-instances";
          }
        }
	//        type leafref {
	//          path "/oc-ni:network-instances/oc-ni:network-instance/oc-ni:name";
	//        }
      }
    }
  }

  grouping clear-bgp-options {
    leaf soft {
      type arc-bgp-types:bgp-route-refresh-type;
      description
        "BGP soft reset (route refresh)";
    }

    uses network-instance-options;
  }

  rpc clear-bgp-neighbor {
    description
      "Clear one or all BGP neighbor sessions from one or all
       network-instances. The clear command can be either hard
       reset or route refresh";

    input {
      leaf address {
        mandatory true;
        description
          "ALL BGP neighbors or the address of one BGP neighbor,
           either in IPv4 or IPv6";
        type union {
          type enumeration {
            enum ALL {
              description
                "All BGP neighbors";
            }
          }
          type oc-inet:ip-address;
	  //          type leafref {
	  //            path "/oc-if:interfaces/oc-if:interface/oc-if:name";
	  //          }
        }
      }

      uses clear-bgp-options;
    }

    output {
      uses arc-common-types:generic-rpc-response;
    }
  }

  rpc clear-bgp-afi-safi {
    description
      "Clear all BGP neighbor sessions with a particular AFI/SAFI in
       one or all network-instances. The clear command can be either
       hard reset or route refresh";

    input {
      leaf afi-safi-name {
        type identityref {
          base oc-bgp-types:AFI_SAFI_TYPE;
        }
        mandatory true;
        description
          "BGP AFI/SAFI name";
      }

      uses clear-bgp-options;
    }

    output {
      uses arc-common-types:generic-rpc-response;
    }
  }

  rpc clear-bgp-peer-group {
    description
      "Clear all BGP neighbor sessions in a peer-group. The clear command
       can be either hard reset or route refresh";

    input {
      leaf peer-group-name {
        type string;
        mandatory true;
        description
          "Name of the peer-group";
      }

      uses clear-bgp-options;
    }

    output {
      uses arc-common-types:generic-rpc-response;
    }
  }

  rpc clear-bgp-timestamps {
    description
      "Clear BGP convergence timestamps for one or all network-instances";

    input {
      uses network-instance-options;
    }

    output {
      uses arc-common-types:generic-rpc-response;
    }
  }

  rpc request-erpl-server-connection {
    description
      "Request BGP to re-initiate connection to eRPL server";

    output {
      uses arc-common-types:generic-rpc-response;
    }
  }

  rpc request-bgp-malloc-trim {
    description
      "Invoke malloc_trim library function to release memory that
       has already been freed";

    output {
      uses arc-common-types:generic-rpc-response;
    }
  }
}
