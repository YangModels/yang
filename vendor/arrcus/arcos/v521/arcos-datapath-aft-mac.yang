submodule arcos-datapath-aft-mac {
   yang-version "1.1";

   belongs-to "arcos-datapath-aft" {
     prefix "arcos-dp-aft";
   }

   import ietf-yang-types { prefix "yang"; }

   organization
     "XXXXX";

   contact
     "XXXXX";

   description
     "Submodule containing definitions of groupings for the abstract
     forwarding tables for L2NI.";

   revision "2023-03-30" {
     description
       "Initial version";
   }

   grouping aft-mac-structural {
     description
       "Structural grouping defining the schema for the flattened L2
       abstract forwarding table.";

     list mac-entry {
         key "mac-address vlan";
         description
           "Table of learned or statically configured MAC addresses and
           corresponding VLANs in the bridge domain";
 
         leaf mac-address {
             type leafref {
                path "../state/mac-address";
             }
             description
                "Reference to mac-address list key";
         }

         leaf vlan {
             type leafref {
               path "../state/vlan";
             }
             description
               "Reference to vlan list key";
         }

         container state {
           description
             "Operational state data for MAC table entries";

           leaf mac-address {
             type string;
             description
               "MAC address for the dynamic or static MAC table
                entry";
           }

           leaf vlan {
             type uint16;
             description
               "VLAN from which this MAC address was received";
           }

           leaf entry-type {
             type enumeration {
               enum STATIC {
                 description
                   "Statically programmed MAC table entry";
               }
               enum DYNAMIC {
                 description
                   "Dynamically learned MAC table entry";
               }
             }
             description
               "Indicates whether the entry was statically configured, or
                dynamically learned.";
           }

           leaf service-label {
             type uint32;
             description
                "Overlay service label for remotely learnt mac address";
           }

           leaf nexthop-id {
             type uint32;
             description
                "Underlay reachability for remotely learnt mac address";
           }

           leaf nexthop-type {
             type enumeration {
               enum SINGLE {
                 value 1;
               }
               enum ECMP {
                 value 2;
               }
               enum PROTECTED {
                 value 3;
               }
               enum VXLAN_NH {
                 value 4;
               }
             }
           }

           leaf interface {
             type string;
             description
               "Interface on which the mac is learnt";
           }
         }
     }
  }
}
