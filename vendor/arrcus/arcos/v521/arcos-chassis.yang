module arcos-chassis {
  namespace "http://yang.arrcus.com/arcos/chassis";

  prefix "arc-chassis";

  import arcos-platform { prefix arc-platform; }

  organization
    "Arrcus, Inc.";

    contact
        "Email: eng@arrcus.com";

  description
    "YANG data-model for Chassis details.";

    revision 2019-10-16 {
        description "ArcOS release ";
    }

  identity ARCOS_PLATFORM_TYPE {
    description
      "Base type for ARCOS platform";
  }

  identity COMPUTE_SERVER {
    base ARCOS_PLATFORM_TYPE;
    description
      "Compute Server";
  }
  identity X86_64_ACCTON_AS7926_40XKE_R0 {
    base ARCOS_PLATFORM_TYPE;
    description
      "Accton sysid x86-64-accton-as7926-40xke-r0";
  }
  identity X86_64_ACCTON_AS7926_40XKE_R0A {
    base ARCOS_PLATFORM_TYPE;
    description
      "Accton sysid x86-64-accton-as7926-40xke-r0a";
  }
  identity X86_64_ACCTON_AS7926_80XK_R0 {
    base ARCOS_PLATFORM_TYPE;
    description
      "Accton sysid x86-64-accton-as7926-80xk-r0";
  }
  identity VIRTUAL_CPS {
    base ARCOS_PLATFORM_TYPE;
    description
      "Virtual Emulation of CPS";
  }
  identity X86_64_ACCTON_AS9926_24D_R0 {
    base ARCOS_PLATFORM_TYPE;
    description
      "Delta sysid x86-64-accton-as9926-24d-r0";
  }
  identity X86_64_UFISPACE_S9705_48D_R7 {
    base ARCOS_PLATFORM_TYPE;
    description
      "Ufispace sysid x86-64-ufispace-s9705-48d-r7";
  }
  identity X86_64_UFISPACE_S9700_53DX_R9 {
    base ARCOS_PLATFORM_TYPE;
    description
      "Ufispace sysid x86-64-ufispace-s9700-53dx-r9";
  }
  identity X86_64_UFISPACE_S9710_76D_R0 {
    base ARCOS_PLATFORM_TYPE;
    description
      "Ufispace sysid x86-64-ufispace-s9710-76d-r0";
  }
  identity X86_64_CEL_REDSTONE_XP_R0 {
    base ARCOS_PLATFORM_TYPE;
    description
      "Celestica sysid x86-64-cel-redstone-xp-r0";
  }
  identity X86_64_QUANTA_IX8A_DNV_R0 {
    base ARCOS_PLATFORM_TYPE;
    description
      "Quanta sysid x86-64-quanta-ix8a-dnv-r0";
  }
  identity VIRTUAL_LC {
    base ARCOS_PLATFORM_TYPE;
    description
      "VM emulation of LC";
  }
  identity VIRTUAL_FC {
    base ARCOS_PLATFORM_TYPE;
    description
      "VM emulation of FC";
  }

  identity STANDALONE_LC {
    base ARCOS_PLATFORM_TYPE;
    description
      "Standalone line card platform";
  }

  identity ARCOS_NODE_TYPE {
    description
      "Base type for ARCOS node type";
  }

  identity LINE_CARD {
    base ARCOS_NODE_TYPE;
    description
      "Linecard Id";
  }
  identity FABRIC_CARD {
    base ARCOS_NODE_TYPE;
    description
      "Fabric card";
  }
  identity COMPUTE_CARD {
    base ARCOS_NODE_TYPE;
    description
      "Compute card";
  }
  identity CONNECTOR_CARD {
    base ARCOS_NODE_TYPE;
    description
      "Connector card";
  }

  grouping chassis-node-config {
    description
      "Top-level Chassis Node configuration parameters";

    leaf id {
      type string {
        length "1..128";
      }
      mandatory true;
      description "Node identification";
    }

    leaf slot-id {
      type uint32;
      mandatory true;
      description "Node's Slot Id";
    }

    leaf platform-type {
      type identityref {
        base ARCOS_PLATFORM_TYPE;
      }
      mandatory true;
      description "Nodes for platform type.";
    }

    leaf enabled {
      type boolean;
      default "true";
      description
        "This leaf contains the configured, desired state of the node";
    }
  }

  grouping chassis-node-config-top {
    description
      "Structural grouping for Chassis slot configuration and
      operational state data.";

    container nodes {
      description
        "Top level container for chassis nodes, including configuration.";
      list node {
        key "id";

        description
          "The list of named nodes on the chassis.";

        leaf id {
          type leafref {
            path "../config/id";
          }
          description
            "References the configured id of the node";

        }
        container config {
          description
            "Configurable items at the chassis node level";
          uses chassis-node-config;

        }
      }
    }
  }

  grouping chassis-node-state {
    description
      "Top-level Chassis Node configuration parameters";

    leaf id {
      type string;
      mandatory true;
      description "Node Id";
    }

    leaf node-type {
      type identityref {
        base ARCOS_NODE_TYPE;
      }
      description "Node type";
    }

    leaf platform-type {
      type identityref {
        base ARCOS_PLATFORM_TYPE;
      }
      description "Slots platform type";
    }

    leaf slot-id {
      type uint32;
      description "Node's slot identification";
    }

    leaf admin-status {
      type enumeration {
        enum UP {
          description
            "Ready to participate in chassis.";
        }
        enum DOWN {
          description
            "Not ready to participate in chassis.";
        }
      }
      description
        "This leaf contains the desired state of the slot";
    }

    leaf oper-status {
      type enumeration {
        enum UP {
          description
            "Node is up and part of the chassis.";
        }
        enum DOWN {
          description
            "Node is down.";
        }
        enum UNCLAIMED {
          description
            "Node is not part of the chassis.";
        }
      }
      description
        "This leaf contains the present state of the slot";
    }
  }

  grouping chassis-node-state-top {
    container nodes {
      config false;
      description
        "Top level container for chassis slots, including configuration
        and state data.";
      list node {
        key "id";

        description
          "The list of named nodes on the chassis.";

        leaf id {
          type leafref {
            path "../state/id";
          }
          description
            "References the id of the node";
        }

        container state {
          description
            "Operational state data at the chassis node level.";

          uses chassis-node-state;
        }
      }
    }
  }

  grouping chassis-top {
    description
      "Structural grouping for Chassis configuration and
      operational state data.";
    container chassis {
      description
        "Top level container for chassis, including configuration
        and state data.";
      container config {
        uses chassis-node-config-top;
      }
      container state {
        when "/arc-platform:platform/arc-platform:deployment-type = 'arc-platform:DISTRIBUTED'";
        config false;
        uses chassis-node-state-top;
      }
    }
  }

  uses chassis-top {
    description "Chassis slot configuration";
  }
}
