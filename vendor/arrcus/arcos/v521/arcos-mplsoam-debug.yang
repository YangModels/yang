/**
 * Filename: arcos-mpls-oam-debug.yang
 *
 * Description:
 * YANG data-model for MPLS-OAM Debugs Action
 *
 * Copyright 2020 by Arrcus, Inc.
 * All rights reserved.
 */

module arcos-mplsoam-debug {
  yang-version 1.1;
  namespace "http://yang.arrcus.com/arcos/mplsoam/debug";
  prefix arc-mplsoam-debug;

  organization
    "Arrcus, Inc.";

  contact
    "Lalit";

  description
    "YANG data-model for MPLSOAM Debugs definitions.";

  typedef mplsoam-debug-op {
    type enumeration {
      enum off {
        description
          "Disable debug";
      }
      enum on {
        description
          "Enable debug";
      }
    }
  }

  container mplsoam-debug {
    description
      "MPLSOAM debug control";

    action all {
      input {
        leaf op {
          type mplsoam-debug-op;
          mandatory true;
          description
            "Turn debug ON/OFF";
        }
      }
      output {
        leaf result {
          type string;
          description
            "The result of operation";
        }
      }
    }
  }
}
