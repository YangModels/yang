module arcos-openconfig-if-aggregate-deviations {
  yang-version 1.1;
  namespace "http://yang.arrcus.com/arcos/openconfig/interfaces/aggregate/deviations";
  prefix arc-oc-lag-dev;

  import openconfig-if-aggregate {
    prefix oc-lag;
  }
  import openconfig-interfaces {
    prefix oc-if;
  }
  import openconfig-lacp {
    prefix oc-lacp;
  }

  deviation "/oc-if:interfaces/oc-if:interface/oc-lag:aggregation" +
            "/oc-lag:config/oc-lag:lag-type"  {
    deviate add {
      default LACP;
      must "(current() != 'LACP') or " 
         + "(/oc-lacp:lacp/oc-lacp:interfaces/oc-lacp:interface[oc-lacp:name=current()/../../../oc-if:name])" {
          error-message "aggregation lag-type needs to be changed to STATIC under interface config";
      }
    }
  }
}
