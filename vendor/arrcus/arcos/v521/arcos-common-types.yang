module arcos-common-types {
  yang-version 1.1;
  namespace "http://yang.arrcus.com/arcos/common/types";
  prefix arc-common-types;

  organization
    "Arrcus, Inc.";

  contact
    "Email: yang-support@arrcus.com";

  description
    "ArcOS Common Types Data Model";

  revision 2019-08-20 {
    description "ArcOS 3.3.1";
  }

  typedef generic-status-code {
    type enumeration {
      enum SUCCESS {
        description
          "Operation Successful";
      }
      enum FAILURE {
        description
          "Operation Failed";
      }
    }
  }


  grouping generic-rpc-response {
    leaf status {
      type generic-status-code;
      description
        "Result of the operation";
    }
    leaf message {
      type string;
      description
        "Description of the result of the operation";
    }
  }
}
