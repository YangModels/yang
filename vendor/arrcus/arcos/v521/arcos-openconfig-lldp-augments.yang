module arcos-openconfig-lldp-augments {
  yang-version 1.1;
  namespace "http://yang.arrcus.com/arcos/openconfig/lldp/augments";
  prefix arc-oc-lldp-aug;

  import openconfig-lldp {
    prefix oc-lldp;
  }

  grouping lldp-l2-management-address {
    leaf management-address {
      type string;
      description
        "The Management Address is a mandatory TLV which identifies a
        network address associated with the local LLDP agent, which
        can be used to reach the agent on the port identified in the
        Port ID TLV.";
    }

    leaf management-address-type {
      type string;
      description
        "The enumerated value for the network address type
        identified in this TLV. This enumeration is defined in the
        'Assigned Numbers' RFC [RFC3232] and the
        ianaAddressFamilyNumbers object.";
    }
  }

  augment "/oc-lldp:lldp/oc-lldp:interfaces/oc-lldp:interface" +
          "/oc-lldp:neighbors/oc-lldp:neighbor/oc-lldp:state" {
    uses lldp-l2-management-address;
  }
}
