module arcos-features {
  yang-version 1.1;
  namespace "http://yang.arrcus.com/arcos/features";
  prefix arc-features;

  organization
    "Arrcus, Inc.";
  contact
    "Arrcus, Inc.
     2077 Gateway Place
     San Jose, CA 95110
     Tel: +1 (408) 884-1965
     E-mail: eng@arrcus.com";
     
  description
    "YANG data-model for feature name definitions

     Copyright (c) 2016-2022 by Arrcus, Inc.
     All rights reserved.";

  revision "2022-03-17" {
    description
      "Add feature name for WRED";
  }

  identity ARCOS_FEATURE {
    description
      "Base type for ARCOS features";
  }

  identity ARCOS_MPLS {
    base ARCOS_FEATURE;
    description
      "ArcOS implementation of MPLS";
  }

  identity ARCOS_QoS {
    base ARCOS_FEATURE;
    description
      "ArcOS implementation of QoS";
  }

  identity ARCOS_SUBIF {
    base ARCOS_FEATURE;
    description
      "ArcOS implementation of Subinterfaces";
  }

  identity ARCOS_SFLOW {
    base ARCOS_FEATURE;
    description
      "ArcOS implementation of Sflow";
  }

  identity ARCOS_RIOT {
    base ARCOS_FEATURE;
    description
      "ArcOS implementation of RIOT";
  }

  identity ARCOS_ICMP_SRC_REWRITE {
    base ARCOS_FEATURE;
    description
      "ArcOS implementation of ICMP source address rewrite";
  }

  identity ARCOS_MONITOR {
    base ARCOS_FEATURE;
    description
      "ArcOS implementation of Mirroring";
  }

  identity ARCOS_QOS_WRED {
    base ARCOS_FEATURE;
    description
      "ArcOS implementation of WRED for QoS";
  }

  identity ARCOS_FRONT_PANEL_ZTP {
    base ARCOS_FEATURE;
    description
      "ArcOS implementation of ZTP via Front Panel Intefaces.";
  }

  identity ARCOS_EXTERNAL_TCAM {
    base ARCOS_FEATURE;
    description
      "ArcOS implementation of external TCAM";
  }

  identity ARCOS_SRV6_EXT_TNL {
    base ARCOS_FEATURE;
    description
      "ArcOS implementation of optimization for high tunnel scale";
  }

  identity ARCOS_PTP_TRANSPARENT_CLOCK {
    base ARCOS_FEATURE;
    description
      "ArcOS implementation of ptp transparent clock";
  }

  identity ARCOS_PTP_BOUNDARY_CLOCK {
    base ARCOS_FEATURE;
    description
      "ArcOS implementation of ptp boundary clock";
  }

  identity ARCOS_MUP1 {
    base ARCOS_FEATURE;
    description
      "ArcOS implementation of MUP1";
  }

  container features {
    list feature {
      key "name";
      description
        "List of features";
      min-elements 1;

      leaf name {
        type identityref {
          base ARCOS_FEATURE;
        }
        description
          "Name of feature";
      }

      leaf supported {
        type boolean;
        mandatory true;
        description
          "Whether feature is supported or not";
      }
    }
  }
}
