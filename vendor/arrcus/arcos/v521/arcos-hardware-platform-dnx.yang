module arcos-hardware-platform-dnx {
  yang-version 1.1;
  namespace "http://yang.arrcus.com/arcos/hardware/platform/dnx";
  prefix arc-hw-platform-dnx;


  grouping linkscan-interval {
    leaf interval {
      description "Time interval in millseconds between each linkscan polling. Default 250 milliseconds";
        type uint32 {
          range "10..250";
         }
        units milliseconds;
        default 250;
    }
  }

  grouping dnx-linkscan-interval {
    description "Controls for tuning device specific load balancing configuration";

    container linkscan {
      description "Polling interval for Linkscan";
      uses linkscan-interval;
    }
  }
}
