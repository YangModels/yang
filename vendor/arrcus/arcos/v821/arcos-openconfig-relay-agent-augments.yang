module arcos-openconfig-relay-agent-augments {
  yang-version 1.1;
  namespace "http://yang.arrcus.com/arcos/openconfig/relay-agent/augments";
  prefix arc-oc-relay-aug;

  import ietf-inet-types {
    prefix inet;
  }

  import ietf-yang-types {
    prefix yang;
  }

  import openconfig-yang-types {
    prefix oc-yang;
  }

  import openconfig-relay-agent {
    prefix oc-relay;
  }

  import openconfig-interfaces {
    prefix oc-if;
  }

  import openconfig-network-instance {
    prefix oc-netinst;
  }

  import openconfig-network-instance-types {
    prefix oc-ni-types;
  }

  organization
    "Arrcus, Inc.";

  contact
    "Arrcus, Inc.
     2077 Gateway Place
     Suite 400
     San Jose, CA 95110

     E-mail: yang-support@arrcus.com";

  description
    "This module defines ArcOS augments to the
     OpenConfig relay-agent module.

     Copyright (c) 2022-2023 by Arrcus, Inc.
     All rights reserved.";

  revision 2023-03-24 {
    description
      "Added VRF configurations.";
  }

  revision 2023-02-24 {
    description
      "Added DHCPv6 option 79 (client link-layer address).";
  }

  revision 2022-09-12 {
    description
      "Added DHCPv6 counters, interface-id-format option;
      replaced 'servers' container with 'helper-address' list.
      Changed oc-yang:counter64 to yang:zero-based-counter64.";
  }

  revision 2022-07-21 {
    description
      "Added Option-82 Circuit ID format support";
  }

  augment "/oc-relay:relay-agent/oc-relay:dhcpv6/oc-relay:config" {
    leaf-list helper-address {
      max-elements 16;
      type inet:ipv6-address;
      description
        "IPv6 address of DHCPv6 server to relay requests towards";
    }
  }

  augment "/oc-relay:relay-agent/oc-relay:dhcpv6/oc-relay:config" {
    leaf use-interface-vrf {
      type boolean;
      default false;
      description
        "When enabled, the DHCPv6 relay agent uses the VRF the incoming
        L3 interface is assigned to in order to reach the DHCPv6 server(s)
        When disabled, the default VRF is used regardless of the incoming
        interface's VRF.";
    }
  }

  augment "/oc-relay:relay-agent/oc-relay:dhcpv6/oc-relay:state" {
    leaf-list helper-address {
      max-elements 16;
      type inet:ipv6-address;
      description
        "IPv6 address of DHCPv6 server to relay requests towards";
    }
  }

  augment "/oc-relay:relay-agent/oc-relay:dhcpv6/oc-relay:state" {
    leaf use-interface-vrf {
      type boolean;
      description
        "When enabled, the DHCPv6 relay agent uses the VRF the incoming
        L3 interface is assigned to in order to reach the DHCPv6 server(s)
        When disabled, the default VRF is used regardless of the incoming
        interface's VRF.";
    }
  }

  grouping relay-agent-dhcp-global-counters {
    description
      "DHCP relay agent global counters grouping";

    container counters {
      description
        "DHCP relay agent global counters";

      container state {

        config false;

        leaf received-requests {
          type yang:zero-based-counter64;
          description
            "Number of DHCP Requests received from a client";
        }
        leaf received-responses {
          type yang:zero-based-counter64;
          description
            "Number of DHCP Responses received from a server";
        }
        leaf relayed-requests {
          type yang:zero-based-counter64;
          description
            "Number of DHCP Requests relayed to a server";
        }
        leaf relayed-responses {
          type yang:zero-based-counter64;
          description
            "Number of DHCP Responses relayed to a client";
        }
        leaf total-drops {
          type yang:zero-based-counter64;
          description
            "Total Number of DHCP packets dropped";
        }
        leaf last-clear {
          type yang:date-and-time;
          description
            "Indicates the last time the counters were
             cleared.";
        }
      }
    }
  }


  grouping relay-agent-dhcp-global-drop-counters {
    description
      "DHCP relay agent global drop counters grouping";

    container drop-counters {
      description
        "DHCP relay agent global drop counters";

      container state {

        config false;

        leaf bad-giaddr {
          type yang:zero-based-counter64;
          description
            "Number of DHCP Responses with a giaddr that doesn't
             match any DHCP relay enabled interface";
        }
        leaf request-send-failure {
          type yang:zero-based-counter64;
          description
            "Number of DHCP Requests that failed to be sent to
             a server";
        }
        leaf response-send-failure {
          type yang:zero-based-counter64;
          description
            "Number of DHCP Responses that failed to be sent to
             a client";
        }
        leaf agent-option-missing {
          type yang:zero-based-counter64;
          description
            "Number of DHCP Responses received without an agent
             option, when requests are sent with one";
        }
        leaf agent-option-corrupt {
          type yang:zero-based-counter64;
          description
            "Number of DHCP Responses received with a corrupt agent
             option, when requests are sent with an agent option";
        }
        leaf circuit-id-missing {
          type yang:zero-based-counter64;
          description
            "Number of DHCP Responses with a an agent option that
             doesn't contain a circuit ID suboption, when requests
             are sent with an agent option";
        }
        leaf no-circuit-id-match {
          type yang:zero-based-counter64;
          description
            "Number of DHCP Responses with an agent option circuit
             ID that doesn't match any DHCP relay enabled
             interface's circuit ID";
        }
        leaf agent-option-add-error {
          type yang:zero-based-counter64;
          description
            "Number of DHCP Requests for which the agent option
             could not be added due to length";
        }
        leaf circuit-id-exists {
          type yang:zero-based-counter64;
          description
            "Number of DHCP Requests received that already contain
             an agent option with a circuit ID";
        }
        leaf parse-error {
          type yang:zero-based-counter64;
          description
            "Error in parsing. For example, options exceed the
             length of the packet";
        }
      }
    }
  }
 
  grouping relay-agent-dhcp-interface-counters {
    description
      "DHCP relay agent per interface counters grouping";

    container counters {
      description
        "DHCP relay agent per interface counters";

      container state {

        config false;

        leaf received-requests {
          type yang:zero-based-counter64;
          description
            "Number of DHCP Requests received from a client on
             the interface";
        }
        leaf relayed-requests {
          type yang:zero-based-counter64;
          description
            "Number of DHCP Requests from the interface that were
             relayed to a server";
        }
        leaf relayed-responses {
          type yang:zero-based-counter64;
          description
            "Number of DHCP Responses relayed to a client on the
             interface";
        }
        leaf drops {
          type yang:zero-based-counter64;
          description
            "Number of DHCP Requests from the interface that were
             dropped";
        }
        leaf last-clear {
          type yang:date-and-time;
          description
            "Indicates the last time the counters were
             cleared.";
        }
      }
    }
  }

  typedef circuit-id-formats {
    type enumeration {
      enum HOSTNAME_PORT {
        description
          "Generate the Circuit ID based on the relay agent's hostname
          and port the request arrived on";
      }
      enum PORT_VLAN {
        description
          "Generate the Circuit ID based on the port and VLAN ID
          the request arrived on";
      }
    }
    description
      "Format of the Agent Information option Circuit-ID generated";
  }

  grouping agent-information-ipv4-interface-config-ext {
    description
      "Extended configuration data for DCHP relay agent information option
      on IPv4 interfaces";

    leaf circuit-id-format {
      type circuit-id-formats;
      must "not(../oc-relay:circuit-id)" {
        error-message "Only one of circuit-id or circuit-id-format may be configured";
      }
      description
        "When configured for an interface, the Circuit ID of relayed packets
        will contain the chosen format";
    }
  }

  grouping agent-information-ipv4-common-config-ext {
    description
      "Extended common configuration data for IPv4 DCHP relay agent
      information option";

    leaf circuit-id-format {
      type circuit-id-formats;
      description
        "When configured the Circuit ID of relayed packets will contain the
        chosen format, unless overridden at the interface level";
    }
  }

  augment "/oc-relay:relay-agent/oc-relay:dhcp/oc-relay:config" {
    leaf-list helper-address {
      max-elements 16;
      type inet:ip-address;
      description
        "IPv4 address of DHCP server to relay requests towards";
    }
  }

  augment "/oc-relay:relay-agent/oc-relay:dhcp/oc-relay:config" {
    leaf use-interface-vrf {
      type boolean;
      default false;
      description
        "When enabled, the DHCP relay agent uses the VRF the incoming
        L3 interface is assigned to in order to reach the DHCP server(s)
        When disabled, the default VRF is used regardless of the incoming
        interface's VRF.";
    }
  }

  augment "/oc-relay:relay-agent/oc-relay:dhcp/oc-relay:state" {
    leaf-list helper-address {
      type inet:ip-address;
      description
        "IPv4 address of DHCP server to relay requests towards";
    }
  }

  augment "/oc-relay:relay-agent/oc-relay:dhcp/oc-relay:state" {
    leaf use-interface-vrf {
      type boolean;
      description
        "When enabled, the DHCP relay agent uses the VRF the incoming
        L3 interface is assigned to in order to reach the DHCP server(s)
        When disabled, the default VRF is used regardless of the incoming
        interface's VRF.";
    }
  }

  augment "/oc-relay:relay-agent/oc-relay:dhcp" {

    uses relay-agent-dhcp-global-counters;
    uses relay-agent-dhcp-global-drop-counters;
  }

  augment "/oc-relay:relay-agent/oc-relay:dhcp/oc-relay:interfaces" +
          "/oc-relay:interface" {
    uses relay-agent-dhcp-interface-counters;
  }
  
  augment "/oc-relay:relay-agent/oc-relay:dhcp/oc-relay:interfaces" +
          "/oc-relay:interface/oc-relay:config" {
    leaf server-vrf {
      type leafref {
        path "/oc-netinst:network-instances/oc-netinst:network-instance" +
             "/oc-netinst:config/oc-netinst:name";
      }
      must "/oc-netinst:network-instances" +
           "/oc-netinst:network-instance[oc-netinst:name=current()]" +
           "/oc-netinst:config/oc-netinst:type = 'oc-ni-types:L3VRF'" {
        error-message "network-instance must be of type L3VRF";
      }
      description
        "Name of the L3VRF network-instance to use to reach the DHCP server(s)
        for DHCP requests received on this interface. This overrides the use
        of the default VRF or the interface's VRF which is used when enabling
        the global 'use-interface-vrf' setting.";
    }
  }

  augment "/oc-relay:relay-agent/oc-relay:dhcp/oc-relay:interfaces" +
          "/oc-relay:interface/oc-relay:state" {
    leaf server-vrf {
      type string;
      description
        "Name of the L3VRF network-instance to used to reach the DHCP server(s)
        for DHCP requests received on this interface.";
    }
  }

  augment "/oc-relay:relay-agent/oc-relay:dhcpv6/oc-relay:interfaces" +
          "/oc-relay:interface/oc-relay:config" {
    leaf server-vrf {
      type leafref {
        path "/oc-netinst:network-instances/oc-netinst:network-instance" +
             "/oc-netinst:config/oc-netinst:name";
      }
      must "/oc-netinst:network-instances" +
           "/oc-netinst:network-instance[oc-netinst:name=current()]" +
           "/oc-netinst:config/oc-netinst:type = 'oc-ni-types:L3VRF'" {
        error-message "network-instance must be of type L3VRF";
      }
      description
        "Name of the L3VRF network-instance to use to reach the DHCPv6 server(s)
        for DHCPv6 requests received on this interface. This overrides the use
        of the default VRF or the interface's VRF which is used when enabling
        the global 'use-interface-vrf' setting.";
    }
  }

  augment "/oc-relay:relay-agent/oc-relay:dhcpv6/oc-relay:interfaces" +
          "/oc-relay:interface/oc-relay:state" {
    leaf server-vrf {
      type string;
      description
        "Name of the L3VRF network-instance used to reach the DHCPv6 server(s)
        for DHCPv6 requests received on this interface.";
    }
  }

  augment "/oc-relay:relay-agent/oc-relay:dhcp/oc-relay:interfaces" +
          "/oc-relay:interface/oc-relay:agent-information-option" +
          "/oc-relay:config" {
    uses agent-information-ipv4-interface-config-ext;
  }

  augment "/oc-relay:relay-agent/oc-relay:dhcp/oc-relay:interfaces" +
          "/oc-relay:interface/oc-relay:agent-information-option" +
          "/oc-relay:state" {
    uses agent-information-ipv4-interface-config-ext;
  }

  augment "/oc-relay:relay-agent/oc-relay:dhcp" +
          "/oc-relay:agent-information-option/oc-relay:config" {
    uses agent-information-ipv4-common-config-ext;
  }

  augment "/oc-relay:relay-agent/oc-relay:dhcp" +
          "/oc-relay:agent-information-option/oc-relay:state" {
    uses agent-information-ipv4-common-config-ext;
  }

  grouping relay-agent-dhcpv6-global-counters {
    description
      "DHCPv6 relay agent global counters grouping";

    container counters {
      description
        "DHCPv6 relay agent global counters";

      container state {

        config false;

        leaf received-requests {
          type yang:zero-based-counter64;
          description
            "Number of DHCPv6 Requests received from a client";
        }
        leaf received-responses {
          type yang:zero-based-counter64;
          description
            "Number of DHCPv6 Responses received from a server";
        }
        leaf relayed-requests {
          type yang:zero-based-counter64;
          description
            "Number of DHCPv6 Requests relayed to a server";
        }
        leaf relayed-responses {
          type yang:zero-based-counter64;
          description
            "Number of DHCPv6 Responses relayed to a client";
        }
        leaf total-drops {
          type yang:zero-based-counter64;
          description
            "Total Number of DHCPv6 packets dropped";
        }
        leaf last-clear {
          type yang:date-and-time;
          description
            "Indicates the last time the counters were
             cleared.";
        }
      }
    }
  }

  grouping relay-agent-dhcpv6-global-drop-counters {
    description
      "DHCPv6 relay agent global drop counters grouping";

    container drop-counters {
      description
        "DHCPv6 relay agent global drop counters";

      container state {

        config false;

        leaf bad-link-address {
          type yang:zero-based-counter64;
          description
            "Number of DHCPv6 Responses with a link-address that doesn't
             match any DHCPv6 relay enabled interface";
        }
        leaf request-send-failure {
          type yang:zero-based-counter64;
          description
            "Number of DHCPv6 Requests that failed to be sent to
             a server";
        }
        leaf response-send-failure {
          type yang:zero-based-counter64;
          description
            "Number of DHCPv6 Responses that failed to be sent to
             a client";
        }
        leaf interface-id-missing {
          type yang:zero-based-counter64;
          description
            "Number of DHCPV6 Responses with a an interface-id option that
             doesn't contain a interface ID suboption, when requests
             are sent with an interface-id option";
        }
        leaf no-interface-id-match {
          type yang:zero-based-counter64;
          description
            "Number of DHCPV6 Responses with an interface-id option interface
             ID that doesn't match any DHCPV6 relay enabled
             interface's interface ID";
        }
        leaf interface-id-add-error {
          type yang:zero-based-counter64;
          description
            "Number of DHCPv6 Requests for which the interface-id option
             could not be added due to length";
        }
        leaf parse-error {
          type yang:zero-based-counter64;
          description
            "Error in parsing. For example, options exceed the
             length of the packet";
        }
      }
    }
  }
 
  augment "/oc-relay:relay-agent/oc-relay:dhcpv6" {
    uses relay-agent-dhcpv6-global-counters;
    uses relay-agent-dhcpv6-global-drop-counters;
  }

  grouping relay-agent-dhcpv6-interface-counters {
    description
      "DHCPv6 relay agent per interface counters grouping";

    container counters {
      description
        "DHCPv6 relay agent per interface counters";

      container state {

        config false;

        leaf received-requests {
          type yang:zero-based-counter64;
          description
            "Number of DHCPv6 Requests received from a client on
             the interface";
        }
        leaf relayed-requests {
          type yang:zero-based-counter64;
          description
            "Number of DHCPv6 Requests from the interface that were
             relayed to a server";
        }
        leaf relayed-responses {
          type yang:zero-based-counter64;
          description
            "Number of DHCPv6 Responses relayed to a client on the
             interface";
        }
        leaf drops {
          type yang:zero-based-counter64;
          description
            "Number of DHCPv6 Requests from the interface that were
             dropped";
        }
        leaf last-clear {
          type yang:date-and-time;
          description
            "Indicates the last time the counters were
             cleared.";
        }
      }
    }
  }

  augment "/oc-relay:relay-agent/oc-relay:dhcpv6/oc-relay:interfaces" +
          "/oc-relay:interface" {
    uses relay-agent-dhcpv6-interface-counters;
  }
  
  typedef interface-id-formats {
    type enumeration {
      enum HOSTNAME_PORT {
        description
          "Generate the Interface ID based on the relay agent's hostname
          and port the request arrived on";
      }
      enum PORT_VLAN {
        description
          "Generate the Interface ID based on the port and VLAN ID
          the request arrived on";
      }
    }
    description
      "Format of the Interface-ID option generated";
  }

  grouping agent-options-ipv6-common-config-ext {
    description
      "Extended common configuration data for IPv6 DCHP relay agent options";

    leaf interface-id-format {
      type interface-id-formats;
      description
        "When configured the Interface ID of relayed packets will contain the
        chosen format, unless overridden at the interface level";
    }

    leaf enable-client-link-layer-address {
      type boolean;
      default false;
      description
        "Enables DHCPv6 OPTION_CLIENT_LINKLAYER_ADDR (79) to provide the
        client's link-layer address to the server.";
      reference
        "IETF RFC 6939 - Client Link-Layer Address Option in DHCPv6";
    }
  }

  augment "/oc-relay:relay-agent/oc-relay:dhcpv6" +
          "/oc-relay:options/oc-relay:config" {
    uses agent-options-ipv6-common-config-ext;
  }

  augment "/oc-relay:relay-agent/oc-relay:dhcpv6" +
          "/oc-relay:options/oc-relay:state" {
    uses agent-options-ipv6-common-config-ext;
  }

  grouping agent-options-ipv6-interface-config-ext {
    description
      "Extended configuration data for DCHP relay agent options
      on IPv6 interfaces";

    leaf interface-id-format {
      type interface-id-formats;
      must "not(../oc-relay:interface-id)" {
        error-message "Only one of interface-id or interface-id-format may be configured";
      }
      description
        "When configured for an interface, the Interface ID of relayed packets
        will contain the chosen format";
    }
  }

  augment "/oc-relay:relay-agent/oc-relay:dhcpv6/oc-relay:interfaces" +
          "/oc-relay:interface/oc-relay:options/oc-relay:config" {
    uses agent-options-ipv6-interface-config-ext;
  }

  augment "/oc-relay:relay-agent/oc-relay:dhcpv6/oc-relay:interfaces" +
          "/oc-relay:interface/oc-relay:options/oc-relay:state" {
    uses agent-options-ipv6-interface-config-ext;
  }

}
