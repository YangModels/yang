module arcos-openconfig-macsec-augments {
  yang-version 1.1;
  namespace "http://yang.arrcus.com/arcos/openconfig/macsec/augments";
  prefix arc-oc-macsec-aug;

  import openconfig-macsec {
    prefix oc-macsec;
  }

  organization
    "Arrcus, Inc.";

  contact
    "Arrcus, Inc.
     Customer Service
     Postal: 2077 Gateway Place
     San Jose, CA 95110
     Tel: +1 408 884-1965
     E-mail: yang-support@arrcus.com";

  description
    "This module defines augments for Arrcus
     implemention of the openconfig macsec model.

     Copyright (c) 2016-2024 by Arrcus, Inc.
     All rights reserved.";

  revision 2025-03-18 {
    description
      "Set default value for cipher suite and server state";
  }
  revision 2024-11-12 {
    description
      "AN (Association Number) display on the Macsec Interface";
  }

  revision 2024-05-10 {
    description
      "MKA participant template added inside interface";
  }

  identity cipher-suite-algorithm {
    description
      "Set Cipher suite(s) for SAK derivation";
  }

  identity GCM_AES_128 {
    base cipher-suite-algorithm;
    description
      "GCM-AES-128 Cipher Suite";
  }

  identity GCM_XPN_128 {
    base cipher-suite-algorithm;
    description
      "GCM-AES-XPN-128 Cipher Suite";
  }

  grouping algorithm {
    leaf macsec-cipher-suite-algorithm {
      type identityref {
        base "cipher-suite-algorithm";
      }
      default "GCM_AES_128";
      description
        "The cipher suite algorithm used for encryption of SAK packets.";
    }
  }

  grouping sak-remaining-time {
    leaf sak-rekey-left-over-time {
      type uint32 {
        range "0 | 30..65535";
      }
      description
        "SAK Rekey left over time in seconds.";
    }
  }

  grouping  macsec-mka-participant {
    leaf connectivity-association-key-name {
      type string {
        length "1..32";
      }
      description
        "The CKN information for the MKA participant.";
    }

    leaf connectivity-association-key {
      type string {
        length "1..16";
      }
      description
        "Indicates the CAK name to identify the Connectivity
         Association Key (CAK) which is the root key in the
         MACsec Key Agreement key hierarchy. All potential
         members of the CA use the same CAK.";
    }

    leaf key-server {
      type enumeration {
        enum enabled {
          value 1;
        }
        enum disabled {
          value 2;
        }
      }
      default "enabled";
      description
        "If this object is set to disable, then the KeyServer
        won`t be set in the Participant Entry Table.
        If enabled, Participant Key Server enable.";
    }
  }

  grouping mka-peer-list {
    leaf peer-mi {
      type string;
      description
        "The peer entry.s Member Identifier(MI) information in the peer list of this active.";
    }

    leaf peer-type {
      type enumeration {
        enum live-peer {
          value 1;
        }
        enum potential-peer {
          value 2;
        }
        enum sak-use-type {
          value 3;
        }
        enum distributed-sak-type {
          value 4;
        }
        enum distributed-cak-type {
          value 5;
        }
        enum kmd-type {
          value 6;
        }
        enum icv-indicator-type {
          value 255;
        }
      }
      description
        "The peer entry.s type in the peer list of this active participant in MKA protocol.";
    }
    
    leaf peer-mn {
      type int32;
      description
        "The peer entry.s Member Number(MN) information in the peer list of this active.";
    }

    leaf peer-sci {
      type string;
      description
        "The SCI(Secure Channel Identifier) information of the peer entry in the peer 
         list of this active participant in MKA protocol.";
    }

    leaf latest-an {
      type uint8;
      description
          "The current AN (Association Number) used to program SAK on the port.";
    }

    leaf old-an {
      type uint8;
      description
          "The previous AN (Association Number) used to program SAK on the port.";
    }
  }

  augment "/oc-macsec:macsec/oc-macsec:interfaces/oc-macsec:interface/oc-macsec:config" {
    uses macsec-mka-participant;
  }

  augment "/oc-macsec:macsec/oc-macsec:interfaces/oc-macsec:interface/oc-macsec:state" {
    uses macsec-mka-participant;
    uses mka-peer-list;
    uses sak-remaining-time;
  }

  augment "/oc-macsec:macsec/oc-macsec:mka/oc-macsec:policies/oc-macsec:policy/oc-macsec:config" {
    uses algorithm;
  }

  augment "/oc-macsec:macsec/oc-macsec:mka/oc-macsec:policies/oc-macsec:policy/oc-macsec:state" {
    uses algorithm;
  }
}
