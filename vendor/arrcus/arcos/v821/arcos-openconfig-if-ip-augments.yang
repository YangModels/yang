module arcos-openconfig-if-ip-augments {
  yang-version 1.1;
  namespace "http://yang.arrcus.com/arcos/openconfig/interfaces/ip/augments";
  prefix arc-oc-ip-aug;

  import openconfig-if-ip {
    prefix oc-ip;
  }

  import openconfig-interfaces {
    prefix oc-if;
  }

  import openconfig-yang-types {
    prefix oc-yang;
  }

  import ietf-yang-types {
    prefix ietf-yang;
  }

  import ietf-inet-types {
    prefix inet;
  }

  import openconfig-policy-types {
    prefix oc-pol-types;
  }

  revision 2025-01-06 {
    description
      "Adding VRRP prefix tracking configuration";
  }

  revision 2024-12-23 {
    description
      "Added the ARP/ND cache limits and count";
  }

  revision 2024-06-25 {
    description
      "Remove version configuration for IPv6 VRRP";
  }

  revision 2024-04-22 {
    description
      "Import IETF YANG types";
  }

  revision 2022-09-13 {
    description
      "Add mac-learning for L2 sub interfaces";
  }

  typedef vrrp-proto-version {
    type enumeration {
      enum VRRP_V2 {
        description "VRRP protocol version 2.";
      }
      enum VRRP_V3 {
        description "VRRP protocol version 3.";
      }
      enum VRRP_V2_V3 {
        description "VRRP protocol version 2 and 3.";
      }
    }
  }
  grouping ipv6-ra-config {
    description
      "Configuration parameters for IPv6 router advertisements.";

    leaf interval {
      type uint32 {
        range "4..1800";
      }
      default 600;
      units seconds;
      description
        "The interval between periodic router advertisement neighbor
        discovery messages sent on this interface expressed in
        seconds.";
    }

    leaf lifetime {
      type uint32 {
        range "0..9000";
      }
      units seconds;
      must 'current() = 0 or current() > ../interval' {
        error-message "If lifetime is not 0, it must be greater than interval";
      }
      description
        "The lifetime advertised in RA messages sent on this interface
         (in seconds), value 0 means don't use as default router.";
    }

    leaf suppress {
      type boolean;
      default false;
      description
        "When set to true, router advertisement neighbor discovery
        messages are not transmitted on this interface.";
    }

    leaf virtual-router-only {
      type boolean;
      default false;
      description
        "When set to true, router advertisement neighbor discovery
        messages are only sent for VRRP virtual-routers on this interface.";
    }

    leaf managed-config-flag {
      type boolean;
      default false;
      description
        "When set to true, router advertisement neighbor discovery
         messages are sent with the Managed address configuration flag set.";
    }

    leaf other-config-flag {
      type boolean;
      default false;
      description
        "When set to true, router advertisement neighbor discovery
         messages are sent with the Other configuration flag set.";
    }
  }

  grouping ipv6-ra-top {
    description
      "Top-level grouping for IPv6 router advertisements ";

    container router-advertisement {
      description
        "Configuration and operational state parameters relating to
        router advertisements.";

      container config {
        description
          "Configuration parameters relating to router advertisements
          for IPv6.";
        uses ipv6-ra-config;
      }

      container state {
        config false;
        description
          "Operational state parameters relating to router
           advertisements for IPv6.";
        uses ipv6-ra-config;
      }
    }
  }

  grouping ipv6-ra-addr-config {
    description
      "Per IPv6 address prefix configuration parameters for router advertisements.";

    leaf auto-config-flag {
      type boolean;
      default false;
      description
        "When set to true, router advertisement neighbor discovery
         messages for this address prefix are sent with the autonomous
         configurationflag set.";
    }
  }

  grouping ipv6-ra-addr-top {
    description
      "Top-level grouping for IPv6 per address prefix router advertisements";

    container router-advertisement {
      description
        "Configuration and operational state parameters relating to
        per address prefix router advertisements";

      container config {
        description
          "Configuration parameters relating to per address prefix
          router advertisements for IPv6.";
        uses ipv6-ra-addr-config;
      }

      container state {
        config false;
        description
          "Operational state parameters relating to per address prefix
          router advertisements for IPv6.";
        uses ipv6-ra-addr-config;
      }
    }
  }

  grouping vrrp-group-ag-state-top {
    description
      "Additional leafs for VRRP Group State ";

    leaf virtual-router-mode {
      type enumeration {
        enum MASTER {
          description "Virtual Router is in MASTER mode.";
        }
        enum BACKUP {
          description "Virtual Router is in BACKUP mode.";
        }
      }
      description
        "The mode of this specific Virtual Group
         on the current Virtual Router";
    }

    leaf advertisement-sent {
      type uint64;
      description
        "Number of VRRP advertisements sent for this VRRP group";
    }

    leaf advertisement-received {
      type uint64;
      description
        "Number of VRRP advertisements received for this VRRP group";
    }

    leaf advertisement-dropped {
      type uint64;
      description
        "Number of VRRP advertisements dropped for this VRRP group";
    }

    leaf virtual-mac-address {
      type ietf-yang:mac-address;
      description
        "VRRP virtual mac address. It is in the format 00-00-5E-00-01-{VRID}
         where VRID is the Virtual Router ID";
    }
  }

  grouping vrrp-prefix-tracking-config {
    leaf prefix {
      type string;
      description "prefix to be tracked";
    }
    leaf priority-cost {
      type uint8 {
        range "1..254";
      }
      description "priority-cost to be subtracted from vr priority";
    }
  }

  typedef vrrp-prefix-tracking-flags {
    type bits {
      bit NEW {
        position 0;
      }
      bit UPDATE {
        position 1;
      }
      bit STALE {
        position 2;
      }
      bit DOWNLOADED {
        position 3;
      }
      bit ACKED {
        position 4;
      }
      bit RESOLVED {
        position 5;
      }
      bit COST_UPDATE {
        position 6;
      }
      bit RIB_RESTART {
        position 7;
      }
    }
  }

  grouping vrrp-prefix-tracking-state {
    uses vrrp-prefix-tracking-config;
    leaf resolved {
      type boolean;
      description
        "Indicate if the prefix tracking is resolved";
    }
    leaf match-prefix {
      type inet:ip-prefix;
      description
        "The prefix that match the prefix tracking";
    }
    leaf identifier {
      type identityref {
        base "oc-pol-types:INSTALL_PROTOCOL_TYPE";
      }
      description
        "The protocol which is downloaded the tracking prefix";
    }
    leaf flags {
      type vrrp-prefix-tracking-flags;
      description
        "tracking flags";
    }
  }

  grouping vrrp-prefix-tracking-top {
    container prefix-trackings {
      list prefix-tracking {
        key "prefix";
        max-elements 10;
        leaf prefix {
          type leafref {
            path "../config/prefix";
          }
          description "tracking prefix";
        }
        must "./config/priority-cost" {
          error-message "priority-cost must be configured";
        }
        container config {
          description "prefix tracking configuration";
          uses vrrp-prefix-tracking-config;
        }
        container state {
          config false;
          description "prefix tracking state";
          uses vrrp-prefix-tracking-state;
        }
      }
    }
  }

  augment "/oc-if:interfaces/oc-if:interface/oc-if:subinterfaces" +
          "/oc-if:subinterface/oc-ip:ipv6" {
    uses ipv6-ra-top;
  }

  augment "/oc-if:interfaces/oc-if:interface/oc-if:subinterfaces" +
          "/oc-if:subinterface/oc-ip:ipv6/oc-ip:addresses/oc-ip:address" {
    uses ipv6-ra-addr-top;
  }

  grouping neighbor-config {
    description
      "Configuration parameters for neighbors.";
    leaf neighbor-timeout {
      description
        "neighbor time out in seconds.";
      type uint32 {
        range "60..65535";
      }
      units seconds;
      default 14400;
    }
    leaf neighbor-cache-limit {
      description
        "neighbor cache limit.";
      type uint32 {
        range "1..65535";
      }
    }
  }

  augment "/oc-if:interfaces/oc-if:interface/oc-if:subinterfaces" +
          "/oc-if:subinterface/oc-ip:ipv4/oc-ip:config" {
    uses neighbor-config;
  }

  augment "/oc-if:interfaces/oc-if:interface/oc-if:subinterfaces" +
          "/oc-if:subinterface/oc-ip:ipv4/oc-ip:state" {
    uses neighbor-config;
    leaf neighbor-cache-count {
      description
        "neighbor cache count.";
      type uint32;
    }
  }

  augment "/oc-if:interfaces/oc-if:interface/oc-if:subinterfaces" +
          "/oc-if:subinterface/oc-ip:ipv6/oc-ip:config" {
    uses neighbor-config;
  }

  augment "/oc-if:interfaces/oc-if:interface/oc-if:subinterfaces" +
          "/oc-if:subinterface/oc-ip:ipv6/oc-ip:state" {
    uses neighbor-config;
    leaf neighbor-cache-count {
      description
        "neighbor cache count.";
      type uint32;
    }
  }

  augment "/oc-if:interfaces/oc-if:interface/oc-if:subinterfaces" +
          "/oc-if:subinterface/oc-ip:ipv4/oc-ip:addresses/oc-ip:address" +
          "/oc-ip:vrrp/oc-ip:vrrp-group/oc-ip:config" {
    leaf vrrp-version {
      description
        "Version of VRRP version to be enabled for this VRRP group.";
      type vrrp-proto-version;
      default "VRRP_V3";
    }
  }

  augment "/oc-if:interfaces/oc-if:interface/oc-if:subinterfaces" +
          "/oc-if:subinterface/oc-ip:ipv4/oc-ip:addresses/oc-ip:address" +
          "/oc-ip:vrrp/oc-ip:vrrp-group" {
    uses vrrp-prefix-tracking-top;
  }

  augment "/oc-if:interfaces/oc-if:interface/oc-if:subinterfaces" +
          "/oc-if:subinterface/oc-ip:ipv6/oc-ip:addresses/oc-ip:address" +
          "/oc-ip:vrrp/oc-ip:vrrp-group" {
    uses vrrp-prefix-tracking-top;
  }

  augment "/oc-if:interfaces/oc-if:interface/oc-if:subinterfaces" +
          "/oc-if:subinterface/oc-ip:ipv4/oc-ip:addresses/oc-ip:address" +
          "/oc-ip:vrrp/oc-ip:vrrp-group/oc-ip:state" {
    leaf vrrp-version {
      description
        "Version of VRRP version to be enabled for this VRRP group.";
      type vrrp-proto-version;
    }
  }

  augment "/oc-if:interfaces/oc-if:interface/oc-if:subinterfaces" +
          "/oc-if:subinterface/oc-ip:ipv6/oc-ip:addresses/oc-ip:address" +
          "/oc-ip:vrrp/oc-ip:vrrp-group/oc-ip:state" {
    leaf vrrp-version {
      description
        "Version of VRRP version to be enabled for this VRRP group.";
      type vrrp-proto-version;
    }
  }


  augment "/oc-if:interfaces/oc-if:interface/oc-if:subinterfaces" +
          "/oc-if:subinterface/oc-ip:ipv4/oc-ip:addresses/oc-ip:address" +
          "/oc-ip:vrrp/oc-ip:vrrp-group/oc-ip:state" {
    uses vrrp-group-ag-state-top;
  }

  augment "/oc-if:interfaces/oc-if:interface/oc-if:subinterfaces" +
          "/oc-if:subinterface/oc-ip:ipv6/oc-ip:addresses/oc-ip:address" +
          "/oc-ip:vrrp/oc-ip:vrrp-group/oc-ip:state" {
    uses vrrp-group-ag-state-top;
  }

  augment "/oc-if:interfaces/oc-if:interface/oc-if:subinterfaces/" +
    "oc-if:subinterface/oc-ip:ipv4/oc-ip:addresses/oc-ip:address/oc-ip:config" {
    leaf label-index {
      type uint32;
      description
      "Label index - Parameter related to Segment Routing";
    }
  }

  augment "/oc-if:interfaces/oc-if:interface/oc-if:subinterfaces/" +
    "oc-if:subinterface/oc-ip:ipv4/oc-ip:addresses/oc-ip:address/oc-ip:state" {
    leaf label-index {
      type uint32;
      description
      "Label index - Parameter related to Segment Routing";
    }
  }

  augment "/oc-if:interfaces/oc-if:interface/oc-if:subinterfaces/" +
    "oc-if:subinterface/oc-ip:ipv6/oc-ip:addresses/oc-ip:address/oc-ip:config" {
    leaf label-index {
      type uint32;
      description
      "Label index - Parameter related to Segment Routing";
    }
  }

  augment "/oc-if:interfaces/oc-if:interface/oc-if:subinterfaces/" +
    "oc-if:subinterface/oc-ip:ipv6/oc-ip:addresses/oc-ip:address/oc-ip:state" {
    leaf label-index {
      type uint32;
      description
      "Label index - Parameter related to Segment Routing";
    }
  }

  augment "/oc-if:interfaces/oc-if:interface/oc-if:subinterfaces/" +
    "oc-if:subinterface/oc-ip:ipv4/oc-ip:addresses/oc-ip:address/oc-ip:config" {
    leaf secondary {
      type empty;
      must "(count(/oc-if:interfaces/oc-if:interface/oc-if:subinterfaces/oc-if:subinterface/oc-ip:ipv4/oc-ip:addresses/oc-ip:address) > 1)" {
          error-message "Cannot delete the primary IP address from interface as the secondary IP config exists";
      }
      description "Indicates whether the IP address is a primary or a secondary IP address";
    }
  }

  augment "/oc-if:interfaces/oc-if:interface/oc-if:subinterfaces/" +
    "oc-if:subinterface/oc-ip:ipv4/oc-ip:addresses/oc-ip:address/oc-ip:state" {
    leaf secondary {
      type empty;
      description "Indicates whether the IP address is a primary or a secondary IP address";
    }
  }

  grouping ipv6-link-local-address {
    description
      "IPv6 link-local address for the interface.";

    leaf ipv6-link-local {
      type inet:ipv6-address-no-zone;
      description
        "[adapted from IETF IP model RFC 7277]

         The IPv6 link-local address on the
         interface.";
    }
  }

  grouping dynamic-address-top {
    description
      "Subinterface data for logical interfaces
       associated with a physical interface.";

    container dynamic {
      config false;
      description
        "Enclosing container for the list of subinterfaces
         associated with a physical interface.";
      uses ipv6-link-local-address;
    }
  }

  augment "/oc-if:interfaces/oc-if:interface/oc-if:subinterfaces/" +
    "oc-if:subinterface/oc-if:state" {
    uses dynamic-address-top;
  }

  grouping l2-subinterface-config {
    leaf mac-learning {
      type boolean;
      default true;
      description
        "When this leaf is set to true, MAC learning is enabled for
        the subinterface, such that MAC addresses are learned
        from ingress frames and added to the FDB.";
    }
    container counters {
      leaf enabled {
        type boolean;
        default "false";
        description
          "Enable counter collection on the subinterface.";
      }
    }
  }

  grouping l2-subinterface-state {
    leaf mac-learning {
      type boolean;
      description
        "Operation value of mac learning for this subinterface";
    }
  }

  augment "/oc-if:interfaces/oc-if:interface/oc-if:subinterfaces/" +
          "oc-if:subinterface/oc-if:config" {
    uses l2-subinterface-config {
         when "current()/../oc-ip:ipv4/oc-ip:config/oc-ip:enabled = 'false' and " +
              "current()/../oc-ip:ipv6/oc-ip:config/oc-ip:enabled = 'false'";
         description
              "l2 subinterface configs";
    }
  }

  augment "/oc-if:interfaces/oc-if:interface/oc-if:subinterfaces/" +
          "oc-if:subinterface/oc-if:state" {
    uses l2-subinterface-state {
         when "current()/../oc-ip:ipv4/oc-ip:config/oc-ip:enabled = 'false' and " +
              "current()/../oc-ip:ipv6/oc-ip:config/oc-ip:enabled = 'false'";
         description
              "l2 subinterface state";
    }
  }
}
