submodule arcos-ospf-rib {

  yang-version "1.1";

  belongs-to arcos-ospf {
    prefix "arc-ospf";
  }

  import ietf-yang-types { prefix "yang"; }
  import ietf-inet-types { prefix "inet"; }
  import openconfig-interfaces { prefix "oc-if"; }
  import arcos-ospf-types { prefix "arc-ospf-types"; }

  // Include submodules
  include arcos-ospf-common;

  organization
    "Arrcus, Inc";

  contact
    "Arrcus, Inc.
     2077 Gateway Place
     Suite 400
     San Jose, CA 95110
     
     E-mail: yang-support@arrcus.com";

  description
    "This submodule provides OSPF configuration and operational
    state parameters that are related to OSPF routing tables.";

  revision "2020-01-01" {
    description
      "Initial version";
  }

  /*
   * Nexthops and Nexthop-sets
   */
  grouping ospf-nexthop-set-state {
    description
      "This grouping defines OSPF nexthop-set state information.";

    container state {
      description
        "This container defines OSPF nexthop-set state information.";

      leaf nexthop-set-id {
        type uint32;
        description
          "Unique identfier for the specific nexthop-set.";
      }

      leaf nexthop-count {
        type uint32;
        description
          "Number of nexthops in the nexthop-set.";
      }

      leaf reference-count {
        type uint32;
        description
          "Number of routes referring to this nexthop-set.";
      }
    }
  }

  grouping ospf-nexthop-set-nexthops {
    description
      "This grouping defines OSPF nexthop-set nexthops information.";

    container nexthops {
      description
        "This container defines OSPF nexthop-set nexthops information.";

      list nexthop {
        key "outgoing-interface nexthop-address";
        description
          "List OSPF route next hop information.";

        leaf outgoing-interface {
          type leafref {
            path "../state/outgoing-interface";
          }
          description
            "Reference to OSPF interface.";
        }

        leaf nexthop-address {
          type leafref {
            path "../state/nexthop-address";
          }
          description
            "Reference to OSPF nexthop address.";
        }

        container state {
          description
            "This container defines OSPF route nexthop state information.";

          leaf outgoing-interface {
            type oc-if:interface-id;
            description
              "The outgoing interface.";
          }

          leaf nexthop-address {
            type inet:ip-address;
            description
              "The nexthop address.";
          }
        }
      }
    }
  }

  grouping ospf-nexthop-sets-structure {
    description
      "This grouping defines OSPF global nexthop sets.";

    container nexthop-sets {
      config false;
      description
        "This container defines a list of OSPF nexthop sets.";

      list nexthop-set {
        key "nexthop-set-id";

        description
          "List of OSPF nexthop sets.";

        leaf nexthop-set-id {
          type leafref {
            path "../state/nexthop-set-id";
          }
          description
            "Unique identifier for the specific nexthop-set.";
        }

        uses ospf-nexthop-set-state;

        uses ospf-nexthop-set-nexthops;
      }
    }
  }

  /*
   * Routes and Paths
   */
  grouping ospf-route-state {
    description
      "This grouping defines OSPF route state.";

    container state {
      description
        "This container defines OSPF route state.";

      leaf path-count {
        type uint32;
        description
          "Number of paths in this route.";
      }

      leaf aggregate-range {
        type inet:ip-prefix;
        description
          "The aggregate range prefix to which this route
           is a contributor";
      }

      leaf-list route-flags {
        type identityref {
          base "arc-ospf-types:OSPF_ROUTE_FLAG";
        }
        description
          "Route flags";
      }
    }

    container bestpath {
      description
        "This container defines OSPF bestpath information.";

      leaf path-type {
        type identityref {
          base "arc-ospf-types:OSPF_ROUTE_TYPE";
        }
        description
          "The path type of the OSPF bestpath.";
      }

      leaf area-id {
        type arc-ospf-types:ospf-area-identifier;
        description
          "The area of the OSPF route. Valid for intra-area and
          inter-area route only";
      }

      leaf metric {
        type uint32;
        description
          "OSPF route metric.";
      }

      leaf type-2-metric {
        type uint32;
        description
          "OSPF route metric for external type-2 and NSSA type-2.";
      }

      leaf tag {
        type uint32;
        description
          "Tag value";
      }

      leaf forwarding-address {
        type inet:ip-address;
        description
          "The Forwarding-Address from the AS-External LSA";
      }

      container received-lsa {
        description
          "The LSA from which this path is learnt.";

        uses ospf-lsa-key-info;
      }

      container self-originated-lsa {
        description
          "The self-originated LSA that corresponds to this route.";

        uses ospf-lsa-key-info;
      }

      leaf-list path-flags {
        type identityref {
          base "arc-ospf-types:OSPF_PATH_FLAG";
        }
        description
          "Path flags";
      }

      container nexthop-set {
        description
          "The nexthop-set describing the nexthops of this route.";

        uses ospf-nexthop-set-state;

        uses ospf-nexthop-set-nexthops;
      }
    }
  }

  grouping ospf-prefixes-structure {
    description
      "This grouping defines OSPF prefixes.";

    container prefixes {
      config false;
      description
        "This container defines OSPF prefixes.";

      list prefix {
        key "prefix-key";

        description
          "List of the local system's OSPF prefixes information learned
          and calculated.";

        leaf prefix-key {
          type leafref {
            path "../prefix-identifier/prefix-key";
          }
          description
            "Reference to the prefix of the OSPF prefix.";
        }

        container prefix-identifier {
          description
            "This container defines prefix identifier.";

          leaf prefix-key {
            type inet:ip-prefix;
            description
              "OSPF IP prefix.";
          }
        }

        uses ospf-route-state;
      }
    }
  }

  grouping ospf-redistributed-prefixes-structure {
    description
      "This grouping defines OSPF redistributed prefixes.";

    container redistributed-prefixes {
      config false;
      description
        "This container defines OSPF redistributed prefixes.";

      list redistributed-prefix {
        key "prefix-key";

        description
          "List of the local system's OSPF redistributed prefixes information
          learned.";

        leaf prefix-key {
          type leafref {
            path "../redistributed-prefix-identifier/prefix-key";
          }
          description
            "Reference to the prefix of the OSPF redistributed prefix.";
        }

        container redistributed-prefix-identifier {
          description
            "This container defines redistributed prefix identifier.";

          leaf prefix-key {
            type inet:ip-prefix;
            description
              "OSPF redistributed IP prefix.";
          }
        }

        uses ospf-route-state;
      }
    }
  }

  grouping ospf-asbrs-structure {
    description
      "This grouping defines OSPF ASBRs.";

    container asbrs {
      config false;
      description
        "This container defines OSPF ASBRs.";

      list asbr {
        key "asbr-router-id";

        description
          "List of the local system's ASBR information learned
          and calculated.";

        leaf asbr-router-id {
          type leafref {
            path "../asbr-identifier/asbr-router-id";
          }
          description
            "Reference to the prefix of the OSPF route.";
        }

        container asbr-identifier {
          description
            "This container defines ASBR identifier.";

          leaf asbr-router-id {
            type yang:dotted-quad;
            description
              "ASBR Router ID.";
          }
        }

        uses ospf-route-state;
      }
    }
  }
}
