module arcos-hardware-platform-interface {
  yang-version 1.1;
  namespace "http://yang.arrcus.com/arcos/hardware/platform/interface";
  prefix arc-hw-platform-if;

  import iana-if-type {
    prefix ianaift;
  }

  import openconfig-interfaces {
    prefix oc-if;
  }

  import arcos-platform {
    prefix arc-platform;
  }

  import arcos-hardware-platform-xgs-interface {
    prefix arc-hw-platform-xgs-if;
  }

  import arcos-hardware-platform-pfc-interface {
    prefix arc-hw-platform-pfc-if;
  }

  import arcos-features {
    prefix arf;
  }

  organization
    "Arrcus, Inc.";

  contact
    "Arrcus, Inc.
     2077 Gateway Place
     Suite 400
     San Jose, CA 95110

     E-mail: yang-support@arrcus.com";

  description
    "This module contains definitions for the platform specific interface features in ArcOS

     Copyright (c) 2016-2023 by Arrcus, Inc.
     All rights reserved.";

  revision 2024-07-02 {
    description "Changes to include pfc configurations";
  }

  revision 2023-09-12 {
    description "Changes platform-interface when statement to use the interface name";
  }

  grouping platform-interface {
    container platform {
      uses arc-hw-platform-xgs-if:xgs-intf-mmu-profile;
      uses arc-hw-platform-pfc-if:pfc-intf-profile;
    }
  }

  augment "/oc-if:interfaces/oc-if:interface" {
    uses platform-interface {
      when "(((current()/oc-if:name != 'ma1') and " +
           "(starts-with(current()/oc-if:name, 'swp'))) and " +
           "((/arc-platform:platform/arc-platform:asic = 'arc-platform:BROADCOM_TRIDENT3') or " +
           "(/arc-platform:platform/arc-platform:asic = 'arc-platform:BROADCOM_TRIDENT4') or " +
           "(/arc-platform:platform/arc-platform:asic = 'arc-platform:BROADCOM_TOMAHAWK5') or " +
           "(/arc-platform:platform/arc-platform:asic = 'arc-platform:BROADCOM_TOMAHAWK')))";
    }
    description
      "Platform MMU queue profile";
  }
}
