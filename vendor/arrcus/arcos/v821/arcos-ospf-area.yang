submodule arcos-ospf-area {

  yang-version "1.1";

  belongs-to arcos-ospf {
    prefix "arc-ospf";
  }

  import arcos-ospf-types { prefix "arc-ospf-types"; }

  // Include submodules
  include arcos-ospf-statistics;
  include arcos-ospf-spf;
  include arcos-ospf-area-interface;
  include arcos-ospf-aggregate;

  organization
    "Arrcus, Inc";

  contact
    "Arrcus, Inc.
     2077 Gateway Place
     Suite 400
     San Jose, CA 95110
     
     E-mail: yang-support@arrcus.com";

  description
    "This submodule provides OSPF configuration and operational
    state parameters that are specific to the area context";

  revision "2020-01-01" {
    description
      "Initial version";
  }

  grouping ospf-area-config {
    description
      "Configuration parameters relating to an OSPF area";

    leaf identifier {
      type arc-ospf-types:ospf-area-identifier;
      description
        "An identifier for the OSPF area - described as either a
        32-bit unsigned integer, or a dotted-quad";
    }

    leaf area-type {
      type arc-ospf-types:ospf-area-type;
      description
        "Type of area.";
    }

    leaf advertise-summary-lsas {
      type boolean;
      description
        "Indicates if Summary LSAs can be advertised into this area.";
    }

    leaf stub-default-cost {
      type uint32;
      description
        "The metric to be used when advertising default route to
         the Stub area.";
    }
  }

  grouping ospf-area-state {
    description
      "Information relating to an OSPF area";

    leaf configured-interface-count {
      type uint32;
      description
        "Total number of interfaces configured in this area.";
    }

    leaf up-interface-count {
      type uint32;
      description
        "Total number of interfaces that are UP in this area.";
    }

    leaf neighbor-count {
      type uint32;
      description
        "The number of neighbors under this interface";
    }

    leaf exchange-neighbor-count {
      type uint32;
      description
        "The number of neighbors under this interface that are in
         EXCHANGE state";
    }

    leaf loading-neighbor-count {
      type uint32;
      description
        "The number of neighbors under this interface that are in
         LOADING state";
    }

    leaf full-neighbor-count {
      type uint32;
      description
        "The number of neighbors under this interface that are in
         FULL state";
    }
  }

  grouping ospf-area-structure {
    description
      "Structural grouping for configuration and operational state
      parameters that relate to an individual area";

    container config {
      description
        "Configuration parameters relating to an OSPF area";

      uses ospf-area-config;
    }

    container state {
      config false;
      description
        "Operational state parameters relating to an OSPF area";

      uses ospf-area-config;
      uses ospf-area-state;
    }

    container spf {
      description
        "This container defines area SPF configuration, state,
        statistics and logging.";

      container state {
        config false;
        description
          "Operational state of area level SPF computation";

        uses ospf-spf-state;
      }

      container last-spf-computation {
        config false;
        description
          "Operational state of the most recent SPF computation";

        uses ospf-spf-comp-state;
      }
    }

    container statistics {
      config false;
      description
        "Area statistics";

      uses ospf-pkt-statistics-structure;
      uses ospf-area-lsa-statistics-structure;
      uses ospf-comp-spf-statistics-structure;
    }

    uses ospf-summary-aggregates-structure;
    uses ospf-area-interface-structure;
  }

  grouping ospf-areas-structure {
    description
      "Structural grouping for configuration and operational state
      parameters that relate to OSPF areas";

    container areas {
      description
        "Configuration and operational state relating to an
	OSPF area.";

      list area {
        key "identifier";

        description
          "The OSPF areas within which the local system exists";

        leaf identifier {
          type leafref {
            path "../config/identifier";
          }
          description
            "A reference to the identifier for the area.";
        }

        uses ospf-area-structure;
      }
    }
  }
}
