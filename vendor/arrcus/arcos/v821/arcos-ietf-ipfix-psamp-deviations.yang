module arcos-ietf-ipfix-psamp-deviations {
  yang-version 1.1;
  namespace "http://yang.arrcus.com/arcos/ietf/ipfix/psamp/deviations";
  prefix arc-ietf-ipfix-psamp-dev;

  import arcos-ietf-ipfix-psamp-augments {
    prefix arc-ietf-ipfix;
  }

  import ietf-ipfix-psamp {
    prefix ietf-ipfix;
  }

  import ietf-inet-types {
    prefix inet;
  }

  organization
    "Arrcus, Inc.";

  contact
    "Email: eng@arrcus.com";

  description
    "This module defines deviation statements for Arrcus
     implemention of the IETF IPFIX Packet Sampling.";

  revision 2024-02-12 {
    description "Limit destination port range";
  }

  revision 2023-07-10 {
    description "Initial Revision";

    reference
      "RFC 6728: https://datatracker.ietf.org/doc/html/rfc6728";
  }

  deviation "/ietf-ipfix:ipfix/ietf-ipfix:collectingProcess" {
    deviate not-supported;
    description "Not supported in this release";
  }

  deviation "/ietf-ipfix:ipfix/ietf-ipfix:observationPoint" {
    deviate add {
      max-elements 1;
    }
  }

  deviation "/ietf-ipfix:ipfix/ietf-ipfix:selectionProcess" {
    deviate add {
      max-elements 1;
    }
  }

  deviation "/ietf-ipfix:ipfix/ietf-ipfix:exportingProcess" {
    deviate add {
      max-elements 5;
    }
  }

  deviation "/ietf-ipfix:ipfix/ietf-ipfix:selectionProcess/ietf-ipfix:selector" {
    deviate add {
      max-elements 1;
    }
  }

  deviation "/ietf-ipfix:ipfix/ietf-ipfix:observationPoint/ietf-ipfix:ifIndex" {
    deviate not-supported;
    description "Not supported in this release";
  }

  deviation "/ietf-ipfix:ipfix/ietf-ipfix:observationPoint/ietf-ipfix:ifName" {
    deviate not-supported;
    description "Not supported in this release";
  }

  deviation "/ietf-ipfix:ipfix/ietf-ipfix:observationPoint/ietf-ipfix:entPhysicalIndex" {
    deviate not-supported;
    description "Not supported in this release";
  }

  deviation "/ietf-ipfix:ipfix/ietf-ipfix:observationPoint/ietf-ipfix:entPhysicalName" {
    deviate not-supported;
    description "Not supported in this release";
  }

  deviation "/ietf-ipfix:ipfix/ietf-ipfix:selectionProcess/ietf-ipfix:selector/ietf-ipfix:packetsObserved" {
    deviate not-supported;
    description "Not applicable in this implementation";
  }

  deviation "/ietf-ipfix:ipfix/ietf-ipfix:selectionProcess/ietf-ipfix:selector/ietf-ipfix:packetsDropped" {
    deviate not-supported;
    description "Not applicable in this implementation";
  }

  deviation "/ietf-ipfix:ipfix/ietf-ipfix:selectionProcess/ietf-ipfix:selector/ietf-ipfix:Method/ietf-ipfix:selectAll" {
    deviate not-supported;
    description "Not supported in this release";
  }

  deviation "/ietf-ipfix:ipfix/ietf-ipfix:selectionProcess/ietf-ipfix:selector/ietf-ipfix:Method/ietf-ipfix:sampTimeBased" {
    deviate not-supported;
    description "Not supported in this release";
  }

  deviation "/ietf-ipfix:ipfix/ietf-ipfix:selectionProcess/ietf-ipfix:selector/ietf-ipfix:Method/ietf-ipfix:sampRandOutOfN" {
    deviate not-supported;
    description "Not supported in this release";
  }

  deviation "/ietf-ipfix:ipfix/ietf-ipfix:selectionProcess/ietf-ipfix:selector/ietf-ipfix:Method/ietf-ipfix:sampUniProb" {
    deviate not-supported;
    description "Not supported in this release";
  }

  deviation "/ietf-ipfix:ipfix/ietf-ipfix:selectionProcess/ietf-ipfix:selector/ietf-ipfix:Method/ietf-ipfix:filterMatch" {
    deviate not-supported;
    description "Not supported in this release";
  }

  deviation "/ietf-ipfix:ipfix/ietf-ipfix:selectionProcess/ietf-ipfix:selector/ietf-ipfix:Method/ietf-ipfix:filterHash" {
    deviate not-supported;
    description "Not supported in this release";
  }

  deviation "/ietf-ipfix:ipfix/ietf-ipfix:selectionProcess/ietf-ipfix:selector/ietf-ipfix:selectorDiscontinuityTime" {
    deviate not-supported;
    description "Not supported in this release";
  }

  deviation "/ietf-ipfix:ipfix/ietf-ipfix:selectionProcess/ietf-ipfix:selectionSequence" {
    deviate not-supported;
    description "Not supported in this release";
  }

  deviation "/ietf-ipfix:ipfix/ietf-ipfix:selectionProcess/ietf-ipfix:cache" {
    deviate not-supported;
    description "Not supported in this release";
  }

  deviation "/ietf-ipfix:ipfix/ietf-ipfix:cache" {
    deviate not-supported;
    description "Not supported in this release";
  }

  deviation "/ietf-ipfix:ipfix/ietf-ipfix:exportingProcess/ietf-ipfix:destination/ietf-ipfix:DestinationParameters/ietf-ipfix:sctpExporter" {
    deviate not-supported;
    description "Not supported in this release";
  }

  deviation "/ietf-ipfix:ipfix/ietf-ipfix:exportingProcess/ietf-ipfix:destination/ietf-ipfix:DestinationParameters/ietf-ipfix:udpExporter/ietf-ipfix:udpExporter/ietf-ipfix:indexOrName" {
    deviate not-supported;
    description "Not supported in this release";
  }

  deviation "/ietf-ipfix:ipfix/ietf-ipfix:exportingProcess/ietf-ipfix:destination/ietf-ipfix:DestinationParameters/ietf-ipfix:udpExporter/ietf-ipfix:udpExporter/ietf-ipfix:sendBufferSize" {
    deviate not-supported;
    description "Not supported in this release";
  }

  deviation "/ietf-ipfix:ipfix/ietf-ipfix:exportingProcess/ietf-ipfix:destination/ietf-ipfix:DestinationParameters/ietf-ipfix:udpExporter/ietf-ipfix:udpExporter/ietf-ipfix:rateLimit" {
    deviate not-supported;
    description "Not supported in this release";
  }

  deviation "/ietf-ipfix:ipfix/ietf-ipfix:exportingProcess/ietf-ipfix:destination/ietf-ipfix:DestinationParameters/ietf-ipfix:udpExporter/ietf-ipfix:udpExporter/ietf-ipfix:transportLayerSecurity" {
    deviate not-supported;
    description "Not supported in this release";
  }

  deviation "/ietf-ipfix:ipfix/ietf-ipfix:exportingProcess/ietf-ipfix:destination/ietf-ipfix:DestinationParameters/ietf-ipfix:udpExporter/ietf-ipfix:udpExporter/ietf-ipfix:templateRefreshTimeout" {
    deviate not-supported;
    description "Not supported in this release";
  }
  deviation "/ietf-ipfix:ipfix/ietf-ipfix:exportingProcess/ietf-ipfix:destination/ietf-ipfix:DestinationParameters/ietf-ipfix:udpExporter/ietf-ipfix:udpExporter/ietf-ipfix:optionsTemplateRefreshTimeout" {
    deviate not-supported;
    description "Not supported in this release";
  }

  deviation "/ietf-ipfix:ipfix/ietf-ipfix:exportingProcess/ietf-ipfix:destination/ietf-ipfix:DestinationParameters/ietf-ipfix:udpExporter/ietf-ipfix:udpExporter/ietf-ipfix:templateRefreshPacket" {
    deviate not-supported;
    description "Not supported in this release";
  }

  deviation "/ietf-ipfix:ipfix/ietf-ipfix:exportingProcess/ietf-ipfix:destination/ietf-ipfix:DestinationParameters/ietf-ipfix:udpExporter/ietf-ipfix:udpExporter/ietf-ipfix:optionsTemplateRefreshPacket" {
    deviate not-supported;
    description "Not supported in this release";
  }

  deviation "/ietf-ipfix:ipfix/ietf-ipfix:exportingProcess/ietf-ipfix:destination/ietf-ipfix:DestinationParameters/ietf-ipfix:tcpExporter" {
    deviate not-supported;
    description "Not supported in this release";
  }

  deviation "/ietf-ipfix:ipfix/ietf-ipfix:exportingProcess/ietf-ipfix:destination/ietf-ipfix:DestinationParameters/ietf-ipfix:fileWriter" {
    deviate not-supported;
    description "Not supported in this release";
  }
  deviation "/ietf-ipfix:ipfix/ietf-ipfix:exportingProcess/ietf-ipfix:options" {
    deviate not-supported;
    description "Not supported in this release";
  }

  deviation "/ietf-ipfix:ipfix/ietf-ipfix:exportingProcess/ietf-ipfix:destination/ietf-ipfix:DestinationParameters/ietf-ipfix:udpExporter/ietf-ipfix:udpExporter/ietf-ipfix:transportSession/ietf-ipfix:destinationPort" {
    deviate replace {
      type inet:port-number {
	      range "1024..65535";
      }
    }
  }

  deviation "/ietf-ipfix:ipfix/ietf-ipfix:exportingProcess/ietf-ipfix:destination/ietf-ipfix:DestinationParameters/ietf-ipfix:udpExporter/ietf-ipfix:udpExporter/ietf-ipfix:destinationPort" {
    deviate replace {
      type inet:port-number {
	      range "1024..65535";
      }
    }
  }

  deviation "/ietf-ipfix:ipfix/ietf-ipfix:observationPoint/ietf-ipfix:direction" {
    deviate replace {
      default ingress;
    }
  }

  deviation "/ietf-ipfix:ipfix/ietf-ipfix:exportingProcess/ietf-ipfix:destination" {
    deviate add {
      max-elements 1;
    }
  }

  deviation "/ietf-ipfix:ipfix/ietf-ipfix:exportingProcess/ietf-ipfix:exportMode" {
    deviate not-supported;
    description "Not supported in this release";
  }

  deviation "/ietf-ipfix:ipfix/ietf-ipfix:exportingProcess/ietf-ipfix:destination/ietf-ipfix:DestinationParameters/ietf-ipfix:udpExporter/ietf-ipfix:udpExporter/ietf-ipfix:maxPacketSize" {
    deviate not-supported;
    description "Not supported in this release";
  }

  deviation "/ietf-ipfix:ipfix/ietf-ipfix:selectionProcess/ietf-ipfix:selector/ietf-ipfix:Method/ietf-ipfix:sampCountBased/ietf-ipfix:sampCountBased/ietf-ipfix:packetInterval" {
    deviate add {
      default 1;
    }
    deviate replace {
      mandatory false;
    }
  }
}
