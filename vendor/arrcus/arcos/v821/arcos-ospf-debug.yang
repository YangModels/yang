/**
 * Filename: arcos-ospf-debug.yang
 *
 * Description:
 * YANG data-model for OSPF Debug Action
 *
 * Copyright 2020 by Arrcus, Inc.
 * All rights reserved.
 */

module arcos-ospf-debug {

  yang-version "1.1";

  namespace "http://yang.arrcus.com/arcos/ospf/debug";

  prefix arc-ospf-dbg;

  import ietf-inet-types { prefix oc-inet; }
  import openconfig-types { prefix "oc-types"; }
  import tailf-common { prefix tailf; }
  import openconfig-yang-types { prefix oc-yang; }
  import openconfig-policy-types { prefix oc-pol-types; }
  import arcos-debug { prefix arc-dbg; }

  organization
    "Arrcus, Inc.";

  contact
    "Arrcus, Inc.
     Customer Service
     Postal: 2077 Gateway Place
     San Jose, CA 95110
     Tel: +1 1XXX XXX-XXXX
     E-mail: xxx@arrcus.com";

  description
    "This module defines debug statements for Arrcus
     implemention of OSPF.";

  revision 2018-06-07 {
    description
      "Initial Revision
      ";

    reference
      "RFC 6020: YANG - A Data Modeling Language for the
       Network Configuration Protocol (NETCONF)";
  }

  /*
   * The top-level container for OSPFv2 debug.
   */
  grouping ospfv2-debug-top {
    container ospfv2 {
      description
        "This container defines instance-specific OSPFv2 debug information.";
      config false;

      uses arc-dbg:debug-component-top;
    }
  }

  /*
   * The top-level container for OSPFv3 debug.
   */
  grouping ospfv3-debug-top {
    container ospfv3 {
      description
        "This container defines instance-specific OSPFv3 debug information.";
      config false;

      uses arc-dbg:debug-component-top;
    }
  }

  /*
   * Add OSPFv2 debug items.
   */
  augment "/arc-dbg:debug/arc-dbg:network-instances/arc-dbg:network-instance" +
          "/arc-dbg:protocols/arc-dbg:protocol" {

    uses arc-ospf-dbg:ospfv2-debug-top {
      when "arc-dbg:identifier = 'oc-pol-types:OSPF'" {
        description
          "Include OSPFv2 debug information when the protocol is of type OSPF";
      }
      description
        "Debug information related to a specific instance of OSPFv2";
    }
  }

  /*
   * Add OSPFv3 debug items.
   */
  augment "/arc-dbg:debug/arc-dbg:network-instances/arc-dbg:network-instance" +
          "/arc-dbg:protocols/arc-dbg:protocol" {

    uses arc-ospf-dbg:ospfv3-debug-top {
      when "arc-dbg:identifier = 'oc-pol-types:OSPF3'" {
        description
          "Include OSPFv3 debug information when the protocol is of type OSPF3";
      }
      description
        "Debug information related to a specific instance of OSPFv3";
    }
  }
}
