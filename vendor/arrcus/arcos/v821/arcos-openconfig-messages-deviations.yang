module arcos-openconfig-messages-deviations {
  yang-version 1.1;
  namespace "http://yang.arrcus.com/arcos/openconfig/messages/deviations";
  prefix arc-oc-messages-dev;

  import openconfig-messages {
    prefix oc-messages;
  }

  deviation "/oc-messages:messages" {
    deviate not-supported;
    description "Not supported in this release";
  }
}
