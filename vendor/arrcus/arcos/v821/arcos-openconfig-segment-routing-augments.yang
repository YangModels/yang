module arcos-openconfig-segment-routing-augments {
  yang-version 1.1;
  namespace "http://yang.arrcus.com/arcos/openconfig/segment-routing/augments";
  prefix arc-oc-sr-aug;

  /*
   * Import basic things
   */
  import openconfig-network-instance { prefix oc-netinst; }
  import ietf-inet-types { prefix "inet"; }

  organization
    "Arrcus, Inc.";

  contact
    "Arrcus, Inc.
    2077 Gateway Place,
    San Jose, CA 95110
    Tel: +1 (408) 884-1965
    E-mail: yang-support@arrcus.com";

  description
    "This module defines augments for Arrcus
     implemention of the openconfig segment routing model.
     Copyright (c) 2023 by Arrcus, Inc.
     All rights reserved.";

  revision 2023-08-26 {
    description
      "Add support for Segment Routing Mapping Server";
  }

  revision "2023-03-15" {
    description
      "Remove augments for segment-routing srgb and srlb";
  }

  grouping mapping-prefix-ipv4-config {
    description
      "IPv4 Prefix for mapping.";
    leaf ipv4-prefix {
      type inet:ipv4-prefix;
      description
        "The IPv4 Prefix.";
    }
  }

  grouping mapping-prefix-ipv6-config {
    description
      "IPv6 Prefix for mapping.";
    leaf ipv6-prefix {
      type inet:ipv6-prefix;
      description
        "The IPv6 Prefix.";
    }
  }


  grouping mapping-sid-config {
    description
      "Common properties used in the SID Configuration.";

    leaf sid {
      mandatory true;
      type uint32 {
        range "0..1048575";
      }
      description
        "The SID value.";
    }

    leaf range {
      mandatory true;
      type uint16 {
        range "0..65535";
      }
      description
        "The SID range.";
    }
  }

  grouping mapping-local-id-config {
    description
      "Local ID configuration.";
    leaf local-id {
      type string;
      description
        "Unique identifier for the SR mapping.";
    }
  }

  grouping mapping-config-top {
    description
      "Configuration parameters relating to the SR Mapping Server.";

    container config {
      description
        "Config parameters relating to the SRMS.";
      uses mapping-local-id-config;
    }
    container state {
      config false;
      description
        "State parameters relating to the SRMS.";
      uses mapping-local-id-config;
    }

    container ipv4 {
      description
        "A list of Prefix to SID mappings.";
      container prefixes {
        list prefix {
          key "ipv4-prefix";
          leaf ipv4-prefix {
            type leafref {
              path "../config/ipv4-prefix";
            }
            description
              "Reference to the IPv4 Prefix for this mapping.";
          }
          container config {
            uses mapping-prefix-ipv4-config;
            uses mapping-sid-config;
          }
          container state {
            config false;
            uses mapping-prefix-ipv4-config;
            uses mapping-sid-config;
          }
        }
      }
    }

    container ipv6 {
      description
        "A list of Prefix to SID mappings.";
      container prefixes {
        list prefix {
          key "ipv6-prefix";
          leaf ipv6-prefix {
            type leafref {
              path "../config/ipv6-prefix";
            }
            description
              "Reference to the IPv6 Prefix for this mapping.";
          }
          container config {
            uses mapping-prefix-ipv6-config;
            uses mapping-sid-config;
          }
          container state {
            config false;
            uses mapping-prefix-ipv6-config;
            uses mapping-sid-config;
          }
        }
      }
    }
  }

  grouping srms-top {
    container srms {
      description
        "Configuration and operational state parameters relating to the
        Segment Routing mapping server.";

      container mappings {
        list mapping {
          key "local-id";
            description
              "A single definition of an SR Mapping List.";
          leaf local-id {
            type leafref {
              path "../config/local-id";
            }
            description
              "A reference to the identifier for the SR Mapping.";
          }
          uses mapping-config-top;
        }
      }
    }
  }

  augment "/oc-netinst:network-instances/oc-netinst:network-instance" +
          "/oc-netinst:segment-routing" {
    uses srms-top;
  }
}
