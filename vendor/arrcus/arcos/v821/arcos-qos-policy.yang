module arcos-qos-policy {
  yang-version 1.1;
  namespace "http://yang.arrcus.com/arcos/qos/policy";
  prefix arc-qos-pol;

  import arcos-policy {
    prefix arc-pol;
  }
  import arcos-policy-action {
    prefix arc-pol-actn;
  }
  import arcos-policy-action-types {
    prefix arc-pol-actn-types;
  }
  import arcos-qos-policy-action-types {
    prefix arc-qos-pol-actn-types;
  }
  import arcos-qos {
    prefix arc-qos;
  }
  import arcos-qos-classifier {
    prefix arc-qos-cfr;
  }
  import arcos-qos-random-detect {
    prefix arc-qos-red;
  }
  import arcos-platform {
    prefix arc-platform;
  }
  import openconfig-types{
    prefix oc-types;
  }
  import openconfig-system {
    prefix oc-sys;
  }
  import arcos-openconfig-system-augments {
    prefix arc-oc-sys-aug;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for qos policy definitions.
     Expanded from the generic policy data model (policy.yang)";

  revision 2024-12-20 {
    description "Increased the priority level range to 1..4";
  }

  revision 2024-11-07 {
    description "Modified the 'when' clause to enable CLI configuration on VM";
  }
  revision "2023-11-07" {
    description
      "Change type of ratio inside rate-excess-parameters to 0..128";
  }

  revision "2023-10-17" {
    description
      "Compensation for VoQs as an action for QoS policy on interfaces";
  }

  revision "2023-08-31" {
    description
      "Enabled either percentage or absolute value to be configured for Rate Min";
  }

  revision "2023-08-15" {
    description
      "Change type of ratio inside rate-excess-parameters to 0..63";
  }

  revision "2023-06-06" {
    description
      "Enabled committed rate unit percentage only on DNX platforms";
  }

  revision "2023-06-06" {
    description
      "Ensured that value is between 0 and 100 for unit percentage in policer";
  }

  revision "2023-03-06" {
    description
      "Enable MARK action support for XGS platforms";
  }

  grouping rate-max-parameters {
    description
      "maximum rate parameters";
    uses arc-pol-actn:traffic-rate;
  }

  grouping rate-max-config {
    description
      "maximum rate configuration parameters";
    container config {
      description
        "Configuration data";
      uses rate-max-parameters;
    }
  }

  grouping rate-max-state {
    description
      "maximum rate state information parameters";
    container state {
      config false;
      description
        "State Information.";
      uses rate-max-parameters;
    }
  }

  grouping rate-max-top {
    description
      "Top level container for fields in maximum rate configuration";
    container rate-max {
      description
        "maximum rate related fields";
      uses rate-max-state;
    }
  }


  grouping rate-min-parameters {
    description
      "minimum rate parameters";
    uses arc-pol-actn:traffic-rate;
  }

  grouping rate-min-config {
    description
      "minimum rate configuration parameters";
    container config {
      description
        "Configuration data";
      uses rate-min-parameters;
    }
  }

  grouping rate-min-state {
    description
      "minimum rate state information parameters";
    container state {
      config false;
      description
        "State Information.";
      uses rate-min-parameters;
    }
  }

  grouping rate-min-top {
    description
      "Top level container for fields in minimum rate configuration";
    container rate-min {
      description
        "minimum rate related fields";
      uses rate-min-state;
    }
  }


  grouping rate-excess-parameters {
    description
      "excess rate parameters";
    leaf ratio {
      type uint8 {
        range "0..128";
      }
      description
        "bandwidth remaining ratio";
    }
  }

  grouping rate-excess-config {
    description
      "excess rate configuration parameters";
    container config {
      description
        "Configuration data";
      uses rate-excess-parameters;
    }
  }

  grouping rate-excess-state {
    description
      "excess rate state information parameters";
    container state {
      config false;
      description
        "State Information.";
      uses rate-excess-parameters;
    }
  }

  grouping rate-excess-top {
    description
      "excess rate configuration parameters";
    container rate-excess {
      description
        "excess rate related fields";
      uses rate-excess-state;
    }
  }

  grouping compensation-parameters {
    description
      "compensation parameters";
    leaf value {
      type int32 {
        range "-128..127";
      }
      description
        "Providing compensation credits to TCs of interfaces";
    }
  }

  grouping compensation-top {
    description
      "compensation configuration parameters";
    container compensation {
      description
        "compensation related fields";

      container config {
        uses compensation-parameters;
        description
          "Config container for compensation parameters";
      }

      container state {
        config false;
        description
          "State container for compensation parameters";
        uses compensation-parameters;
      }
    }
  }


  grouping priority-parameters {
    description
      "priority parameters";
    leaf level {
      type uint8 {
        range "1..4";
      }
      description
        "priority level";
    }
  }

  grouping priority-config {
    description
      "priority configuration parameters";
    container config {
      description
        "Configuration data";
      uses priority-parameters;
    }
  }

  grouping priority-state {
    description
      "priority state information parameters";
    container state {
      config false;
      description
        "State Information.";
      uses priority-parameters;
    }
  }

  grouping priority-top {
    description
      "priority configuration parameters";
    container priority {
      description
        "priority related fields";
      uses priority-state;
    }
  }

  grouping random-detect-parameters {
    description
      "random-detect parameters";
    leaf profile {
      type leafref {
        path "/arc-qos:qos/arc-qos-red:random-detect/arc-qos-red:profile/arc-qos-red:name";
      }
      description
        "Name of a random-detect profile";
    }
  }

  grouping random-detect-config {
    description
      "random-detect configuration parameters";
    container config {
      description
        "Configuration data";
      uses random-detect-parameters;
    }
  }

  grouping random-detect-state {
    description
      "random-detect state information parameters";
    container state {
      config false;
      description
        "State Information.";
      uses random-detect-parameters;
    }
  }

  grouping random-detect-top {
    description
      "random-detect configuration parameters";
    container random-detect {
      description
        "random-detect related fields";
      uses random-detect-state;
    }
  }

  augment "/arc-qos:qos/policies/policy/classifiers/classifier/actions/action" {
    uses rate-min-top {
      when "./type = 'arc-qos-pol-actn-types:RATE_MIN'";
    }
  }

  augment "/arc-qos:qos/policies/policy/classifiers/classifier/actions/action/rate-min" {
    uses rate-min-config {
      refine "config/rate/value" {
        mandatory true;
        must "(current()/../unit != 'percentage') or " +
             "((current()/../unit = 'percentage') and " +
             " (current() >= 0 and current() <= 100))"{
          error-message "Value can only be between 0 and 100 for unit type of percentage";
        }
      }
    }
  }

  augment "/arc-qos:qos/policies/policy/classifiers/classifier/actions/action" {
    uses rate-max-top {
      when "./type = 'arc-qos-pol-actn-types:RATE_MAX'";
    }
  }

  augment "/arc-qos:qos/policies/policy/classifiers/classifier/actions/action/rate-max" {
    uses rate-max-config {
      refine "config/rate/value" {
        mandatory true;
        must "(current()/../unit != 'percentage') or " +
             "((current()/../unit = 'percentage') and " +
             " (current() >= 0 and current() <= 100))"{
          error-message "Value can only be between 0 and 100 for unit type of percentage";
        }
      }
    }
  }

  augment "/arc-qos:qos/policies/policy/classifiers/classifier/actions/action" {
    uses rate-excess-top {
      when "./type = 'arc-qos-pol-actn-types:RATE_EXCESS'";
    }
  }

  augment "/arc-qos:qos/policies/policy/classifiers/classifier/actions/action/rate-excess" {
    uses rate-excess-config;
  }

  augment "/arc-qos:qos/policies/policy/classifiers/classifier/actions/action" {
    uses priority-top {
      when "./type = 'arc-qos-pol-actn-types:PRIORITY'";
    }
  }

  augment "/arc-qos:qos/policies/policy/classifiers/classifier/actions/action/priority" {
    uses priority-config;
  }

  augment "/arc-qos:qos/policies/policy/classifiers/classifier/actions/action" {
    uses compensation-top {
      when "derived-from-or-self(./type, 'arc-qos-pol-actn-types:COMPENSATION')";
    }
  }

  augment "/arc-qos:qos/policies/policy/classifiers/classifier/actions/action" {
    uses random-detect-top {
      when "./type = 'arc-qos-pol-actn-types:RANDOM_DETECT'";
    }
  }

  augment "/arc-qos:qos/policies/policy/classifiers/classifier/actions/action/random-detect" {
    uses random-detect-config;
  }


  augment "/arc-qos:qos/policies/policy/classifiers/classifier/actions"
        + "/action" {
    uses arc-pol-actn:mark-top {
      when "./type = 'arc-pol-actn-types:MARK'";
    }
  }

  augment "/arc-qos:qos/policies/policy/classifiers/classifier/actions"
        + "/action/mark" {
    uses arc-pol-actn:mark-config;
  }

  augment "/arc-qos:qos/policies/policy/classifiers/classifier/actions"
        + "/action/mark/config" {
    uses arc-pol-actn:mark-local-tc-top;
  }

  augment "/arc-qos:qos/policies/policy/classifiers/classifier/actions"
        + "/action/mark/config" {
    uses arc-pol-actn:mark-local-tc-drop-precedence-top;
  }


  augment "/arc-qos:qos/policies/policy/classifiers/classifier/actions"
        + "/action/mark/state" {
    uses arc-pol-actn:mark-local-tc-top;
  }

  augment "/arc-qos:qos/policies/policy/classifiers/classifier/actions"
        + "/action/mark/state" {
    uses arc-pol-actn:mark-local-tc-drop-precedence-top;
  }


  augment "/arc-qos:qos/policies/policy/classifiers/classifier/actions"
        + "/action" {
    uses arc-pol-actn:police-top {
      when "./type = 'arc-pol-actn-types:POLICE'";
    }
  }

  augment "/arc-qos:qos/policies/policy/classifiers/classifier/actions"
        + "/action/police" {
    uses arc-pol-actn:police-config {
      refine "config/committed/rate/value" {
        must "(current()/../unit != 'percentage') or " +
             "((current()/../unit = 'percentage') and " +
             " (current() >= 0 and current() <= 100))"{
          error-message "Value can only be between 0 and 100 for unit type of percentage";
        }
        description
          "rate value in the unit of bps, kbps, mbps, gbps or percentage of the interface bandwidth";
      }

      refine "config/committed/rate/unit" {
        must "current() != 'percentage' or " +
             "((current() = 'percentage') and " +
             " ((/arc-platform:platform/arc-platform:family = 'arc-platform:BROADCOM_DNX') or " +
             "  (/arc-platform:platform/arc-platform:deployment-type = 'arc-platform:DISTRIBUTED') or " +
             "  (/oc-sys:system/arc-oc-sys-aug:cli/arc-oc-sys-aug:config/arc-oc-sys-aug:unhide-unsupported-cli = 'true')))" {
          error-message "committed rate unit not supported on qos";
        }
      }

      refine "config/committed/burst/value" {
        description
          "burst value in the unit of bytes";
      }
      refine "config/conform/action-type" {
        must "current() = 'arc-pol-actn-types:TRANSMIT'" {
          error-message "action type not supported for qos policer";
        }
      }
      refine "config/exceed/action-type" {
        must "current() = 'arc-pol-actn-types:DROP'" {
          error-message "action type not supported for qos policer";
        }
      }
      refine "config/violate/action-type" {
        must "current() = 'arc-pol-actn-types:DROP'" {
          error-message "action type not supported for qos policer";
        }
      }
    }
  }


  grouping qos-policy-top {
    description
      "Top-level container for QoS specific policy database";
    uses arc-pol:policies-top {
      refine "policies/policy/classifiers/classifier" {
        min-elements 1;
        max-elements 1000;
      }
      refine "policies/policy/classifiers/classifier/actions/action/type" {
        must "current() = 'arc-qos-pol-actn-types:PRIORITY' or "
           + "current() = 'arc-qos-pol-actn-types:RATE_MIN' or "
           + "current() = 'arc-qos-pol-actn-types:RATE_EXCESS' or "
           + "current() = 'arc-qos-pol-actn-types:RATE_MAX' or "
           + "current() = 'arc-qos-pol-actn-types:COMPENSATION' or "
           + "current() = 'arc-pol-actn-types:POLICE' or "
           + "((current() = 'arc-qos-pol-actn-types:RANDOM_DETECT') and "
           + " ((/arc-platform:platform/arc-platform:family = 'arc-platform:BROADCOM_XGS') or "
           + "  (/arc-platform:platform/arc-platform:family = 'arc-platform:BROADCOM_DNX') or "
           + "  (/arc-platform:platform/arc-platform:family = 'arc-platform:BROADCOM_DNX_JPLUS') or "
           + "  (/arc-platform:platform/arc-platform:deployment-type = 'arc-platform:DISTRIBUTED') or "
           + "  (/oc-sys:system/arc-oc-sys-aug:cli/arc-oc-sys-aug:config/arc-oc-sys-aug:unhide-unsupported-cli = 'true'))) or "
           + "((current() = 'arc-pol-actn-types:MARK') and "
           + " ((/arc-platform:platform/arc-platform:family = 'arc-platform:BROADCOM_DNX') or "
           + "  (/arc-platform:platform/arc-platform:family = 'arc-platform:BROADCOM_XGS') or "
           + "  (/arc-platform:platform/arc-platform:deployment-type = 'arc-platform:DISTRIBUTED') or "
           + "  (/oc-sys:system/arc-oc-sys-aug:cli/arc-oc-sys-aug:config/arc-oc-sys-aug:unhide-unsupported-cli = 'true')))" {
          error-message "action type not supported for qos";
        }
      }
    }
  }

  augment "/arc-qos:qos" {
    uses qos-policy-top;
  }
}
