module arcos-interfaces-breakout {
  yang-version 1.1;
  namespace "http://yang.arrcus.com/arcos/interfaces/breakout";
  prefix arc-if-brkout;

  revision 2024-08-08 {
    description "Added 400gx2 support";
  }

  revision 2023-10-10 {
    description "Add slot-id range ";
  }

  container break-out {
    description
        "Configure physical port break-out";
    list slot {
      key "slot-id";
        description "List of slots (corresponding to LCs) eligible to be configured for breakout";
      leaf slot-id {
        type uint32 {
          range 0..99;
        }
        description "individual slot-id of a given LC";
      }
      list ports {
       description "port number to break-out";
       key "port";
        leaf port {
          type uint16;
          description "port number";
        }
        leaf mode {
          type enumeration {
            enum 10gx4 {
              value 1;
            }
            enum 25gx4 {
              value 2;
            }
            enum 40gx2 {
              value 3;
            }
            enum 50gx2 {
              value 4;
            }
            enum 10gx8 {
              value 5;
            }
            enum 25gx8 {
              value 6;
            }
            enum 50gx4 {
              value 7;
            }
            enum 100gx4 {
              value 8;
            }
            enum 100gx2 {
              value 9;
            }
            enum 200gx2 {
              value 10;
            }
            enum 10gx2 {
              value 11;
            }
            enum 400gx2 {
              value 12;
            }
            enum 200gx4 {
              value 13;
            }
            enum 100gx8 {
              value 14;
            }
          }
          mandatory true;
          description "breakout type(speed x number of ports)";
        }
      }
    }
  }
}
