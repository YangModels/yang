module arcos-isis-debug {
  yang-version 1.1;
  namespace "http://yang.arrcus.com/arcos/isis/debug";
  prefix arc-isis-dbg;

  import openconfig-policy-types {
    prefix oc-pol-types;
  }

  import arcos-debug {
    prefix arc-dbg;
  }

  grouping isis-debug-filters {
    uses arc-dbg:sysid-match-filter {
      when "item-name = 'adjacency'" +
           " or item-name = 'lsp'" +
           " or item-name = 'snp'";
    }

    uses arc-dbg:intf-match-filter {
      when "item-name = 'adjacency'" +
           " or item-name = 'iih'" +
           " or item-name = 'interface'" +
           " or item-name = 'packet'" +
           " or item-name = 'bfd'";
    }

    uses arc-dbg:ip-prefix-match-filter {
      when "item-name = 'rib'" +
           " or item-name = 'redist-rib'";
    }
  }

  grouping isis-debug-top {
    container isis {
      description
        "This container defines instance-specific ISIS debug information.";
      config false;

      uses arc-dbg:debug-component-top;
    }
  }

  augment "/arc-dbg:debug/arc-dbg:network-instances/arc-dbg:network-instance" +
          "/arc-dbg:protocols/arc-dbg:protocol" {

    uses isis-debug-top {
      when "arc-dbg:identifier = 'oc-pol-types:ISIS'" {
        description
          "Include IS-IS debug information when the protocol is of type
          IS-IS";
      }
      description
        "Debug information related to a specific instance of IS-IS.";
    }
  }

  augment "/arc-dbg:debug/arc-dbg:network-instances/arc-dbg:network-instance" +
          "/arc-dbg:protocols/arc-dbg:protocol/arc-isis-dbg:isis" +
          "/arc-isis-dbg:component-debug-items" {
    uses isis-debug-filters;
  }
}
