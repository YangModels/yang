module arcos-clear-voq {

  yang-version "1.1";

  namespace "http://yang.arrcus.com/arcos/clear/voq";

  prefix "arc-clr-voq";

  import tailf-common {
    prefix tailf;
  }
  import arcos-platform {prefix arc-platform;}
  import arcos-datapath-types { prefix "arcos-dp-types"; }
  import arcos-datapath-aft { prefix "arcos-aft"; }
  import arcos-datapath-nexthop { prefix "arcos-nh"; }
  import arcos-datapath-tunnel { prefix "arcos-tnl"; }
  import arcos-datapath-queues { prefix "arcos-queues"; }
  import arcos-datapath-asic { prefix "arcos-asic"; }
  import arcos-common-types { prefix arc-common-types; }
  import arcos-datapath { prefix arcos-dp; }
  import openconfig-interfaces { prefix "oc-if"; }
  import arcos-runtime {
    prefix arc-runtime;
  }

  organization
    "Arrcus, Inc";

  contact
    "Arrcus, Inc.
     2077 Gateway Place
     Suite 400
     San Jose, CA 95110
     E-mail: yang-support@arrcus.com";

  description
    "A model describing the various datapath instances used for clear command. A
     datapath instance is an entity that deals with packet processing at
     some level. Examples are network processors, application specific
     integrated circuits (ASICs), software forwarding instances and so
     on. Each datapath instance may be responsible for one more functions like
     packet forwarding, packet filtering (ACLs), QoS, tunnel encapsulations
     and so on. This model defines a clear datapath instance only for clearing voq counters.
     Copyright (c) 2023 by Arrcus, Inc.
     All rights reserved.";

  revision "2025-04-13" {
    description
      "Fixing VOQ clear for multi-unit systems";
  }

  revision "2024-07-09" {
    description
      "Enable support for VDR";
  }

  grouping voq-datapath {
    leaf name {
      tailf:cli-drop-node-name;
      mandatory true;
      type leafref {
        path "/arcos-dp:datapath-instances/arcos-dp:datapath-instance/arcos-dp:name";
      }
    }
  }

  grouping voq-top {
      container voq {
      action datapath { 
        input {
          uses voq-datapath {
            when "/arc-platform:platform/arc-platform:deployment-type != 'arc-platform:DISTRIBUTED'";
          }
          leaf interface {
            mandatory true;
            type leafref {
              path "/oc-if:interfaces/oc-if:interface/oc-if:config/oc-if:name";
            }
          }
        }
        output {
          leaf result {
            type string;
            description "The status of operation";
          }
          leaf result_code {
            type boolean;
            description "The status code of operation";
          }
        }
      }
    }
  }


  augment "/arc-runtime:runtime-instances" +
          "/arc-runtime:runtime-instance" {
     uses voq-top;
  }
  uses voq-top {
    when "derived-from-or-self(/arc-platform:platform/arc-platform:family, 'arc-platform:BROADCOM_DNX') or "
    + "derived-from-or-self(/arc-platform:platform/arc-platform:asic, 'arc-platform:BROADCOM_TRIDENT3') or "
    + "derived-from-or-self(/arc-platform:platform/arc-platform:asic, 'arc-platform:BROADCOM_TOMAHAWK5')";
  }
}
