module arcos-openconfig-rib-bgp-augments-deviations {
  yang-version 1.1;
  namespace "http://yang.arrcus.com/arcos/openconfig/rib/bgp/augments/deviations";
  prefix arc-oc-rib-bgp-aug-dev;

  import arcos-openconfig-rib-bgp-augments {
    prefix arc-oc-rib-bgp-aug;
  }

  import openconfig-network-instance {
    prefix oc-ni;
  }

  deviation "/oc-ni:network-instances/oc-ni:network-instance" +
            "/oc-ni:protocols/oc-ni:protocol" +
            "/oc-ni:bgp/oc-ni:rib" +
            "/oc-ni:afi-safis/oc-ni:afi-safi" +
            "/arc-oc-rib-bgp-aug:ipv4-label-unicast/arc-oc-rib-bgp-aug:neighbors" +
            "/arc-oc-rib-bgp-aug:neighbor/arc-oc-rib-bgp-aug:state" +
            "/arc-oc-rib-bgp-aug:neighbor-address" {
    deviate replace {
      type leafref {
        path "/oc-ni:network-instances/oc-ni:network-instance" +
             "/oc-ni:protocols/oc-ni:protocol" +
             "/oc-ni:bgp" +
             "/oc-ni:neighbors/oc-ni:neighbor/oc-ni:neighbor-address";
      }
    }
    description "Change neighbor-address type to leafref";
  }

  deviation "/oc-ni:network-instances/oc-ni:network-instance" +
            "/oc-ni:protocols/oc-ni:protocol" +
            "/oc-ni:bgp/oc-ni:rib" +
            "/oc-ni:afi-safis/oc-ni:afi-safi" +
            "/arc-oc-rib-bgp-aug:ipv6-label-unicast/arc-oc-rib-bgp-aug:neighbors" +
            "/arc-oc-rib-bgp-aug:neighbor/arc-oc-rib-bgp-aug:state" +
            "/arc-oc-rib-bgp-aug:neighbor-address" {
    deviate replace {
      type leafref {
        path "/oc-ni:network-instances/oc-ni:network-instance" +
             "/oc-ni:protocols/oc-ni:protocol" +
             "/oc-ni:bgp" +
             "/oc-ni:neighbors/oc-ni:neighbor/oc-ni:neighbor-address";
      }
    }
    description "Change neighbor-address type to leafref";
  }

  deviation "/oc-ni:network-instances/oc-ni:network-instance" +
            "/oc-ni:protocols/oc-ni:protocol" +
            "/oc-ni:bgp/oc-ni:rib" +
            "/oc-ni:afi-safis/oc-ni:afi-safi" +
            "/arc-oc-rib-bgp-aug:l3vpn-ipv4-unicast/arc-oc-rib-bgp-aug:neighbors" +
            "/arc-oc-rib-bgp-aug:neighbor/arc-oc-rib-bgp-aug:state" +
            "/arc-oc-rib-bgp-aug:neighbor-address" {
    deviate replace {
      type leafref {
        path "/oc-ni:network-instances/oc-ni:network-instance" +
             "/oc-ni:protocols/oc-ni:protocol" +
             "/oc-ni:bgp" +
             "/oc-ni:neighbors/oc-ni:neighbor/oc-ni:neighbor-address";
      }
    }
    description "Change neighbor-address type to leafref";
  }

  deviation "/oc-ni:network-instances/oc-ni:network-instance" +
            "/oc-ni:protocols/oc-ni:protocol" +
            "/oc-ni:bgp/oc-ni:rib" +
            "/oc-ni:afi-safis/oc-ni:afi-safi" +
            "/arc-oc-rib-bgp-aug:l3vpn-ipv6-unicast/arc-oc-rib-bgp-aug:neighbors" +
            "/arc-oc-rib-bgp-aug:neighbor/arc-oc-rib-bgp-aug:state" +
            "/arc-oc-rib-bgp-aug:neighbor-address" {
    deviate replace {
      type leafref {
        path "/oc-ni:network-instances/oc-ni:network-instance" +
             "/oc-ni:protocols/oc-ni:protocol" +
             "/oc-ni:bgp" +
             "/oc-ni:neighbors/oc-ni:neighbor/oc-ni:neighbor-address";
      }
    }
    description "Change neighbor-address type to leafref";
  }

  deviation "/oc-ni:network-instances/oc-ni:network-instance" +
            "/oc-ni:protocols/oc-ni:protocol" +
            "/oc-ni:bgp/oc-ni:rib" +
            "/oc-ni:afi-safis/oc-ni:afi-safi" +
            "/arc-oc-rib-bgp-aug:l2vpn-evpn/arc-oc-rib-bgp-aug:neighbors" +
            "/arc-oc-rib-bgp-aug:neighbor/arc-oc-rib-bgp-aug:state" +
            "/arc-oc-rib-bgp-aug:neighbor-address" {
    deviate replace {
      type leafref {
        path "/oc-ni:network-instances/oc-ni:network-instance" +
             "/oc-ni:protocols/oc-ni:protocol" +
             "/oc-ni:bgp" +
             "/oc-ni:neighbors/oc-ni:neighbor/oc-ni:neighbor-address";
      }
    }
    description "Change neighbor-address type to leafref";
  }
}
