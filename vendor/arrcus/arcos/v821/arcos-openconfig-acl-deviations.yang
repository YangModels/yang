module arcos-openconfig-acl-deviations {
  yang-version 1.1;
  namespace "http://yang.arrcus.com/arcos/openconfig/acl/deviations";
  prefix arc-oc-acl-dev;

  import openconfig-acl {
    prefix oc-acl;
  }

  import ietf-inet-types {
    prefix ietf-inet;
  }

  import openconfig-inet-types {
    prefix oc-inet;
  }

  import openconfig-packet-match-types {
    prefix oc-pkt-match-types;
  }

  organization
    "Arrcus, Inc.";
  contact
    "Arrcus, Inc.
     2077 Gateway Place
     Suite 400
     San Jose, CA 95110
     E-mail: yang-support@arrcus.com";
  description
    "YANG data-model for deviations that are applied to 
     OpenConfig ACL model.
     
     Copyright (c) 2016-2023 by Arrcus, Inc.
     All rights reserved.";

  revision 2023-08-23 {
    description
      "Prevent destination/source port config if protocol is
       ICMP.";
  }
  revision 2023-07-19 {
    description
      "Initial version.";
  }

  deviation "/oc-acl:acl/oc-acl:acl-sets/oc-acl:acl-set" +
            "/oc-acl:config/oc-acl:name" {
    deviate replace {
      type string {
        length "0..79";
      }
    }
  }

  deviation "/oc-acl:acl/oc-acl:acl-sets/oc-acl:acl-set" +
            "/oc-acl:config/oc-acl:description" {
    deviate replace {
      type string {
        length "0..79";
      }
    }
  }

  deviation "/oc-acl:acl/oc-acl:acl-sets/oc-acl:acl-set" +
            "/oc-acl:acl-entries/oc-acl:acl-entry/oc-acl:config" +
            "/oc-acl:description" {
    deviate replace {
      type string {
        length "0..79";
      }
    }
  }

  deviation "/oc-acl:acl/oc-acl:acl-sets/oc-acl:acl-set/oc-acl:acl-entries" +
            "/oc-acl:acl-entry/oc-acl:config/oc-acl:sequence-id" {
    deviate replace {
      type uint64 {
        range "1..65534";
      }
    }
    description "increase to uint64 from uint32";
  }

  deviation "/oc-acl:acl/oc-acl:acl-sets/oc-acl:acl-set/oc-acl:acl-entries" +
            "/oc-acl:acl-entry/oc-acl:state/oc-acl:sequence-id" {
    deviate replace {
      type uint64;
    }
    description "increase to uint64 from uint32";
  }

  deviation "/oc-acl:acl/oc-acl:acl-sets/oc-acl:acl-set/oc-acl:acl-entries" +
            "/oc-acl:acl-entry/oc-acl:actions/oc-acl:config/oc-acl:forwarding-action" {
    deviate replace {
      mandatory false;
    }
    description "action is not a mandatory configuration";
  }

  deviation "/oc-acl:acl/oc-acl:acl-sets/oc-acl:acl-set/oc-acl:acl-entries" +
            "/oc-acl:acl-entry/oc-acl:ipv4/oc-acl:config" +
            "/oc-acl:source-address" {
    deviate replace {
      type ietf-inet:ipv4-prefix;
    }
    description "Use ietf-inet types instead of oc-inet";
  }

  deviation "/oc-acl:acl/oc-acl:acl-sets/oc-acl:acl-set/oc-acl:acl-entries" +
            "/oc-acl:acl-entry/oc-acl:ipv4/oc-acl:state" +
            "/oc-acl:source-address" {
    deviate replace {
      type ietf-inet:ipv4-prefix;
    }
    description "Use ietf-inet types instead of oc-inet";
  }

  deviation "/oc-acl:acl/oc-acl:acl-sets/oc-acl:acl-set/oc-acl:acl-entries" +
            "/oc-acl:acl-entry/oc-acl:ipv4/oc-acl:config" +
            "/oc-acl:destination-address" {
    deviate replace {
      type ietf-inet:ipv4-prefix;
    }
    description "Use ietf-inet types instead of oc-inet";
  }

  deviation "/oc-acl:acl/oc-acl:acl-sets/oc-acl:acl-set/oc-acl:acl-entries" +
            "/oc-acl:acl-entry/oc-acl:ipv4/oc-acl:state" +
            "/oc-acl:destination-address" {
    deviate replace {
      type ietf-inet:ipv4-prefix;
    }
    description "Use ietf-inet types instead of oc-inet";
  }

  deviation "/oc-acl:acl/oc-acl:acl-sets/oc-acl:acl-set/oc-acl:acl-entries" +
            "/oc-acl:acl-entry/oc-acl:ipv6/oc-acl:config" +
            "/oc-acl:source-address" {
    deviate replace {
      type ietf-inet:ipv6-prefix;
    }
    description "Use ietf-inet types instead of oc-inet";
  }

  deviation "/oc-acl:acl/oc-acl:acl-sets/oc-acl:acl-set/oc-acl:acl-entries" +
            "/oc-acl:acl-entry/oc-acl:ipv6/oc-acl:state" +
            "/oc-acl:source-address" {
    deviate replace {
      type ietf-inet:ipv6-prefix;
    }
    description "Use ietf-inet types instead of oc-inet";
  }

  deviation "/oc-acl:acl/oc-acl:acl-sets/oc-acl:acl-set/oc-acl:acl-entries" +
            "/oc-acl:acl-entry/oc-acl:ipv6/oc-acl:config" +
            "/oc-acl:destination-address" {
    deviate replace {
      type ietf-inet:ipv6-prefix;
    }
    description "Use ietf-inet types instead of oc-inet";
  }

  deviation "/oc-acl:acl/oc-acl:acl-sets/oc-acl:acl-set/oc-acl:acl-entries" +
            "/oc-acl:acl-entry/oc-acl:ipv6/oc-acl:state" +
            "/oc-acl:destination-address" {
    deviate replace {
      type ietf-inet:ipv6-prefix;
    }
    description "Use ietf-inet types instead of oc-inet";
  }

  deviation "/oc-acl:acl/oc-acl:acl-sets/oc-acl:acl-set" +
            "/oc-acl:acl-entries/oc-acl:acl-entry/oc-acl:transport" +
	    "/oc-acl:config/oc-acl:source-port" {
    deviate add {
      must "not(derived-from-or-self(../../../ipv4/config/protocol, " +
           "'oc-pkt-match-types:IP_ICMP')) and " +
           "not(derived-from-or-self(../../../ipv6/config/protocol, " +
	   "'oc-pkt-match-types:IP_ICMP')) and " +
           "not(derived-from-or-self(../../../ipv6/config/protocol, " +
	   "'oc-pkt-match-types:IP_ICMPV6'))" {
        error-message
          "Configuration of source-port allowed only if the " +
          "protocol is NOT ICMP.";
      }
    }
    deviate replace {
      type union {
        type string {
          pattern '(6[0-5][0-5][0-3][0-5]|[0-5]?[0-9]?[0-9]?[0-9]?' +
            '[0-9]?)\.\.(6[0-5][0-5][0-3][0-5]|[0-5]?[0-9]?[0-9]?' +
            '[0-9]?[0-9]?)';
        }
        type oc-inet:port-number;
        type enumeration {
          enum ANY {
            description
              "Indicates any valid port number (e.g., wildcard)";
          }
        }
      }
    }
    description "Fix the pattern of union member port-num-range
                 string by removing ^ and $.";
  }

  deviation "/oc-acl:acl/oc-acl:acl-sets/oc-acl:acl-set" +
            "/oc-acl:acl-entries/oc-acl:acl-entry/oc-acl:transport" +
	    "/oc-acl:config/oc-acl:destination-port" {
    deviate add {
      must "not(derived-from-or-self(../../../ipv4/config/protocol, " +
           "'oc-pkt-match-types:IP_ICMP')) and " +
           "not(derived-from-or-self(../../../ipv6/config/protocol, " +
	   "'oc-pkt-match-types:IP_ICMP')) and " +
           "not(derived-from-or-self(../../../ipv6/config/protocol, " +
	   "'oc-pkt-match-types:IP_ICMPV6'))" {
        error-message
          "Configuration of destination-port allowed only if the " +
          "protocol is NOT ICMP.";
      }
    }
    deviate replace {
      type union {
        type string {
          pattern '(6[0-5][0-5][0-3][0-5]|[0-5]?[0-9]?[0-9]?[0-9]?' +
            '[0-9]?)\.\.(6[0-5][0-5][0-3][0-5]|[0-5]?[0-9]?[0-9]?' +
            '[0-9]?[0-9]?)';
        }
        type oc-inet:port-number;
        type enumeration {
          enum ANY {
            description
              "Indicates any valid port number (e.g., wildcard)";
          }
        }
      }
    }
    description "Fix the pattern of union member port-num-range string by
                removing ^ and $.";
  }

  deviation "/oc-acl:acl/oc-acl:acl-sets/oc-acl:acl-set/oc-acl:acl-entries" +
            "/oc-acl:acl-entry/oc-acl:transport/oc-acl:state" +
            "/oc-acl:source-port" {
    deviate replace {
      type union {
        type string {
          pattern '(6[0-5][0-5][0-3][0-5]|[0-5]?[0-9]?[0-9]?[0-9]?' +
            '[0-9]?)\.\.(6[0-5][0-5][0-3][0-5]|[0-5]?[0-9]?[0-9]?' +
            '[0-9]?[0-9]?)';
        }
        type oc-inet:port-number;
        type enumeration {
          enum ANY {
            description
              "Indicates any valid port number (e.g., wildcard)";
          }
        }
      }
    }
    description "Fix the pattern of union member port-num-range string by
                removing ^ and $.";
  }

  deviation "/oc-acl:acl/oc-acl:acl-sets/oc-acl:acl-set/oc-acl:acl-entries" +
            "/oc-acl:acl-entry/oc-acl:transport/oc-acl:state" +
            "/oc-acl:destination-port" {
    deviate replace {
      type union {
        type string {
          pattern '(6[0-5][0-5][0-3][0-5]|[0-5]?[0-9]?[0-9]?[0-9]?' +
            '[0-9]?)\.\.(6[0-5][0-5][0-3][0-5]|[0-5]?[0-9]?[0-9]?' +
            '[0-9]?[0-9]?)';
        }
        type oc-inet:port-number;
        type enumeration {
          enum ANY {
            description
              "Indicates any valid port number (e.g., wildcard)";
          }
        }
      }
    }
    description "Fix the pattern of union member port-num-range string by
                removing ^ and $.";
  }

  deviation "/oc-acl:acl/oc-acl:acl-sets/oc-acl:acl-set/oc-acl:acl-entries" +
            "/oc-acl:acl-entry/oc-acl:ipv4/oc-acl:config" +
            "/oc-acl:dscp" {
    deviate replace {
      type union {
        type oc-inet:dscp;
        type string {
          pattern '(6[0-3]|[1-5][0-9]|[0-9])\.\.(6[0-3]|[1-5][0-9]|[0-9])';
        }
      }
    }
    description "Use union of oc-inet:dscp/range instead of oc-inet:dscp";
  }

  deviation "/oc-acl:acl/oc-acl:acl-sets/oc-acl:acl-set/oc-acl:acl-entries" +
            "/oc-acl:acl-entry/oc-acl:ipv4/oc-acl:state" +
            "/oc-acl:dscp" {
    deviate replace {
      type union {
        type oc-inet:dscp;
        type string {
          pattern '(6[0-3]|[1-5][0-9]|[0-9])\.\.(6[0-3]|[1-5][0-9]|[0-9])';
        }
      }
    }
    description "Use union of oc-inet:dscp/range instead of oc-inet:dscp";
  }

  deviation "/oc-acl:acl/oc-acl:acl-sets/oc-acl:acl-set/oc-acl:acl-entries" +
            "/oc-acl:acl-entry/oc-acl:ipv6/oc-acl:config" +
            "/oc-acl:dscp" {
    deviate replace {
      type union {
        type oc-inet:dscp;
        type string {
          pattern '(6[0-3]|[1-5][0-9]|[0-9])\.\.(6[0-3]|[1-5][0-9]|[0-9])';
        }
      }
    }
    description "Use union of oc-inet:dscp/range instead of oc-inet:dscp";
  }

  deviation "/oc-acl:acl/oc-acl:acl-sets/oc-acl:acl-set/oc-acl:acl-entries" +
            "/oc-acl:acl-entry/oc-acl:ipv6/oc-acl:state" +
            "/oc-acl:dscp" {
    deviate replace {
      type union {
        type oc-inet:dscp;
        type string {
          pattern '(6[0-3]|[1-5][0-9]|[0-9])\.\.(6[0-3]|[1-5][0-9]|[0-9])';
        }
      }
    }
    description "Use union of oc-inet:dscp/range instead of oc-inet:dscp";
  }

  deviation "/oc-acl:acl/oc-acl:acl-sets/oc-acl:acl-set/oc-acl:acl-entries" +
            "/oc-acl:acl-entry/oc-acl:ipv4/oc-acl:config" +
            "/oc-acl:protocol" {
    deviate replace {
      type union {
        type uint8 {
          range 0..max;
        }
        type identityref {
          base oc-pkt-match-types:IP_PROTOCOL;
        }
      }
    }
    description "Change range to 0..max";
  }

  deviation "/oc-acl:acl/oc-acl:acl-sets/oc-acl:acl-set/oc-acl:acl-entries" +
            "/oc-acl:acl-entry/oc-acl:ipv4/oc-acl:state" +
            "/oc-acl:protocol" {
    deviate replace {
      type union {
        type uint8 {
          range 0..max;
        }
        type identityref {
          base oc-pkt-match-types:IP_PROTOCOL;
        }
      }
    }
    description "Change range to 0..max";
  }

  deviation "/oc-acl:acl/oc-acl:acl-sets/oc-acl:acl-set/oc-acl:acl-entries" +
            "/oc-acl:acl-entry/oc-acl:ipv6/oc-acl:config" +
            "/oc-acl:protocol" {
    deviate replace {
      type union {
        type uint8 {
          range 0..max;
        }
        type identityref {
          base oc-pkt-match-types:IP_PROTOCOL;
        }
      }
    }
    description "Change range to 0..max";
  }

  deviation "/oc-acl:acl/oc-acl:acl-sets/oc-acl:acl-set/oc-acl:acl-entries" +
            "/oc-acl:acl-entry/oc-acl:ipv6/oc-acl:state" +
            "/oc-acl:protocol" {
    deviate replace {
      type union {
        type uint8 {
          range 0..max;
        }
        type identityref {
          base oc-pkt-match-types:IP_PROTOCOL;
        }
      }
    }
    description "Change range to 0..max";
  }

  deviation "/oc-acl:acl/oc-acl:acl-sets/oc-acl:acl-set/oc-acl:acl-entries" +
            "/oc-acl:acl-entry/oc-acl:ipv6/oc-acl:config" +
            "/oc-acl:destination-flow-label" {
    deviate not-supported;
    description "Do not support ipv6 destination-flow-label in this release";
  }

  deviation "/oc-acl:acl/oc-acl:acl-sets/oc-acl:acl-set/oc-acl:acl-entries" +
            "/oc-acl:acl-entry/oc-acl:ipv6/oc-acl:state" +
            "/oc-acl:destination-flow-label" {
    deviate not-supported;
    description "Do not support ipv6 destination-flow-label in this release";
  }

  deviation "/oc-acl:acl/oc-acl:acl-sets/oc-acl:acl-set/oc-acl:acl-entries" +
            "/oc-acl:acl-entry/oc-acl:input-interface" {
    deviate not-supported;
    description "Do not support input-interface in this release";
  }

  deviation /oc-acl:acl/oc-acl:interfaces {
    deviate not-supported;
    description "ACL targets shall be configured under interfaces directly";
  }

  deviation "/oc-acl:acl/oc-acl:acl-sets/oc-acl:acl-set/oc-acl:acl-entries" +
            "/oc-acl:acl-entry/oc-acl:l2/oc-acl:config/oc-acl:source-mac" {
    deviate replace {
      type union {
        type string {
          pattern '[0-9a-fA-F]{2}(:[0-9a-fA-F]{2}){5}';
        }
        type enumeration {
          enum ANY {
            description
              "Matches on any mac addresses";
          }
        } 
      }
    }
    description "Fix the pattern of mac-address by removing ^ and $.";
  }

  deviation "/oc-acl:acl/oc-acl:acl-sets/oc-acl:acl-set/oc-acl:acl-entries" +
            "/oc-acl:acl-entry/oc-acl:l2/oc-acl:state/oc-acl:source-mac" {
    deviate replace {
      type union {
        type string {
          pattern '[0-9a-fA-F]{2}(:[0-9a-fA-F]{2}){5}';
        }
        type enumeration {
          enum ANY { 
            description
              "Matches on any mac addresses";
          }
        } 
      }
    }
    description "Fix the pattern of mac-address by removing ^ and $.";
  }

  deviation "/oc-acl:acl/oc-acl:acl-sets/oc-acl:acl-set/oc-acl:acl-entries" +
            "/oc-acl:acl-entry/oc-acl:l2/oc-acl:config" +
            "/oc-acl:source-mac-mask" {
    deviate replace {
      type string {
        pattern '[0-9a-fA-F]{2}(:[0-9a-fA-F]{2}){5}';
      }
    }
    description "Fix the pattern of mac-address by removing ^ and $.";
  }

  deviation "/oc-acl:acl/oc-acl:acl-sets/oc-acl:acl-set/oc-acl:acl-entries" +
            "/oc-acl:acl-entry/oc-acl:l2/oc-acl:state" +
            "/oc-acl:source-mac-mask" {
    deviate replace {
      type string {
        pattern '[0-9a-fA-F]{2}(:[0-9a-fA-F]{2}){5}';
      }
    }
    description "Fix the pattern of mac-address by removing ^ and $.";
  }

  deviation "/oc-acl:acl/oc-acl:acl-sets/oc-acl:acl-set/oc-acl:acl-entries" +
            "/oc-acl:acl-entry/oc-acl:l2/oc-acl:config" +
            "/oc-acl:destination-mac" {
    deviate replace {
      type union {
        type string {
          pattern '[0-9a-fA-F]{2}(:[0-9a-fA-F]{2}){5}';
        }
        type enumeration {
          enum ANY {
            description
              "Matches on any mac addresses";
          }
        } 
      }
    }
    description "Fix the pattern of mac-address by removing ^ and $.";
  }

  deviation "/oc-acl:acl/oc-acl:acl-sets/oc-acl:acl-set/oc-acl:acl-entries" +
            "/oc-acl:acl-entry/oc-acl:l2/oc-acl:state" +
            "/oc-acl:destination-mac" {
    deviate replace {
      type union {
        type string {
          pattern '[0-9a-fA-F]{2}(:[0-9a-fA-F]{2}){5}';
        }
        type enumeration {
          enum ANY {
            description
              "Matches on any mac addresses";
          }
        } 
      }
    }
    description "Fix the pattern of mac-address by removing ^ and $.";
  }

  deviation "/oc-acl:acl/oc-acl:acl-sets/oc-acl:acl-set/oc-acl:acl-entries" +
            "/oc-acl:acl-entry/oc-acl:l2/oc-acl:config" +
            "/oc-acl:destination-mac-mask" {
    deviate replace {
      type string {
        pattern '[0-9a-fA-F]{2}(:[0-9a-fA-F]{2}){5}';
      }
    }
    description "Fix the pattern of mac-address by removing ^ and $.";
  }

  deviation "/oc-acl:acl/oc-acl:acl-sets/oc-acl:acl-set/oc-acl:acl-entries" +
            "/oc-acl:acl-entry/oc-acl:l2/oc-acl:state" +
            "/oc-acl:destination-mac-mask" {
    deviate replace {
      type string {
        pattern '[0-9a-fA-F]{2}(:[0-9a-fA-F]{2}){5}';
      }
    }
    description "Fix the pattern of mac-address by removing ^ and $.";
  }

  deviation "/oc-acl:acl/oc-acl:acl-sets/oc-acl:acl-set/oc-acl:acl-entries" +
            "/oc-acl:acl-entry/oc-acl:state/oc-acl:matched-packets" {
    deviate not-supported;
    description "Replaced with matched-ingress-packets and
                matched-egress-packet";
  }

  deviation "/oc-acl:acl/oc-acl:acl-sets/oc-acl:acl-set/oc-acl:acl-entries" +
            "/oc-acl:acl-entry/oc-acl:state/oc-acl:matched-octets" {
    deviate not-supported;
    description "Replaced with matched-ingress-octets and
                matched-egress-octets";
  }

}
