/**
 * Filename: arcos-ldp-debug.yang
 *
 * Description:
 * YANG data-model for LDP Debugs Action 
 *
 * Copyright 2019 by Arrcus, Inc.
 * All rights reserved.
 */

module arcos-ldp-debug {
  namespace "http://yang.arrcus.com/arcos/ldp/debug";

  prefix arc-ldp-debug;

  import ietf-inet-types { prefix inet; }
  import openconfig-types { prefix "oc-types"; }
  import ietf-interfaces { prefix ietf-if; }
  import tailf-common { prefix tailf; }

  organization
    "Arrcus, Inc.";

  contact
    "Arrcus, Inc.
     2077 Gateway Place
     Suite 400
     San Jose, CA 95110

     E-mail: yang-support@arrcus.com";

  description
    "YANG data-model for LDP Debugs definitions.

     Copyright (c) 2023 by Arrcus, Inc.
     All rights reserved.";

  revision 2023-12-03 {
    description
      "Add model for tech-support debug state";
  }
 
  revision "2023-03-24" {
    description
      "Updated debug options for LDP";
  }

  

  typedef ldp-debug-state {
    type enumeration { 
      enum on {
        description
          "Enable debug";
      }
      enum off {
        description
          "Disable debug";
      }
    }
  }

  typedef ldp-debug-type {
    type enumeration { 
      enum ldp {
        description
          "Control ldp debugs";
      }
      enum ldp-engine {
        description
          "Control ldp-engine debugs";
      }
      enum session {
        description
          "Control ldp session debugs";
      }
      enum label {
        description
          "Control ldp label operation debugs";
      }
      enum all {
        description
          "Control All debugs";
      }
    }
  }

   grouping ldp-debugs-state {
    description
      "ldp debugs information";

    leaf debug-flag {
      type ldp-debug-type;
      description
        "ldp debug flags";
    }
    leaf enabled {
      type boolean;
      description
        "Indicates whether the debug flag is enabled or not";
    }
  }

  grouping ldp-show-debug-top {
    container ldp-show-debugs {
      list ldp-debug {
        key "debug-flag";

        description
          "ldp debugs information";

        leaf debug-flag {
          type leafref {
            path "../state/debug-flag";
          }
          description
            "ldp Debug flags";
        }

        container state {
          uses ldp-debugs-state;
        }
      }
    }
  }

  container ldp-debug {
    description
      "LDP debug control";
    tailf:action debug {
      tailf:cli-operational-mode;
      tailf:cli-mount-point "tech-support";
      tailf:actionpoint ldp-debug-point;
      input {
        leaf type {
        type ldp-debug-type;
        mandatory true;
          description
          "Debug to be controlled";
        }
        leaf op {
        type ldp-debug-state;
        mandatory true;
          description
          "turn on/off operation";
        }
      }
      output {
        leaf result {
        type string;
          description
          "The status of operation"; 
        }
      }
    }
  }
}
