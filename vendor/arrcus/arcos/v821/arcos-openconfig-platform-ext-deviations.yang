module arcos-openconfig-platform-ext-deviations {
  yang-version 1.1;
  namespace "http://yang.arrcus.com/arcos/openconfig/platform/extension/deviations";
  prefix arc-oc-platform-ext-dev;

  import openconfig-platform {
    prefix oc-platform;
  }

  import openconfig-platform-ext {
    prefix oc-platform-ext;
  }

  organization
    "Arrcus, Inc.";

  contact
    "Arrcus, Inc.
     Customer Service
     Postal: 2077 Gateway Place
     San Jose, CA 95110
     Tel: +1 408 884-1965
     E-mail: yang-support@arrcus.com";


  description
    "This module defines deviation statements for Arrcus
     implemention of the openconfig platform extension module.

     Copyright (c) 2022 by Arrcus, Inc.
     All rights reserved.";

  revision 2022-11-08 {
    description
      "Initial revision";
  }

  deviation "/oc-platform:components/oc-platform:component/oc-platform:state/" +
            "oc-platform-ext:entity-id" {
    deviate not-supported;
    description "Not supported in this release";
  }
}
