module arcos-ipfix-clear {
  yang-version 1.1;
  namespace "http://yang.arrcus.com/arcos/ipfix/clear";
  prefix arc-ipfix-clr;


  organization
    "Arrcus, Inc.";

  contact
    "Arrcus, Inc.
     Customer Service
     Postal: 2077 Gateway Place
     San Jose, CA 95110
     Tel: +1 408 884-1965
     E-mail: yang-support@arrcus.com";

  description
    "This module defines yang model for clearing IPFIX counters.

     Copyright (c) 2016-2024 by Arrcus, Inc.
     All rights reserved.";

  revision 2025-04-03 {
    description
      "Initial version";
  }
  
  container ipfix-clear {
    description
      "Clear IPFIX statistics for exporting process";

    action counters {
      description
        "Clear IPFIX statistics for exporting process";

      input {
        leaf name {
          type string;
          mandatory true;
          description
            "The IPFIX exporter whose counters needs to be cleared.
             Use 'all' for all exporters";
        }
      }
      output {
        leaf result {
        type string;
          description
          "The status of operation";
        }
      }
    }
  }
}
