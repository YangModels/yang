module arcos-packet-match-mpls {
  yang-version 1.1;
  namespace "http://yang.arrcus.com/arcos/packet-match-mpls";
  prefix arc-match-mpls;

  organization
    "Arrcus, Inc.";

  contact
    "Arrcus, Inc.
     2077 Gateway Place
     Suite 400
     San Jose, CA 95110

     E-mail: yang-support@arrcus.com";

  description
    "YANG data model for matching fields in the IP packet for MPLS.

    Copyright (c) 2016-2023 by Arrcus, Inc.
    All rights reserved.";

  revision 2023-06-27 {
    description
      "Initial revision.";
  }

  grouping mpls-fields-config {
    description
      "Configuration data of MPLS fields";

    leaf label-id {
      type uint32 {
        range "0..1048575";
      }
      description
      "Match the conditon that an IP packet contains a specific MPLS
      label.";
    }
  }

  grouping mpls-fields-state {
    description
      "State data of mpls-fields";
  }

  grouping mpls-fields-top {
    description
      "Destination mpls-fields top level grouping";

    container mpls {
      description
        "MPLS fields container";

      container config {
        description
          "Configuration data";
        uses mpls-fields-config;
      }

      container state {
        config false;
        description
          "State data";
        uses mpls-fields-config;
        uses mpls-fields-state;
      }
    }
  }
}
