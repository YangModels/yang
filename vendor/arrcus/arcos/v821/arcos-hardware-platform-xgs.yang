module arcos-hardware-platform-xgs {
  yang-version 1.1;
  namespace "http://yang.arrcus.com/arcos/hardware/platform/xgs";
  prefix arc-hw-platform-xgs;

  import arcos-hardware-platform-types {
    prefix arc-hw-platform-types;
  }

  import openconfig-interfaces {
    prefix "oc-if";
  }

  import openconfig-vlan-types {
    prefix oc-vlan-types;
  }

  import ietf-yang-types {
    prefix yang;
  }

  import arcos-platform {
    prefix arc-platform;
  }

  grouping xgs-profile {
    leaf name {
      type string {
        length "0..64";
      }
      description "Name of MMU queue profile";
    }
    container ucast-queue-0 {
      leaf reserved {
        type uint32;
        default 0;
        description "Reserved buffer space for unicast queue 0 in bytes";
      }
      leaf threshold {
        type arc-hw-platform-types:MMU_QUEUE_ALPHA_VALUE;
        default 2;
        description "Dynamic threshold value setting for unicast queue 0";
      }
    }
    container ucast-queue-1 {
      leaf reserved {
        type uint32;
        default 0;
        description "Reserved buffer space for unicast queue 1 in bytes";
      }
      leaf threshold {
        type arc-hw-platform-types:MMU_QUEUE_ALPHA_VALUE;
        default 2;
        description "Dynamic threshold value setting for unicast queue 1";
      }
    }
    container ucast-queue-2 {
      leaf reserved {
        type uint32;
        default 0;
        description "Reserved buffer space for unicast queue 2 in bytes";
      }
      leaf threshold {
        type arc-hw-platform-types:MMU_QUEUE_ALPHA_VALUE;
        default 2;
        description "Dynamic threshold value setting for unicast queue 2";
      }
    }
    container ucast-queue-3 {
      leaf reserved {
        type uint32;
        default 0;
        description "Reserved buffer space for unicast queue 3 in bytes";
      }
      leaf threshold {
        type arc-hw-platform-types:MMU_QUEUE_ALPHA_VALUE;
        default 2;
        description "Dynamic threshold value setting for unicast queue 3";
      }
    }
    container ucast-queue-4 {
      leaf reserved {
        type uint32;
        default 0;
        description "Reserved buffer space for unicast queue 4 in bytes";
      }
      leaf threshold {
        type arc-hw-platform-types:MMU_QUEUE_ALPHA_VALUE;
        default 2;
        description "Dynamic threshold value setting for unicast queue 4";
      }
    }
    container ucast-queue-5 {
      leaf reserved {
        type uint32;
        default 0;
        description "Reserved buffer space for unicast queue 5 in bytes";
      }
      leaf threshold {
        type arc-hw-platform-types:MMU_QUEUE_ALPHA_VALUE;
        default 2;
        description "Dynamic threshold value setting for unicast queue 5";
      }
    }
    container ucast-queue-6 {
      leaf reserved {
        type uint32;
        default 0;
        description "Reserved buffer space for unicast queue 6 in bytes";
      }
      leaf threshold {
        type arc-hw-platform-types:MMU_QUEUE_ALPHA_VALUE;
        default 2;
        description "Dynamic threshold value setting for unicast queue 6";
      }
    }
    container ucast-queue-7 {
      leaf reserved {
        type uint32;
        default 0;
        description "Reserved buffer space for unicast queue 7 in bytes";
      }
      leaf threshold {
        type arc-hw-platform-types:MMU_QUEUE_ALPHA_VALUE;
        default 2;
        description "Dynamic threshold value setting for unicast queue 7";
      }
    }
    container mcast-queue-0 {
      leaf reserved {
        type uint32;
        default 0;
        description "Reserved buffer space for multicast queue 0 in bytes";
      }
      leaf threshold {
        type arc-hw-platform-types:MMU_QUEUE_ALPHA_VALUE;
        default 2;
        description "Dynamic threshold value setting for multicast queue 0";
      }
    }
    container mcast-queue-1 {
      leaf reserved {
        type uint32;
        default 0;
        description "Reserved buffer space for multicast queue 1 in bytes";
      }
      leaf threshold {
        type arc-hw-platform-types:MMU_QUEUE_ALPHA_VALUE;
        default 2;
        description "Dynamic threshold value setting for multicast queue 1";
      }
    }
    container mcast-queue-2 {
      leaf reserved {
        type uint32;
        default 0;
        description "Reserved buffer space for multicast queue 2 in bytes";
      }
      leaf threshold {
        type arc-hw-platform-types:MMU_QUEUE_ALPHA_VALUE;
        default 2;
        description "Dynamic threshold value setting for multicast queue 2";
      }
    }
    container mcast-queue-3 {
      leaf reserved {
        type uint32;
        default 0;
        description "Reserved buffer space for multicast queue 3 in bytes";
      }
      leaf threshold {
        type arc-hw-platform-types:MMU_QUEUE_ALPHA_VALUE;
        default 2;
        description "Dynamic threshold value setting for multicast queue 3";
      }
    }
    container mcast-queue-4 {
      leaf reserved {
        type uint32;
        default 0;
        description "Reserved buffer space for multicast queue 4 in bytes";
      }
      leaf threshold {
        type arc-hw-platform-types:MMU_QUEUE_ALPHA_VALUE;
        default 2;
        description "Dynamic threshold value setting for multicast queue 4";
      }
    }
    container mcast-queue-5 {
      leaf reserved {
        type uint32;
        default 0;
        description "Reserved buffer space for multicast queue 5 in bytes";
      }
      leaf threshold {
        type arc-hw-platform-types:MMU_QUEUE_ALPHA_VALUE;
        default 2;
        description "Dynamic threshold value setting for multicast queue 5";
      }
    }
    container mcast-queue-6 {
      leaf reserved {
        type uint32;
        default 0;
        description "Reserved buffer space for multicast queue 6 in bytes";
      }
      leaf threshold {
        type arc-hw-platform-types:MMU_QUEUE_ALPHA_VALUE;
        default 2;
        description "Dynamic threshold value setting for multicast queue 6";
      }
    }
    container mcast-queue-7 {
      leaf reserved {
        type uint32;
        default 0;
        description "Reserved buffer space for multicast queue 7 in bytes";
      }
      leaf threshold {
        type arc-hw-platform-types:MMU_QUEUE_ALPHA_VALUE;
        default 2;
        description "Dynamic threshold value setting for multicast queue 7";
      }
    }
  }

  grouping queue-profile {
    container queue {
      description "MMU queue specific configuration/state";
      list profile {
        description "Queue profile configuration";
        key "name";

        leaf name {
          description "Name of MMU queue profile";
          type leafref {
            path ../config/name;
          }
        }

        container config {
          uses xgs-profile;
        }
      }

      leaf apply-profile {
        description "Global knob to allow an MMU queue profile to be attached to all ports";
        type leafref {
          path "../profile/name";
        }
      }
    }
  }

  grouping shared-pool-stats {
    leaf sp-0 {
      description "Usage count in cells for shared pool-0";
      type uint64;
    }
    leaf sp-1 {
      description "Usage count in cells for shared pool-1";
      type uint64;
    }
    leaf sp-2 {
      description "Usage count in cells for shared pool-2";
      type uint64;
    }
    leaf sp-3 {
      description "Usage count in cells for shared pool-3";
      type uint64;
    }
  }

  grouping per-cosq-stats {
    leaf queue-0 {
      description "Usage count in cells for queue-0";
      type uint64;
    }
    leaf queue-1 {
      description "Usage count in cells for queue-1";
      type uint64;
    }
    leaf queue-2 {
      description "Usage count in cells for queue-2";
      type uint64;
    }
    leaf queue-3 {
      description "Usage count in cells for queue-3";
      type uint64;
    }
    leaf queue-4 {
      description "Usage count in cells for queue-4";
      type uint64;
    }
    leaf queue-5 {
      description "Usage count in cells for queue-5";
      type uint64;
    }
    leaf queue-6 {
      description "Usage count in cells for queue-6";
      type uint64;
    }
    leaf queue-7 {
      description "Usage count in cells for queue-7";
      type uint64;
    }
  }

  grouping per-pg-stats {
    leaf pg-0 {
      description "Usage count in cells for pg-0";
      type uint64;
    }
    leaf pg-1 {
      description "Usage count in cells for pg-1";
      type uint64;
    }
    leaf pg-2 {
      description "Usage count in cells for pg-2";
      type uint64;
    }
    leaf pg-3 {
      description "Usage count in cells for pg-3";
      type uint64;
    }
    leaf pg-4 {
      description "Usage count in cells for pg-4";
      type uint64;
    }
    leaf pg-5 {
      description "Usage count in cells for pg-5";
      type uint64;
    }
    leaf pg-6 {
      description "Usage count in cells for pg-6";
      type uint64;
    }
    leaf pg-7 {
      description "Usage count in cells for pg-7";
      type uint64;
    }
  }


  grouping xgs-buffer-stats {
    description "Aggregate list of buffer related statistics";

    leaf last-clear-time {
      description "Time buffer stats counters were last cleared";
      type yang:date-and-time;
    }

    container global {
      description "Buffer relates statistics for device wide resources. Stats are reported in cells (256 bytes approx.)";

      container ing-shared-pool {
        description "Usage count in cells for ingress shared pools";
        uses shared-pool-stats;
      }

      container ing-glbl-hdrm {
        description "Usage count in cells for ingress global headroom pools";
        uses shared-pool-stats;
      }

      container ing-glbl-hdrm-drops {
        description "Drop count in packets for ingress global headroom pools";
        uses shared-pool-stats;
      }

      container egr-shared-pool {
        description "Usage count in cells for egress shared pools";
        uses shared-pool-stats;
      }
    }

    container per-interface {
      config false;
      description "Buffer related statistics for interface specific resources. Stats are reported in cells (256 bytes approx.)";

      container ing-pg-min {
        description "Usage count in cells for ingress port PG min";

        list interface {
          key "name";
          leaf "name" {
            type string;
          }
          uses per-pg-stats;
        }
      }
      container ing-port-shared-pool {
        description "Usage count in cells for ingress port shared pool";

        list interface {
          key "name";
          leaf "name" {
            type string;
          }
          uses shared-pool-stats;
        }
      }
      container ing-pg-hdrm {
        description "Usage count in cells for ingress port PG Headroom";

        list interface {
          key "name";
          leaf "name" {
            type string;
          }
          uses per-pg-stats;
        }
      }
      container egr-uc-queue {
        description "Usage count in cells for egress UC queue min";

        list interface {
          key "name";
          leaf "name" {
            type string;
          }
          uses per-cosq-stats;
        }
      }
      container egr-uc-shared-pool {
        description "Usage count in cells for egress UC shared pool";

        list interface {
          key "name";
          leaf "name" {
            type string;
          }
          uses shared-pool-stats;
        }
      }
      container egr-mc-queue {
        description "Usage count in cells for egress MC queue min";

        list interface {
          key "name";
          leaf "name" {
            type string;
          }
          uses per-cosq-stats;
        }
      }
      container egr-mc-shared-pool {
        description "Usage count in cells for egress MC shared pool";

        list interface {
          key "name";
          leaf "name" {
            type string;
          }
          uses shared-pool-stats;
        }
      }
    }
  }

  grouping xgs-buffer-stats-config {
    container buffer-stats {
      description "Global control to enable/disable buffer statistics";
      leaf tracking-mode {
        type identityref {
          base arc-hw-platform-types:BUFFER_STATS_MODE;
        }
        default arc-hw-platform-types:BUFFER_STATS_MODE_PEAK;
      }
    }
  }

  grouping xgs-buffer-stats-state {
    container buffer-stats {
      description "Global control to enable/disable buffer statistics";

      leaf tracking-mode {
        description "Buffer statistics collection mode";
        type identityref {
          base arc-hw-platform-types:BUFFER_STATS_MODE;
        }
      }
      leaf refresh-interval {
        description "Time interval in seconds between successive refreshes of stats";
        type uint32;
        units seconds;
      }
      leaf cell-size {
        description "Cell size in bytes";
        type uint32;
        units bytes;
      }
      uses xgs-buffer-stats;
    }
  }

  grouping xgs-queue-profile {
    description "Controls for tuning device specific queue configuration";
    container mmu {
      description "MMU configuration/state";

      container config {
        uses queue-profile;
        uses xgs-buffer-stats-config {
          when "((/arc-platform:platform/arc-platform:asic = 'arc-platform:BROADCOM_TRIDENT3') or " +
               "(/arc-platform:platform/arc-platform:asic = 'arc-platform:BROADCOM_TOMAHAWK') or " +
               "(/arc-platform:platform/arc-platform:asic = 'arc-platform:BROADCOM_TOMAHAWK5') or " +
               "(/arc-platform:platform/arc-platform:asic = 'arc-platform:BROADCOM_TRIDENT4'))";
        }
      }

      container state {
        config false;
        uses xgs-buffer-stats-state {
          when "((/arc-platform:platform/arc-platform:asic = 'arc-platform:BROADCOM_TRIDENT3') or " +
               "(/arc-platform:platform/arc-platform:asic = 'arc-platform:BROADCOM_TOMAHAWK') or " +
               "(/arc-platform:platform/arc-platform:asic = 'arc-platform:BROADCOM_TOMAHAWK5') or " +
               "(/arc-platform:platform/arc-platform:asic = 'arc-platform:BROADCOM_TRIDENT4'))";
        }
      }
    }
  }

  grouping ecmp-dlb-top {
    leaf sampling-rate {
      type uint32;
      default 16;
      description "Sampling Rate for DLB in micro seconds";
    }
  }

  grouping inactive-duration {
    leaf inactivity-duration {
      type arc-hw-platform-types:inact-int-uint32;
      description "Inactivity duration for Dynamic loadbalancing in microseconds";
    }
  }

  grouping dlb-port-quality {
    container port-quality {
      config false;
      list interface {
        key "ifname";

        leaf ifname {
          type leafref {
            path "/oc-if:interfaces/oc-if:interface/oc-if:config/oc-if:name";
          }
          description "Interface Name";
        }
        list mmu-quality {
          key "mmu-id";
          leaf mmu-id {
            type uint16;
            description "The MMU ID";
          }
          leaf quality {
            type uint16;
            description "The port Quality for the MMU";
          }
        }
      }
    }
  }

  grouping ecmp-profile {
     leaf dlb-profile {
      description
        "Dynamic loadbalancing profile based on application use case";
      type enumeration {
        enum AI-ML {
          description
            "Profile to be used if this device is part of artifical intelligence / machine learning cluster topology";
        }
        enum GENERAL {
          description
            "Profile to be used if device is part of general switching or routing topology";
        }
      }
      default GENERAL;
    }
  }

  grouping ecmp-loadbalancing {
    description
      "Configure ecmp loadbalancing mode and parameters";

    leaf mode {
      type enumeration {
        enum RESILIENT {
          description
            "Resilient mode";
        }
        enum DYNAMIC {
          description
            "Dynamic mode";
        }
      }
      description "Loadbalancing mode for ECMP. Config will be applied to hardware after restart"  ;
      default RESILIENT;
    }

    uses inactive-duration {
      when "mode = 'DYNAMIC'" {
        description "inactivity duration should be configured only if DLB mode is enabled";
      }
    }

    uses ecmp-dlb-top {
      when "mode = 'DYNAMIC'" {
        description "DLB specific configs";
      }
    }

    uses dlb-port-quality;

    uses ecmp-profile {
      when "mode = 'DYNAMIC' and "
        + "derived-from-or-self(/arc-platform:platform/arc-platform:asic, 'arc-platform:BROADCOM_TOMAHAWK5')" {
          description "profile to be configured when dynamic mode is enabled";
        }
    }
  }

  grouping xgs-load-balancing {
    description "Controls for tuning device specific load balancing configuration";

    container ecmp {
      description "IP ECMP load balancing";
      uses ecmp-loadbalancing;
    }
  }
}
