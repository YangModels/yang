submodule arcos-ospfv2-area-interface {

  yang-version "1.1";

  belongs-to arcos-ospfv2 {
    prefix "arc-ospfv2";
  }

  import ietf-yang-types { prefix "yang"; }

  organization
    "Arrcus, Inc";

  contact
    "Arrcus, Inc.
     2077 Gateway Place
     Suite 400
     San Jose, CA 95110
     
     E-mail: yang-support@arrcus.com";

  description
    "This submodule provides OSPFv2 configuration and operational
    state parameters that are specific to the interface context";

  revision "2020-01-01" {
    description
      "Initial version";
  }

  grouping ospfv2-area-interface-neighbor-state {
    description
      "Operation state parameters of an OSPFv2 neighbor";

    leaf dr-ip-address {
      type yang:dotted-quad;
      description
        "The IP address of the designated router elected by the neighbor.";
    }

    leaf bdr-ip-address {
      type yang:dotted-quad;
      description
        "The IP address of the backup designated router elected by the neighbor.";
    }
  }

  grouping ospfv2-area-interface-neighbor-bfd-structure {
    description
      "This grouping defines OSPFv2 neighbor BFD information.";

    container bfd {
      description
        "This container defines neighbor BFD state.";

      container state {
        leaf ipv4-bfd-up {
          type boolean;
          description
            "OSPF neighbor IPV4 BFD up";
        }
      }
    }
  }
}
