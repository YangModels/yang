/*
 * Generated by confdc --mib2yang
 * Source: TOKEN-RING-RMON-MIB.mib
 */
module TOKEN-RING-RMON-MIB {
  namespace "http://tail-f.com/ns/mibs/TOKEN-RING-RMON-MIB/1.0";
  prefix TOKEN_RING_RMON_MIB;
  tailf:id "";
  tailf:snmp-mib-module-name "TOKEN-RING-RMON-MIB";

  import ietf-yang-types {
    prefix yang;
  }
  import tailf-common {
    prefix tailf;
  }
  import RMON-MIB {
    prefix RMON-MIB;
  }

  container TOKEN-RING-RMON-MIB {
    config false;
    container tokenRingMLStatsTable {
      list tokenRingMLStatsEntry {
        key "tokenRingMLStatsIndex";
        tailf:sort-order "snmp";
        tailf:snmp-name "tokenRingMLStatsTable";
        leaf tokenRingMLStatsIndex {
          type tokenRingMLStatsIndexType;
          tailf:snmp-name "tokenRingMLStatsIndex";
        }
        leaf tokenRingMLStatsDataSource {
          type yang:object-identifier;
          tailf:snmp-name "tokenRingMLStatsDataSource";
        }
        leaf tokenRingMLStatsDropEvents {
          type yang:counter32;
          tailf:snmp-name "tokenRingMLStatsDropEvents";
        }
        leaf tokenRingMLStatsMacOctets {
          type yang:counter32;
          tailf:snmp-name "tokenRingMLStatsMacOctets";
        }
        leaf tokenRingMLStatsMacPkts {
          type yang:counter32;
          tailf:snmp-name "tokenRingMLStatsMacPkts";
        }
        leaf tokenRingMLStatsRingPurgeEvents {
          type yang:counter32;
          tailf:snmp-name "tokenRingMLStatsRingPurgeEvents";
        }
        leaf tokenRingMLStatsRingPurgePkts {
          type yang:counter32;
          tailf:snmp-name "tokenRingMLStatsRingPurgePkts";
        }
        leaf tokenRingMLStatsBeaconEvents {
          type yang:counter32;
          tailf:snmp-name "tokenRingMLStatsBeaconEvents";
        }
        leaf tokenRingMLStatsBeaconTime {
          type TimeInterval;
          tailf:snmp-name "tokenRingMLStatsBeaconTime";
        }
        leaf tokenRingMLStatsBeaconPkts {
          type yang:counter32;
          tailf:snmp-name "tokenRingMLStatsBeaconPkts";
        }
        leaf tokenRingMLStatsClaimTokenEvents {
          type yang:counter32;
          tailf:snmp-name "tokenRingMLStatsClaimTokenEvents";
        }
        leaf tokenRingMLStatsClaimTokenPkts {
          type yang:counter32;
          tailf:snmp-name "tokenRingMLStatsClaimTokenPkts";
        }
        leaf tokenRingMLStatsNAUNChanges {
          type yang:counter32;
          tailf:snmp-name "tokenRingMLStatsNAUNChanges";
        }
        leaf tokenRingMLStatsLineErrors {
          type yang:counter32;
          tailf:snmp-name "tokenRingMLStatsLineErrors";
        }
        leaf tokenRingMLStatsInternalErrors {
          type yang:counter32;
          tailf:snmp-name "tokenRingMLStatsInternalErrors";
        }
        leaf tokenRingMLStatsBurstErrors {
          type yang:counter32;
          tailf:snmp-name "tokenRingMLStatsBurstErrors";
        }
        leaf tokenRingMLStatsACErrors {
          type yang:counter32;
          tailf:snmp-name "tokenRingMLStatsACErrors";
        }
        leaf tokenRingMLStatsAbortErrors {
          type yang:counter32;
          tailf:snmp-name "tokenRingMLStatsAbortErrors";
        }
        leaf tokenRingMLStatsLostFrameErrors {
          type yang:counter32;
          tailf:snmp-name "tokenRingMLStatsLostFrameErrors";
        }
        leaf tokenRingMLStatsCongestionErrors {
          type yang:counter32;
          tailf:snmp-name "tokenRingMLStatsCongestionErrors";
        }
        leaf tokenRingMLStatsFrameCopiedErrors {
          type yang:counter32;
          tailf:snmp-name "tokenRingMLStatsFrameCopiedErrors";
        }
        leaf tokenRingMLStatsFrequencyErrors {
          type yang:counter32;
          tailf:snmp-name "tokenRingMLStatsFrequencyErrors";
        }
        leaf tokenRingMLStatsTokenErrors {
          type yang:counter32;
          tailf:snmp-name "tokenRingMLStatsTokenErrors";
        }
        leaf tokenRingMLStatsSoftErrorReports {
          type yang:counter32;
          tailf:snmp-name "tokenRingMLStatsSoftErrorReports";
        }
        leaf tokenRingMLStatsRingPollEvents {
          type yang:counter32;
          tailf:snmp-name "tokenRingMLStatsRingPollEvents";
        }
        leaf tokenRingMLStatsOwner {
          type RMON-MIB:OwnerString;
          tailf:snmp-name "tokenRingMLStatsOwner";
        }
        leaf tokenRingMLStatsStatus {
          type RMON-MIB:EntryStatus;
          tailf:snmp-name "tokenRingMLStatsStatus";
        }
      }
    }
    container tokenRingPStatsTable {
      list tokenRingPStatsEntry {
        key "tokenRingPStatsIndex";
        tailf:sort-order "snmp";
        tailf:snmp-name "tokenRingPStatsTable";
        leaf tokenRingPStatsIndex {
          type tokenRingPStatsIndexType;
          tailf:snmp-name "tokenRingPStatsIndex";
        }
        leaf tokenRingPStatsDataSource {
          type yang:object-identifier;
          tailf:snmp-name "tokenRingPStatsDataSource";
        }
        leaf tokenRingPStatsDropEvents {
          type yang:counter32;
          tailf:snmp-name "tokenRingPStatsDropEvents";
        }
        leaf tokenRingPStatsDataOctets {
          type yang:counter32;
          tailf:snmp-name "tokenRingPStatsDataOctets";
        }
        leaf tokenRingPStatsDataPkts {
          type yang:counter32;
          tailf:snmp-name "tokenRingPStatsDataPkts";
        }
        leaf tokenRingPStatsDataBroadcastPkts {
          type yang:counter32;
          tailf:snmp-name "tokenRingPStatsDataBroadcastPkts";
        }
        leaf tokenRingPStatsDataMulticastPkts {
          type yang:counter32;
          tailf:snmp-name "tokenRingPStatsDataMulticastPkts";
        }
        leaf tokenRingPStatsDataPkts18to63Octets {
          type yang:counter32;
          tailf:snmp-name "tokenRingPStatsDataPkts18to63Octets";
        }
        leaf tokenRingPStatsDataPkts64to127Octets {
          type yang:counter32;
          tailf:snmp-name "tokenRingPStatsDataPkts64to127Octets";
        }
        leaf tokenRingPStatsDataPkts128to255Octets {
          type yang:counter32;
          tailf:snmp-name "tokenRingPStatsDataPkts128to255Octets";
        }
        leaf tokenRingPStatsDataPkts256to511Octets {
          type yang:counter32;
          tailf:snmp-name "tokenRingPStatsDataPkts256to511Octets";
        }
        leaf tokenRingPStatsDataPkts512to1023Octets {
          type yang:counter32;
          tailf:snmp-name "tokenRingPStatsDataPkts512to1023Octets";
        }
        leaf tokenRingPStatsDataPkts1024to2047Octets {
          type yang:counter32;
          tailf:snmp-name "tokenRingPStatsDataPkts1024to2047Octets";
        }
        leaf tokenRingPStatsDataPkts2048to4095Octets {
          type yang:counter32;
          tailf:snmp-name "tokenRingPStatsDataPkts2048to4095Octets";
        }
        leaf tokenRingPStatsDataPkts4096to8191Octets {
          type yang:counter32;
          tailf:snmp-name "tokenRingPStatsDataPkts4096to8191Octets";
        }
        leaf tokenRingPStatsDataPkts8192to18000Octets {
          type yang:counter32;
          tailf:snmp-name "tokenRingPStatsDataPkts8192to18000Octets";
        }
        leaf tokenRingPStatsDataPktsGreaterThan18000Octets {
          type yang:counter32;
          tailf:snmp-name "tokenRingPStatsDataPktsGreaterThan18000Octets";
        }
        leaf tokenRingPStatsOwner {
          type RMON-MIB:OwnerString;
          tailf:snmp-name "tokenRingPStatsOwner";
        }
        leaf tokenRingPStatsStatus {
          type RMON-MIB:EntryStatus;
          tailf:snmp-name "tokenRingPStatsStatus";
        }
      }
    }
    container tokenRingMLHistoryTable {
      list tokenRingMLHistoryEntry {
        key "tokenRingMLHistoryIndex tokenRingMLHistorySampleIndex";
        tailf:sort-order "snmp";
        tailf:snmp-name "tokenRingMLHistoryTable";
        leaf tokenRingMLHistoryIndex {
          type tokenRingMLHistoryIndexType;
          tailf:snmp-name "tokenRingMLHistoryIndex";
        }
        leaf tokenRingMLHistorySampleIndex {
          type int32;
          tailf:snmp-name "tokenRingMLHistorySampleIndex";
        }
        leaf tokenRingMLHistoryIntervalStart {
          type yang:timeticks;
          tailf:snmp-name "tokenRingMLHistoryIntervalStart";
        }
        leaf tokenRingMLHistoryDropEvents {
          type yang:counter32;
          tailf:snmp-name "tokenRingMLHistoryDropEvents";
        }
        leaf tokenRingMLHistoryMacOctets {
          type yang:counter32;
          tailf:snmp-name "tokenRingMLHistoryMacOctets";
        }
        leaf tokenRingMLHistoryMacPkts {
          type yang:counter32;
          tailf:snmp-name "tokenRingMLHistoryMacPkts";
        }
        leaf tokenRingMLHistoryRingPurgeEvents {
          type yang:counter32;
          tailf:snmp-name "tokenRingMLHistoryRingPurgeEvents";
        }
        leaf tokenRingMLHistoryRingPurgePkts {
          type yang:counter32;
          tailf:snmp-name "tokenRingMLHistoryRingPurgePkts";
        }
        leaf tokenRingMLHistoryBeaconEvents {
          type yang:counter32;
          tailf:snmp-name "tokenRingMLHistoryBeaconEvents";
        }
        leaf tokenRingMLHistoryBeaconTime {
          type TimeInterval;
          tailf:snmp-name "tokenRingMLHistoryBeaconTime";
        }
        leaf tokenRingMLHistoryBeaconPkts {
          type yang:counter32;
          tailf:snmp-name "tokenRingMLHistoryBeaconPkts";
        }
        leaf tokenRingMLHistoryClaimTokenEvents {
          type yang:counter32;
          tailf:snmp-name "tokenRingMLHistoryClaimTokenEvents";
        }
        leaf tokenRingMLHistoryClaimTokenPkts {
          type yang:counter32;
          tailf:snmp-name "tokenRingMLHistoryClaimTokenPkts";
        }
        leaf tokenRingMLHistoryNAUNChanges {
          type yang:counter32;
          tailf:snmp-name "tokenRingMLHistoryNAUNChanges";
        }
        leaf tokenRingMLHistoryLineErrors {
          type yang:counter32;
          tailf:snmp-name "tokenRingMLHistoryLineErrors";
        }
        leaf tokenRingMLHistoryInternalErrors {
          type yang:counter32;
          tailf:snmp-name "tokenRingMLHistoryInternalErrors";
        }
        leaf tokenRingMLHistoryBurstErrors {
          type yang:counter32;
          tailf:snmp-name "tokenRingMLHistoryBurstErrors";
        }
        leaf tokenRingMLHistoryACErrors {
          type yang:counter32;
          tailf:snmp-name "tokenRingMLHistoryACErrors";
        }
        leaf tokenRingMLHistoryAbortErrors {
          type yang:counter32;
          tailf:snmp-name "tokenRingMLHistoryAbortErrors";
        }
        leaf tokenRingMLHistoryLostFrameErrors {
          type yang:counter32;
          tailf:snmp-name "tokenRingMLHistoryLostFrameErrors";
        }
        leaf tokenRingMLHistoryCongestionErrors {
          type yang:counter32;
          tailf:snmp-name "tokenRingMLHistoryCongestionErrors";
        }
        leaf tokenRingMLHistoryFrameCopiedErrors {
          type yang:counter32;
          tailf:snmp-name "tokenRingMLHistoryFrameCopiedErrors";
        }
        leaf tokenRingMLHistoryFrequencyErrors {
          type yang:counter32;
          tailf:snmp-name "tokenRingMLHistoryFrequencyErrors";
        }
        leaf tokenRingMLHistoryTokenErrors {
          type yang:counter32;
          tailf:snmp-name "tokenRingMLHistoryTokenErrors";
        }
        leaf tokenRingMLHistorySoftErrorReports {
          type yang:counter32;
          tailf:snmp-name "tokenRingMLHistorySoftErrorReports";
        }
        leaf tokenRingMLHistoryRingPollEvents {
          type yang:counter32;
          tailf:snmp-name "tokenRingMLHistoryRingPollEvents";
        }
        leaf tokenRingMLHistoryActiveStations {
          type int32;
          tailf:snmp-name "tokenRingMLHistoryActiveStations";
        }
      }
    }
    container tokenRingPHistoryTable {
      list tokenRingPHistoryEntry {
        key "tokenRingPHistoryIndex tokenRingPHistorySampleIndex";
        tailf:sort-order "snmp";
        tailf:snmp-name "tokenRingPHistoryTable";
        leaf tokenRingPHistoryIndex {
          type tokenRingPHistoryIndexType;
          tailf:snmp-name "tokenRingPHistoryIndex";
        }
        leaf tokenRingPHistorySampleIndex {
          type int32;
          tailf:snmp-name "tokenRingPHistorySampleIndex";
        }
        leaf tokenRingPHistoryIntervalStart {
          type yang:timeticks;
          tailf:snmp-name "tokenRingPHistoryIntervalStart";
        }
        leaf tokenRingPHistoryDropEvents {
          type yang:counter32;
          tailf:snmp-name "tokenRingPHistoryDropEvents";
        }
        leaf tokenRingPHistoryDataOctets {
          type yang:counter32;
          tailf:snmp-name "tokenRingPHistoryDataOctets";
        }
        leaf tokenRingPHistoryDataPkts {
          type yang:counter32;
          tailf:snmp-name "tokenRingPHistoryDataPkts";
        }
        leaf tokenRingPHistoryDataBroadcastPkts {
          type yang:counter32;
          tailf:snmp-name "tokenRingPHistoryDataBroadcastPkts";
        }
        leaf tokenRingPHistoryDataMulticastPkts {
          type yang:counter32;
          tailf:snmp-name "tokenRingPHistoryDataMulticastPkts";
        }
        leaf tokenRingPHistoryDataPkts18to63Octets {
          type yang:counter32;
          tailf:snmp-name "tokenRingPHistoryDataPkts18to63Octets";
        }
        leaf tokenRingPHistoryDataPkts64to127Octets {
          type yang:counter32;
          tailf:snmp-name "tokenRingPHistoryDataPkts64to127Octets";
        }
        leaf tokenRingPHistoryDataPkts128to255Octets {
          type yang:counter32;
          tailf:snmp-name "tokenRingPHistoryDataPkts128to255Octets";
        }
        leaf tokenRingPHistoryDataPkts256to511Octets {
          type yang:counter32;
          tailf:snmp-name "tokenRingPHistoryDataPkts256to511Octets";
        }
        leaf tokenRingPHistoryDataPkts512to1023Octets {
          type yang:counter32;
          tailf:snmp-name "tokenRingPHistoryDataPkts512to1023Octets";
        }
        leaf tokenRingPHistoryDataPkts1024to2047Octets {
          type yang:counter32;
          tailf:snmp-name "tokenRingPHistoryDataPkts1024to2047Octets";
        }
        leaf tokenRingPHistoryDataPkts2048to4095Octets {
          type yang:counter32;
          tailf:snmp-name "tokenRingPHistoryDataPkts2048to4095Octets";
        }
        leaf tokenRingPHistoryDataPkts4096to8191Octets {
          type yang:counter32;
          tailf:snmp-name "tokenRingPHistoryDataPkts4096to8191Octets";
        }
        leaf tokenRingPHistoryDataPkts8192to18000Octets {
          type yang:counter32;
          tailf:snmp-name "tokenRingPHistoryDataPkts8192to18000Octets";
        }
        leaf tokenRingPHistoryDataPktsGreaterThan18000Octets {
          type yang:counter32;
          tailf:snmp-name "tokenRingPHistoryDataPktsGreaterThan18000Octets";
        }
      }
    }
    container ringStationControlTable {
      list ringStationControlEntry {
        key "ringStationControlIfIndex";
        tailf:sort-order "snmp";
        tailf:snmp-name "ringStationControlTable";
        leaf ringStationControlIfIndex {
          type ringStationControlIfIndexType;
          tailf:snmp-name "ringStationControlIfIndex";
        }
        leaf ringStationControlTableSize {
          type int32;
          tailf:snmp-name "ringStationControlTableSize";
        }
        leaf ringStationControlActiveStations {
          type int32;
          tailf:snmp-name "ringStationControlActiveStations";
        }
        leaf ringStationControlRingState {
          type ringStationControlRingStateType;
          tailf:snmp-name "ringStationControlRingState";
        }
        leaf ringStationControlBeaconSender {
          type MacAddress;
          tailf:snmp-name "ringStationControlBeaconSender";
        }
        leaf ringStationControlBeaconNAUN {
          type MacAddress;
          tailf:snmp-name "ringStationControlBeaconNAUN";
        }
        leaf ringStationControlActiveMonitor {
          type MacAddress;
          tailf:snmp-name "ringStationControlActiveMonitor";
        }
        leaf ringStationControlOrderChanges {
          type yang:counter32;
          tailf:snmp-name "ringStationControlOrderChanges";
        }
        leaf ringStationControlOwner {
          type RMON-MIB:OwnerString;
          tailf:snmp-name "ringStationControlOwner";
        }
        leaf ringStationControlStatus {
          type RMON-MIB:EntryStatus;
          tailf:snmp-name "ringStationControlStatus";
        }
      }
    }
    container ringStationTable {
      list ringStationEntry {
        key "ringStationIfIndex ringStationMacAddress";
        tailf:sort-order "snmp";
        tailf:snmp-name "ringStationTable";
        leaf ringStationIfIndex {
          type int32;
          tailf:snmp-name "ringStationIfIndex";
        }
        leaf ringStationMacAddress {
          type MacAddress;
          tailf:snmp-name "ringStationMacAddress";
        }
        leaf ringStationLastNAUN {
          type MacAddress;
          tailf:snmp-name "ringStationLastNAUN";
        }
        leaf ringStationStationStatus {
          type ringStationStationStatusType;
          tailf:snmp-name "ringStationStationStatus";
        }
        leaf ringStationLastEnterTime {
          type yang:timeticks;
          tailf:snmp-name "ringStationLastEnterTime";
        }
        leaf ringStationLastExitTime {
          type yang:timeticks;
          tailf:snmp-name "ringStationLastExitTime";
        }
        leaf ringStationDuplicateAddresses {
          type yang:counter32;
          tailf:snmp-name "ringStationDuplicateAddresses";
        }
        leaf ringStationInLineErrors {
          type yang:counter32;
          tailf:snmp-name "ringStationInLineErrors";
        }
        leaf ringStationOutLineErrors {
          type yang:counter32;
          tailf:snmp-name "ringStationOutLineErrors";
        }
        leaf ringStationInternalErrors {
          type yang:counter32;
          tailf:snmp-name "ringStationInternalErrors";
        }
        leaf ringStationInBurstErrors {
          type yang:counter32;
          tailf:snmp-name "ringStationInBurstErrors";
        }
        leaf ringStationOutBurstErrors {
          type yang:counter32;
          tailf:snmp-name "ringStationOutBurstErrors";
        }
        leaf ringStationACErrors {
          type yang:counter32;
          tailf:snmp-name "ringStationACErrors";
        }
        leaf ringStationAbortErrors {
          type yang:counter32;
          tailf:snmp-name "ringStationAbortErrors";
        }
        leaf ringStationLostFrameErrors {
          type yang:counter32;
          tailf:snmp-name "ringStationLostFrameErrors";
        }
        leaf ringStationCongestionErrors {
          type yang:counter32;
          tailf:snmp-name "ringStationCongestionErrors";
        }
        leaf ringStationFrameCopiedErrors {
          type yang:counter32;
          tailf:snmp-name "ringStationFrameCopiedErrors";
        }
        leaf ringStationFrequencyErrors {
          type yang:counter32;
          tailf:snmp-name "ringStationFrequencyErrors";
        }
        leaf ringStationTokenErrors {
          type yang:counter32;
          tailf:snmp-name "ringStationTokenErrors";
        }
        leaf ringStationInBeaconErrors {
          type yang:counter32;
          tailf:snmp-name "ringStationInBeaconErrors";
        }
        leaf ringStationOutBeaconErrors {
          type yang:counter32;
          tailf:snmp-name "ringStationOutBeaconErrors";
        }
        leaf ringStationInsertions {
          type yang:counter32;
          tailf:snmp-name "ringStationInsertions";
        }
      }
    }
    container ringStationOrderTable {
      list ringStationOrderEntry {
        key "ringStationOrderIfIndex ringStationOrderOrderIndex";
        tailf:sort-order "snmp";
        tailf:snmp-name "ringStationOrderTable";
        leaf ringStationOrderIfIndex {
          type int32;
          tailf:snmp-name "ringStationOrderIfIndex";
        }
        leaf ringStationOrderOrderIndex {
          type int32;
          tailf:snmp-name "ringStationOrderOrderIndex";
        }
        leaf ringStationOrderMacAddress {
          type MacAddress;
          tailf:snmp-name "ringStationOrderMacAddress";
        }
      }
    }
    container ringStationConfigControlTable {
      list ringStationConfigControlEntry {
        key "ringStationConfigControlIfIndex ringStationConfigControlMacAddress";
        tailf:sort-order "snmp";
        tailf:snmp-name "ringStationConfigControlTable";
        leaf ringStationConfigControlIfIndex {
          type int32;
          tailf:snmp-name "ringStationConfigControlIfIndex";
        }
        leaf ringStationConfigControlMacAddress {
          type MacAddress;
          tailf:snmp-name "ringStationConfigControlMacAddress";
        }
        leaf ringStationConfigControlRemove {
          type ringStationConfigControlRemoveType;
          tailf:snmp-name "ringStationConfigControlRemove";
        }
        leaf ringStationConfigControlUpdateStats {
          type ringStationConfigControlUpdateStatsType;
          tailf:snmp-name "ringStationConfigControlUpdateStats";
        }
      }
    }
    container ringStationConfigTable {
      list ringStationConfigEntry {
        key "ringStationConfigIfIndex ringStationConfigMacAddress";
        tailf:sort-order "snmp";
        tailf:snmp-name "ringStationConfigTable";
        leaf ringStationConfigIfIndex {
          type int32;
          tailf:snmp-name "ringStationConfigIfIndex";
        }
        leaf ringStationConfigMacAddress {
          type MacAddress;
          tailf:snmp-name "ringStationConfigMacAddress";
        }
        leaf ringStationConfigUpdateTime {
          type yang:timeticks;
          tailf:snmp-name "ringStationConfigUpdateTime";
        }
        leaf ringStationConfigLocation {
          type ringStationConfigLocationType;
          tailf:snmp-name "ringStationConfigLocation";
        }
        leaf ringStationConfigMicrocode {
          type ringStationConfigMicrocodeType;
          tailf:snmp-name "ringStationConfigMicrocode";
        }
        leaf ringStationConfigGroupAddress {
          type ringStationConfigGroupAddressType;
          tailf:snmp-name "ringStationConfigGroupAddress";
        }
        leaf ringStationConfigFunctionalAddress {
          type ringStationConfigFunctionalAddressType;
          tailf:snmp-name "ringStationConfigFunctionalAddress";
        }
      }
    }
    container sourceRoutingStatsTable {
      list sourceRoutingStatsEntry {
        key "sourceRoutingStatsIfIndex";
        tailf:sort-order "snmp";
        tailf:snmp-name "sourceRoutingStatsTable";
        leaf sourceRoutingStatsIfIndex {
          type int32;
          tailf:snmp-name "sourceRoutingStatsIfIndex";
        }
        leaf sourceRoutingStatsRingNumber {
          type int32;
          tailf:snmp-name "sourceRoutingStatsRingNumber";
        }
        leaf sourceRoutingStatsInFrames {
          type yang:counter32;
          tailf:snmp-name "sourceRoutingStatsInFrames";
        }
        leaf sourceRoutingStatsOutFrames {
          type yang:counter32;
          tailf:snmp-name "sourceRoutingStatsOutFrames";
        }
        leaf sourceRoutingStatsThroughFrames {
          type yang:counter32;
          tailf:snmp-name "sourceRoutingStatsThroughFrames";
        }
        leaf sourceRoutingStatsAllRoutesBroadcastFrames {
          type yang:counter32;
          tailf:snmp-name "sourceRoutingStatsAllRoutesBroadcastFrames";
        }
        leaf sourceRoutingStatsSingleRouteBroadcastFrames {
          type yang:counter32;
          tailf:snmp-name "sourceRoutingStatsSingleRouteBroadcastFrames";
        }
        leaf sourceRoutingStatsInOctets {
          type yang:counter32;
          tailf:snmp-name "sourceRoutingStatsInOctets";
        }
        leaf sourceRoutingStatsOutOctets {
          type yang:counter32;
          tailf:snmp-name "sourceRoutingStatsOutOctets";
        }
        leaf sourceRoutingStatsThroughOctets {
          type yang:counter32;
          tailf:snmp-name "sourceRoutingStatsThroughOctets";
        }
        leaf sourceRoutingStatsAllRoutesBroadcastOctets {
          type yang:counter32;
          tailf:snmp-name "sourceRoutingStatsAllRoutesBroadcastOctets";
        }
        leaf sourceRoutingStatsSingleRoutesBroadcastOctets {
          type yang:counter32;
          tailf:snmp-name "sourceRoutingStatsSingleRoutesBroadcastOctets";
        }
        leaf sourceRoutingStatsLocalLLCFrames {
          type yang:counter32;
          tailf:snmp-name "sourceRoutingStatsLocalLLCFrames";
        }
        leaf sourceRoutingStats1HopFrames {
          type yang:counter32;
          tailf:snmp-name "sourceRoutingStats1HopFrames";
        }
        leaf sourceRoutingStats2HopsFrames {
          type yang:counter32;
          tailf:snmp-name "sourceRoutingStats2HopsFrames";
        }
        leaf sourceRoutingStats3HopsFrames {
          type yang:counter32;
          tailf:snmp-name "sourceRoutingStats3HopsFrames";
        }
        leaf sourceRoutingStats4HopsFrames {
          type yang:counter32;
          tailf:snmp-name "sourceRoutingStats4HopsFrames";
        }
        leaf sourceRoutingStats5HopsFrames {
          type yang:counter32;
          tailf:snmp-name "sourceRoutingStats5HopsFrames";
        }
        leaf sourceRoutingStats6HopsFrames {
          type yang:counter32;
          tailf:snmp-name "sourceRoutingStats6HopsFrames";
        }
        leaf sourceRoutingStats7HopsFrames {
          type yang:counter32;
          tailf:snmp-name "sourceRoutingStats7HopsFrames";
        }
        leaf sourceRoutingStats8HopsFrames {
          type yang:counter32;
          tailf:snmp-name "sourceRoutingStats8HopsFrames";
        }
        leaf sourceRoutingStatsMoreThan8HopsFrames {
          type yang:counter32;
          tailf:snmp-name "sourceRoutingStatsMoreThan8HopsFrames";
        }
        leaf sourceRoutingStatsOwner {
          type RMON-MIB:OwnerString;
          tailf:snmp-name "sourceRoutingStatsOwner";
        }
        leaf sourceRoutingStatsStatus {
          type RMON-MIB:EntryStatus;
          tailf:snmp-name "sourceRoutingStatsStatus";
        }
      }
    }
  }

  typedef MacAddress {
    type tailf:hex-list {
      tailf:value-length "6";
    }
  }

  typedef TimeInterval {
    type int32 {
      range "-2147483648 .. 2147483647";
    }
  }

  typedef tokenRingMLStatsIndexType {
    type int32 {
      range "1 .. 65535";
    }
  }

  typedef tokenRingPStatsIndexType {
    type int32 {
      range "1 .. 65535";
    }
  }

  typedef tokenRingMLHistoryIndexType {
    type int32 {
      range "1 .. 65535";
    }
  }

  typedef tokenRingPHistoryIndexType {
    type int32 {
      range "1 .. 65535";
    }
  }

  typedef ringStationControlIfIndexType {
    type int32 {
      range "1 .. 65535";
    }
  }

  typedef ringStationControlRingStateType {
    type enumeration {
      enum "normalOperation" {
        value 1;
      }
      enum "ringPurgeState" {
        value 2;
      }
      enum "claimTokenState" {
        value 3;
      }
      enum "beaconFrameStreamingState" {
        value 4;
      }
      enum "beaconBitStreamingState" {
        value 5;
      }
      enum "beaconRingSignalLossState" {
        value 6;
      }
      enum "beaconSetRecoveryModeState" {
        value 7;
      }
    }
  }

  typedef ringStationStationStatusType {
    type enumeration {
      enum "active" {
        value 1;
      }
      enum "inactive" {
        value 2;
      }
      enum "forcedRemoval" {
        value 3;
      }
    }
  }

  typedef ringStationConfigControlRemoveType {
    type enumeration {
      enum "stable" {
        value 1;
      }
      enum "removing" {
        value 2;
      }
    }
  }

  typedef ringStationConfigControlUpdateStatsType {
    type enumeration {
      enum "stable" {
        value 1;
      }
      enum "updating" {
        value 2;
      }
    }
  }

  typedef ringStationConfigLocationType {
    type tailf:hex-list {
      tailf:value-length "4";
    }
  }

  typedef ringStationConfigMicrocodeType {
    type tailf:hex-list {
      tailf:value-length "10";
    }
  }

  typedef ringStationConfigGroupAddressType {
    type tailf:hex-list {
      tailf:value-length "4";
    }
  }

  typedef ringStationConfigFunctionalAddressType {
    type tailf:hex-list {
      tailf:value-length "4";
    }
  }
}
