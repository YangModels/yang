module arcos-isis-types {
  yang-version 1.1;
  namespace "http://yang.arrcus.com/arcos/isis/types";
  prefix arc-isis-types;

  import openconfig-isis-types {
    prefix "oc-isis-types";
  }

  organization
    "Arrcus, Inc.";

  contact
    "Arrcus, Inc.
     Customer Service
     Postal: 2077 Gateway Place
     San Jose, CA 95110
     Tel: +1 408 884-1965
     E-mail: yang-support@arrcus.com";

  description
    "This module defines Arrcus implementation
     of the IS-IS types.

     Copyright (c) 2023 by Arrcus, Inc.
     All rights reserved.";

  revision 2024-10-03 {
    description
      "Move prefix attribute flags identity ref type to ISIS types";
  }

  revision 2023-09-24 {
    description
      "Add delay overload reset trigger type";
  }

  revision 2019-11-04 {
    description
      "Initial module for extended IS-IS type definitions";
  }

  identity level-bits {
    description "Base identitfy type for level-bits.";
  }

  identity LEVEL_NONE {
    base level-bits;
    description "Identitfy for no level-bits set.";
  }

  identity LEVEL_1 {
    base level-bits;
    description "Identitfy for level 1 bit set.";
  }

  identity LEVEL_2 {
    base level-bits;
    description "Identitfy for level 2 bit set.";
  }

  identity LEVEL_1_2 {
    base level-bits;
    description "Identitfy for level 1 and 2 bits set.";
  }

  identity WAIT_DELAY {
    base oc-isis-types:OVERLOAD_RESET_TRIGGER_TYPE;
    description
      "Base identity type for resetting Overload Bit when
       configured delay time expires.";
  }

  typedef network-type {
    type enumeration {
      enum UNKNOWN {
        description "This enum describes a unknown interface.";
      }
      enum LOOPBACK {
        description "This enum describes a loopback interface.";
      }
      enum POINT_TO_POINT {
        description "This enum describes a point-to-point interface.";
      }
      enum BROADCAST {
        description "This enum describes a broadcast interface.";
      }
    }
    description
        "This type defines ISIS interface network types.";
  }

  typedef node-id {
    type string {
      pattern
        '[0-9A-Fa-f]{4}\.[0-9A-Fa-f]{4}\.[0-9A-Fa-f]{4}\.[0-9][0-9]';
    }
    description
      "This type defines ISIS node ID. ISIS node ID type should be in
       the form of xxxx.xxxx.xxxx.xx. It is used to represent LAN ID
       and circuit ID";
  }

  typedef system-name {
    type string {
      pattern '.*';
    }
    description
      "This type defines ISIS node name. ISIS system ID type should be in
       the form of <name>, where <name> is either a hostname or in the
       format 'XXXX.XXXX.XXXX'.";
  }

  typedef node-name {
    type string {
      pattern '.*\.[0-9A-Fa-f]{2}';
    }
    description
      "This type defines ISIS node name. ISIS node ID type should be in
       the form of <name>.xx, where <name> is either a hostname or in the
       format 'XXXX.XXXX.XXXX'. It is used to represent LAN ID and circuit ID";
  }

  typedef lsp-name {
    type string {
      pattern '.*\.[0-9A-Fa-f]{2}-[0-9A-Fa-f]{2}';
    }
    description
      "This type defines ISIS LSP name. ISIS LSP name type should be in
      the form of <name>.xx-xx, where <name> is either a hostname or in the
      format 'XXXX.XXXX.XXXX'.";
  }

  /*
   * LSP Prefix Reachability TLV sub-TLV 4 Prefix Attribute Flags
   */
  identity ISIS_PREFIX_ATTRIBUTES_FLAG {
    description
      "Base identity for ISIS sub-TLV 4 of TLVs 27, 135, 235, 236, and 237";
    reference
      "RFC7794: IS-IS Prefix Attributes for Extended IPv4 and IPv6
       Reachability. sub-TLV 4.";
  }

  identity ISIS_PREFIX_EXTERNAL_FLAG {
    base "ISIS_PREFIX_ATTRIBUTES_FLAG";
    description
      "External prefix flag. Set if the prefix has been
       redistributed from another protocol. This includes the case
       where multiple virtual routers are supported and the source of
       the redistributed prefix is another IS-IS instance.";
    reference
      "RFC7794: IS-IS Prefix Attributes for Extended IPv4 and IPv6
       Reachability. sub-TLV 4.";
  }

  identity ISIS_PREFIX_READVERTISEMENT_FLAG {
    base "ISIS_PREFIX_ATTRIBUTES_FLAG";
    description
      "Readvertisement flag. Set when the prefix has been leaked
       from one level to another (upwards or downwards).";
    reference
      "RFC7794: IS-IS Prefix Attributes for Extended IPv4 and IPv6
       Reachability. sub-TLV 4.";
  }

  identity ISIS_PREFIX_NODE_FLAG {
    base "ISIS_PREFIX_ATTRIBUTES_FLAG";
    description
      "Node flag. Set when the prefix identifies the advertising
       router, i.e., the prefix is a host prefix advertising  a
       globally reachable address typically associated with a
       loopback address.";
    reference
      "RFC7794: IS-IS Prefix Attributes for Extended IPv4 and IPv6
       Reachability. sub-TLV 4.";
  }

  identity ISIS_PREFIX_ANYCAST_FLAG {
    base "ISIS_PREFIX_ATTRIBUTES_FLAG";
    description
      "When the prefix/SRv6 locator is configured as anycast, the ANYCAST
       flag SHOULD be set. Otherwise, this flag MUST be clear.";
    reference
      "draft-ietf-lsr-isis-srv6-extensions";
  }

  identity ISIS_PREFIX_UNREACHABLE_FLAG {
    base "ISIS_PREFIX_ATTRIBUTES_FLAG";
    description
      "Unreachable prefix flag. Indicates that the prefix is unreachable due to the unplanned reason";
    reference
      "draft-ietf-lsr-igp-ureach-prefix-announce-02";
  }

  identity ISIS_PREFIX_UNREACHABLE_PLANNED_FLAG {
    base "ISIS_PREFIX_ATTRIBUTES_FLAG";
    description
      "Unreachable planned prefix flag. Indicates that the prefix is unreachable due to a planned reason";
    reference
      "draft-ietf-lsr-igp-ureach-prefix-announce-02";
  }

  typedef isis-prefix-attributes-flags-type {
    type union {
      type identityref {
        base "ISIS_PREFIX_ATTRIBUTES_FLAG";
      }
      type uint8 {
        range "0..7";
      }
    }
    description
      "Type definition for ISIS prefix attributes flags. Unknown
       flags are represented as an integer describing the bit position
       of the flag.";
    reference
      "RFC7794: Section 2.1 IPv4/IPv6 Extended Reachability Attribute Flags";
  }
}
