submodule arcos-hardware-uft {

  belongs-to arcos-hardware {
    prefix arc-hw;
  }

  grouping hardware-uft-profile {
    description
      "config uft partition";

	  leaf uft-profile {
	    type uint32;
	    description "Select uft profile";
	  }
  }
}
