module arcos-apply-path {
  yang-version 1.1;
  namespace "http://yang.arrcus.com/arcos/apply/path";
  prefix arc-app-path;

  import ietf-inet-types {
    prefix inet;
  }

  organization
    "Arrcus, Inc.";
  contact
    "Arrcus, Inc.
     2077 Gateway Place
     Suite 400
     San Jose, CA 95110

     E-mail: yang-support@arrcus.com";

  description
    "YANG data-model for apply-path feature.
    
     Copyright (c) 2024 by Arrcus, Inc.
     All rights reserved.";

  revision 2024-02-19 {
    description
      "Initial revision.";
  }
  grouping apply-paths-top {
    description
      "Grouping for apply-paths config and state.";

    leaf name {
      type string;
      description
        "A unique name for the apply-path.";
    }

    leaf path {
      type string;
      description
        "A flat string that indicates the path that needs to be
         applied to match the configuration.";
    }
  }

  container apply-paths {
    description
      "Container for the apply-path feature.";

    list apply-path {
      key name;

      leaf name {
        type leafref {
          path "../config/name";
        }
      }

      container config {
        uses apply-paths-top;
      }

      container state {
        config false;
        uses apply-paths-top;

        list address-list {
          key "address";
          leaf address {
            type inet:ip-address;
          }
        }
        description
          "list of prefixes learnt by appying the apply-path.";

        leaf cfg-pending {
          type boolean;
          description
            "Indicates if the running configuration is being read";
        }
      }
    }
  }
}
