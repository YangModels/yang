module arcos-ospfv3 {

  yang-version "1.1";

  namespace "http://yang.arrcus.com/arcos/ospfv3";

  prefix "arc-ospfv3";

  import openconfig-network-instance { prefix "oc-netinst"; }
  import arcos-ospf { prefix "arc-ospf"; }

  // Include submodules
  include arcos-ospfv3-common;
  include arcos-ospfv3-area-interface;
  include arcos-ospfv3-lsdb;

  organization
    "Arrcus, Inc";

  contact
    "Arrcus, Inc.
     2077 Gateway Place
     Suite 400
     San Jose, CA 95110
     
     E-mail: yang-support@arrcus.com";

  description
    "A model for Open Shortest Path First (OSPF) v3 protocol";

  revision "2020-01-01" {
    description
      "Initial version";
  }

  augment "/oc-netinst:network-instances/oc-netinst:network-instance" +
          "/oc-netinst:protocols/oc-netinst:protocol/arc-ospf:ospfv3" +
          "/arc-ospf:global/arc-ospf:maintenance-mode" +
          "/arc-ospf:router-lsa/arc-ospf:config" {
    uses ospfv3-maint-router-lsa-config;
  }

  augment "/oc-netinst:network-instances/oc-netinst:network-instance" +
          "/oc-netinst:protocols/oc-netinst:protocol/arc-ospf:ospfv3" +
          "/arc-ospf:global/arc-ospf:maintenance-mode" +
          "/arc-ospf:router-lsa/arc-ospf:state" {
    uses ospfv3-maint-router-lsa-config;
  }

  augment "/oc-netinst:network-instances/oc-netinst:network-instance" +
          "/oc-netinst:protocols/oc-netinst:protocol/arc-ospf:ospfv3" +
          "/arc-ospf:as-scope" {
    uses ospfv3-lsdb-structure;
  }

  /*
   * Augment ospfv3 areas area
   */
  augment "/oc-netinst:network-instances/oc-netinst:network-instance" +
          "/oc-netinst:protocols/oc-netinst:protocol/arc-ospf:ospfv3" +
          "/arc-ospf:areas/arc-ospf:area" {
    uses ospfv3-lsdb-structure;
  }

  /*
   * Augment ospfv3 areas area interfaces interface
   */
  augment "/oc-netinst:network-instances/oc-netinst:network-instance" +
          "/oc-netinst:protocols/oc-netinst:protocol/arc-ospf:ospfv3" +
          "/arc-ospf:areas/arc-ospf:area" +
          "/arc-ospf:interfaces/arc-ospf:interface" {
    uses ospfv3-lsdb-structure;
  }

  /*
   * Augment ospfv3 areas area interfaces interface config
   */
  augment "/oc-netinst:network-instances/oc-netinst:network-instance" +
          "/oc-netinst:protocols/oc-netinst:protocol/arc-ospf:ospfv3" +
          "/arc-ospf:areas/arc-ospf:area" +
          "/arc-ospf:interfaces/arc-ospf:interface/arc-ospf:config" {
    uses ospfv3-area-interface-config;
  }

  /*
   * Augment ospfv3 areas area interfaces interface state
   */
  augment "/oc-netinst:network-instances/oc-netinst:network-instance" +
          "/oc-netinst:protocols/oc-netinst:protocol/arc-ospf:ospfv3" +
          "/arc-ospf:areas/arc-ospf:area" +
          "/arc-ospf:interfaces/arc-ospf:interface/arc-ospf:state" {
    uses ospfv3-area-interface-config;
  }

  /*
   * Augment ospfv3 areas area interfaces interface neighbors neighbor
   */
  augment "/oc-netinst:network-instances/oc-netinst:network-instance" +
          "/oc-netinst:protocols/oc-netinst:protocol/arc-ospf:ospfv3" +
          "/arc-ospf:areas/arc-ospf:area" +
          "/arc-ospf:interfaces/arc-ospf:interface" +
          "/arc-ospf:neighbors/arc-ospf:neighbor" {
    uses ospfv3-area-interface-neighbor-bfd-structure;
  }

  /*
   * Augment ospfv3 areas area interfaces interface neighbors neighbor state
   */
  augment "/oc-netinst:network-instances/oc-netinst:network-instance" +
          "/oc-netinst:protocols/oc-netinst:protocol/arc-ospf:ospfv3" +
          "/arc-ospf:areas/arc-ospf:area" +
          "/arc-ospf:interfaces/arc-ospf:interface" +
          "/arc-ospf:neighbors/arc-ospf:neighbor/arc-ospf:state" {
    uses ospfv3-area-interface-neighbor-state;
  }
}
