module arcos-bgp-rnh {
  yang-version 1.1;
  namespace "http://yang.arrcus.com/arcos/bgp/rnh";
  prefix arc-bgp-rnh;

  import ietf-inet-types {
    prefix inet;
  }

  import openconfig-network-instance {
    prefix oc-netinst;
  }

  import arcos-openconfig-bgp-types {
    prefix arc-oc-bgp-types;
  }

  import openconfig-bgp-types {
    prefix oc-bgp-types;
  }

  import arcos-srv6-types {
    prefix arc-srv6-types;
  }

  import arcos-evpn {
    prefix arc-evpn;
  }

  organization
    "Arrcus, Inc.";

  contact
    "Arrcus, Inc.
     2077 Gateway Place
     Suite 400
     San Jose, CA 95110
     E-mail: yang-support@arrcus.com";

  description
    "This module defines augmentation for Arrcus
     implementation of the openconfig BGP RIB module.

     Copyright (c) 2016-2023 by Arrcus, Inc.
     All rights reserved.";

  revision 2025-03-13 {
    description "Add RIB-Out reference count";
  }

  revision 2024-06-17 {
    description "Additional attributes for next-hop and sub-next-hop to assist debugging";
  }

  revision 2024-05-25 {
    description "Add resolution information for MUP EXTCOMM next hop";
  }

  revision 2024-03-22 {
    description "Add color extended community for EVPN-IMET and
                 L2-ATTRIBUTE-EXTENDED-COMMUNITY";
  }

  revision 2024-02-27 {
    description "Add ethernet-tag-identifier (ETI) leaf
                 for EVPN-IMET next-hop and sub-next-hop type";
  }

  revision 2024-02-20 {
    description "Add flow-label-received leaf for L2-ATTRIBUTE-EXTENDED-COMMUNITY
                 next-hop and sub-next-hop type";
  }

  revision 2024-01-16 {
    description
      "* Add EVPN-IMET, L2-ATTRIBUTE-EXTENDED-COMMUNITY next-hop type,
       and EVPN-IMET, L2-ATTRIBUTE-EXTENDED-COMMUNITY sub-next-hop type
       * Update nexthop and sub-nexthop oper model to
       to include EVPN-IMET and L2-ATTRIBUTE-EXTENDED-COMMUNITY";
  }

  revision 2023-12-20 {
    description "Add MUP-INTERWORK-LOCATOR sub-next-hop type";
  }

  revision 2023-12-01 {
    description "Add OWN-ADDRESS sub-next-hop type";
  }

  revision 2023-06-30 {
    description "Add resolving-prefix attribute to
                 ISD address sub-next-hop";
  }

  revision 2023-06-02 {
    description "Updated nexthop model to with additional
                 information based on the next-hop type";
  }

  revision 2022-12-28 {
    description "Added sub-nexthop state model";
  }

  typedef next-hop-type {
    type enumeration {
      enum ADDRESS {
        description "Address next-hop";
      }
      enum ADDRESS-INTERFACE {
        description "Address and interface next-hop";
      }
      enum ADDRESS-COLOR {
        description "Address and color next-hop";
      }
      enum MUP-ENDPOINT {
        description "MUP endpoint and color next-hop";
      }
      enum MUP-EXTENDED-COMMUNITY {
        description "MUP extended community next-hop";
      }
      enum LOCAL {
        description "Local next-hop";
      }
      enum LOCAL-MUP {
        description "Local MUP next-hop";
      }
      enum PREFIX {
        description "Prefix next-hop";
      }
      enum EVPN-IMET {
        description "EVPN IMET next-hop";
      }
      enum L2-ATTRIBUTE-EXTENDED-COMMUNITY {
        description "L2 Attribute Extended Community next-hop";
      }
    }
  }

  typedef sub-next-hop-type {
    type enumeration {
      enum PREFIX {
        description "Prefix sub-next-hop";
      }
      enum ADDRESS-INTERFACE {
        description "Address interface sub-next-hop";
      }
      enum ENDPOINT-COLOR {
        description "Endpoint color sub-next-hop";
      }
      enum MUP-ISD-ADDRESS {
        description "MUP ISD address sub-next-hop";
      }
      enum MUP-EXTENDED-COMMUNITY {
        description "MUP extended community sub-next-hop";
      }
      enum IPV4-TUNNEL {
        description "IPv4 Tunnel sub-next-hop";
      }
      enum SRV6-TUNNEL {
        description "SRv6 Tunnel sub-next-hop";
      }
      enum MPLS-LABEL {
        description "MPLS Label sub-next-hop";
      }
      enum SRV6-SID {
        description "SRv6 SID sub-next-hop";
      }
      enum OWN-ADDRESS {
        description "Own Address sub-next-hop";
      }
      enum MUP-INTERWORK-LOCATOR {
        description "MUP interwork locator sub-next-hop";
      }
      enum EVPN-IMET {
        description "EVPN IMET sub-next-hop";
      }
      enum L2-ATTRIBUTE-EXTENDED-COMMUNITY {
        description "L2 Attribute Extended Community sub-next-hop";
      }
    }
  }

  grouping next-hop-resolution-info {
    container resolution {
      description "Resolution information";
      container state {
        leaf mobile-sid {
          type inet:ipv6-address;
          description
            "Resolved Mobile SRv6 SID";
        }
        leaf next-hop-address {
          type inet:ip-address;
          description
            "Nexthop address used for forwarding";
        }
      }
    }
  }

  grouping next-hop-info {
    description
      "Parameters related to a BGP group";
    container state {
      leaf id {
        type string;
        description
          "The next-hop name";
      }

      leaf type {
        type next-hop-type;
        description
          "The next-hop type";
      }

      leaf resolved {
        type boolean;
        description
          "The validity of the next-hop";
      }

      leaf metric {
        type uint32;
        description
          "Metric of the next-hop";
      }

      leaf mpls-label-allocation-enabled {
        type boolean;
        description
          "The MPLS label allocation requested state for this next-hop";
      }

      leaf mpls-label {
        type uint32;
        description
          "Allocated MPLS label";
      }

      leaf srv6-sid-allocation-enabled {
        type boolean;
        description
          "The SRv6 SID allocation requested state for this next-hop";
      }

      leaf srv6-sid {
        type inet:ip-prefix;
        description
          "Allocated SRv6 SID";
      }

      leaf path-count {
        type uint32;
        description
          "The path count";
      }

      leaf neighbor-count {
        type uint32;
        description
          "The neighbor count";
      }

      leaf rib-in-pre-count {
        type uint32;
        description
          "The RIB-In-Pre reference count";
      }

      leaf rib-out-count {
        type uint32;
        description
          "The RIB-Out reference count";
      }

      leaf pseudo-route-count {
        type uint32;
        description
          "Pseudo route reference count";
      }

      leaf used-by-routing-policy {
        type boolean;
        description
          "Set when used by the routing policy";
      }

      leaf last-update-time {
        type string;
        description
          "Last updated timestamp";
      }

      leaf update-pending {
        type boolean;
        description
          "Set when update is pending for the nexthop";
      }
    }
    container sub-nexthops {
      list sub-nexthop {
        key "id";
        leaf id {
          type leafref {
            path "../state/id";
          }
        }
        container state {
          leaf id {
            type string;
            description "Sub nexthop ID";
          }
          leaf type {
            type sub-next-hop-type;
            description "Sub next-hop type";
          }
          leaf must-resolve {
            type boolean;
            description "The sub-nexthop resolution is required";
          }
          leaf resolved {
            type boolean;
            description "Sub next-hop resolution";
          }
          leaf last-update-time {
            type string;
            description
              "Last updated timestamp";
          }
        }
      }
    }
    container tunnel {
      container state {
        leaf source {
          type inet:ip-address;
          description "Tunnel source address";
        }
        leaf endpoint {
          type inet:ip-address;
          description "Tunnel endpoint address";
        }
        leaf endpoint-function {
          type arc-srv6-types:srv6-endpoint-behavior-type;
          description "SRv6 endpoint behaviour";
        }
        leaf srv6-prefix-sid {
          type inet:ipv6-prefix;
          description "SRv6 SID prefix";
        }
      }
    }
    container address {
      container state {
        leaf global {
          type inet:ip-address;
          description
            "The global next-hop address";
        }

        leaf link-local {
          type inet:ip-address;
          description
            "The link-local next-hop address";
        }

        leaf network-instance {
          type oc-netinst:network-instance-ref;
          description
            "The network-instance in which global next-hop is reachable";
        }

        leaf used-by-import-source-paths {
          type boolean;
          description "Used by import source paths";
        }
      }
    }
    container address-interface {
      when "../state/type = 'ADDRESS-INTERFACE'" {
        description "When next-hop is interface bound address";
      }
      container state {
        leaf interface {
          type string;
          description "Interface name";
        }
        leaf interface-index {
          type uint32;
          description "Interface index";
        }
      }
    }
    container address-color {
      when "../state/type = 'ADDRESS-COLOR'" {
        description "When next-hop is address color";
      }
      container state {
        leaf-list color-extended-community {
          type string;
          description
            "Colors value along with flags represented as string";
        }
      }
    }
    container mup-endpoint {
      when "../state/type = 'MUP-ENDPOINT'" {
        description "When next-hop is MUP endpoint";
      }
      uses next-hop-resolution-info;
      container state {
        leaf endpoint {
          type inet:ip-address;
          description "MUP endpoint address";
        }
        leaf route-distinguisher {
          type string;
          description
            "Route-distinguisher";
        }
        leaf teid {
          type uint32;
          description "Tunnel endpoint identifier";
        }
        leaf qfi {
          type uint8;
          description "QoS flow identifier";
        }
        leaf mup-architecture {
          type identityref {
            base arc-oc-bgp-types:MUP_ARCHITECTURE_TYPE;
          }
          description "MUP architecture";
        }
        leaf-list color-extended-community {
          type string;
          description
            "Colors value along with flags represented as string";
        }
      }
    }

    container mup-extended-community {
      when "../state/type = 'MUP-EXTENDED-COMMUNITY'" {
        description "When next-hop is MUP endpoint";
      }
      uses next-hop-resolution-info;
      container state {
        leaf route-distinguisher {
          type string;
          description
            "Route-distinguisher";
        }
        leaf-list mup-extended-community {
          type string;
          description
            "MUP extended community values";
        }
      }
    }
    container local {
      when "../state/type = 'LOCAL'" {
        description "When next-hop is local";
      }
      container state {
        leaf unspecified {
          type boolean;
          description "Nexthop address is unspecified";
        }
      }
    }
    container local-mup {
      when "../state/type = 'LOCAL-MUP'" {
        description "When next-hop is local";
      }
      container state {
        leaf route-distinguisher {
          type string;
          description
            "Route-distinguisher";
        }
        leaf endpoint {
          type inet:ip-address;
          description "Endpoint address";
        }
        leaf mup-architecture {
          type identityref {
            base arc-oc-bgp-types:MUP_ARCHITECTURE_TYPE;
          }
          description "MUP architecture";
        }
      }
    }
    container prefix {
      when "../state/type = 'PREFIX'" {
        description "When next-hop is a prefix";
      }
      container state {
        leaf prefix {
          type inet:ip-prefix;
          description
            "The next-hop prefix to track";
        }

        leaf local {
          type boolean;
          description
            "Next-hop is locally reachable";
        }
      }
    }
    container evpn-imet {
      when "../state/type = 'EVPN-IMET'" {
        description "When next-hop is EVPN IMET route";
      }
      container state {
        leaf route-distinguisher {
          type string;
          description
            "Route-distinguisher";
        }
        leaf ethernet-tag-identifier {
          type uint32;
          description
            "Ethernet Tag Identifier";
        }
        leaf-list color-extended-community {
          type string;
          description
            "Colors value along with flags represented as string";
        }
      }
    }
    container l2-attribute-extended-community {
      when "../state/type = 'L2-ATTRIBUTE-EXTENDED-COMMUNITY'" {
        description "When next-hop is dependent on L2 Attributes Extended Community";
      }
      container state {
        leaf network-instance {
          type oc-netinst:network-instance-ref;
          description
            "The network-instance for which L2 Attributes Extended Community is received";
        }

        leaf domain {
          type leafref {
            path "/arc-evpn:evpn/arc-evpn:domains/arc-evpn:domain/arc-evpn:name";
          }
          description
            "The domain in which L2 Attributes Extended Community is received";
        }
  
        leaf control-word {
          type boolean;
          description
            "Received/Local control-word flag in IMET route";
        }

        leaf flow-label {
          type boolean;
          description
            "Received/Local flow-label flag in IMET route";
        }

        leaf l2-attr-received {
          type boolean;
          description
            "If the nh is based on received l2 attributes for IMET route";
        }

        leaf-list color-extended-community {
          type string;
          description
            "Colors value along with flags represented as string";
        }
      }
    }
  }

  grouping sub-next-hop-info {
    description
      "Parameters related to a BGP group";
    container state {
      leaf id {
        type string;
        description
          "The next-hop name";
      }
      leaf type {
        type sub-next-hop-type;
        description
          "The sub next-hop type";
      }
      leaf dependent-nexthop-count {
        type uint32;
        description
          "Dependent next-hop count";
      }
      leaf last-update-time {
        type string;
        description
          "Last updated timestamp";
      }
    }
    container resolution {
      container state {
        leaf valid {
          type boolean;
          description
            "Sub next-hop reachability valid";
        }
      }
    }
    container prefix {
      when "../state/type = 'PREFIX'" {
        description
          "Applicable only when sub next-hop
           is a prefix";
      }
      container state {
        leaf prefix {
          type inet:ip-prefix;
          description
            "Nexthop IP prefix";
        }
        leaf network-instance {
          type oc-netinst:network-instance-ref;
          description
            "Network instance the IP to be resolved";
        }
        leaf over-mobile-sid {
          type boolean;
          description
            "Mobile SID resolution";
        }
      }
      container resolution {
        container state {
          leaf mpls-reachable {
            type boolean;
            description
              "MPLS reachable";
          }
          leaf resolving-prefix {
            type inet:ip-prefix;
            description
              "Resolving prefix";
          }
        }
      }
    }
    container address-interface {
      when "../state/type = 'ADDRESS-INTERFACE'" {
        description
          "Applicable only when sub next-hop
           is an interface bound address";
      }
      container state {
        leaf ip {
          type inet:ip-address;
          description
            "Nexthop IP address";
        }
        leaf interface {
          type string;
          description
            "Interface name";
        }
        leaf interface-index {
          type uint32;
          description
            "Interface index";
        }
      }
    }
    container mup-extended-community {
      when "../state/type = 'MUP-EXTENDED-COMMUNITY'" {
        description
          "Applicable only when sub next-hop
           is MUP extended community";
      }
      container state {
        leaf-list value {
          type string;
          description
            "MUP extended community values";
        }
        leaf route-distinguisher {
          type string;
          description
            "Route-distinguisher";
        }
        leaf afi-safi {
          type identityref {
            base oc-bgp-types:AFI_SAFI_TYPE;
          }
          description
            "AFI-SAFI to resolve MUP extended-community";
        }
      }
      container resolution {
        container state {
          leaf resolving-network-instance {
            type oc-netinst:network-instance-ref;
            description
              "Network instance of DSD route";
          }
          leaf prefix-sid {
            type inet:ipv6-address;
            description
              "Prefix SID from DSD route";
          }
        }
      }
    }
    container endpoint-color {
      when "../state/type = 'ENDPOINT-COLOR'" {
        description
          "Applicable only when sub next-hop
           is SR-Policy resolvable";
      }
      container state {
        leaf network-instance {
          type oc-netinst:network-instance-ref;
          description
            "Network instance";
        }
        leaf endpoint {
          type inet:ip-address;
          description
            "Endpoint address";
        }
        leaf-list color {
          type string;
          description
            "Color";
        }
      }
      container resolution {
        container state {
          leaf srpolicy-nh-id {
            type uint32;
            description
              "SR Policy nexthop ID";
          }
          leaf resolving-policy-endpoint {
            type inet:ip-address;
            description
              "Resolving SR Policy endpoint";
          }
          leaf resolving-policy-color {
            type uint32;
            description
              "Resolving SR Policy color";
          }
        }
      }
    }
    container mup-isd-address {
      when "../state/type = 'MUP-ISD-ADDRESS'" {
        description
          "Applicable only when sub next-hop
           is MUP ISD address";
      }
      container state {
        leaf route-distinguisher {
          type string;
          description
            "Route distinguisher";
        }
        leaf endpoint {
          type inet:ip-address;
          description
            "Endpoint address";
        }
        leaf mup-architecture {
          type identityref {
            base arc-oc-bgp-types:MUP_ARCHITECTURE_TYPE;
          }
          description "MUP architecture";
        }
      }
      container resolution {
        container state {
          leaf resolving-prefix {
            type inet:ip-prefix;
            description
              "ISD Prefix resolving the address";
          }
          leaf mobile-sid {
            type inet:ip-address;
            description
              "Mobile SID";
          }
          leaf nexthop-address {
            type inet:ip-address;
            description
              "ISD Route's nexthop address";
          }
          leaf nexthop-network-instance {
            type oc-netinst:network-instance-ref;
            description
              "ISD route's reachability network-instance";
          }
        }
      }
    }

    container mup-interwork-locator {
      when "../state/type = 'MUP-INTERWORK-LOCATOR'" {
        description
          "Applicable only when sub next-hop
           is MUP Interwork locator";
      }
      container state {
        leaf sid {
          type inet:ipv6-prefix;
          description
            "SID prefix allocator for interwork segment";
        }
      }
      container resolution {
        container state {
          leaf nexthop-network-instance {
            type oc-netinst:network-instance-ref;
            description
              "ISD route's reachability network-instance";
          }
        }
      }
    }

    container ipv4-tunnel {
      when "../state/type = 'IPV4-TUNNEL'" {
        description
          "Applicable only when sub next-hop
           is IPv4 tunnel";
      }
      container state {
        leaf source {
          type inet:ipv4-address;
          description
            "IPv4 source address for the tunnel";
        }
        leaf destination {
          type inet:ipv4-address;
          description
            "IPv4 destination address for the tunnel";
        }
      }
      container resolution {
        container state {
          leaf tunnel-id {
            type uint32;
            description
              "Tunnel ID";
          }
        }
      }
    }
    container srv6-tunnel {
      when "../state/type = 'SRV6-TUNNEL'" {
        description
          "Applicable only when sub next-hop
           is SRv6 tunnel";
      }
      container state {
        leaf source {
          type inet:ipv6-address;
          description
            "IPv6 source address for the tunnel";
        }
        leaf destination {
          type inet:ipv6-address;
          description
            "IPv6 destination address for the tunnel";
        }
        leaf endpoint {
          type inet:ipv6-address;
          description
            "IPv6 endpoint address for the tunnel";
        }
        leaf endpoint-function {
          type arc-srv6-types:srv6-endpoint-behavior-type;
          description
            "SRv6 Endpoint function";
        }
        leaf network-instance {
          type oc-netinst:network-instance-ref;
          description
            "Network instance for the tunnel";
        }
        leaf afi-safi {
          type identityref {
            base oc-bgp-types:AFI_SAFI_TYPE;
          }
          description
            "AFI-SAFI of tunnel user";
        }
        leaf oam-tracking-enabled {
          type boolean;
          description
            "OAM Tracking enabled state";
        }
      }
      container resolution {
        container state {
          leaf tunnel-id {
            type uint32;
            description
              "Tunnel ID";
          }
          leaf oam-profile {
            type string;
            description
              "OAM Profile used for tracking";
          }
          leaf oam-metric {
            type uint32;
            description
              "OAM metric";
          }
          leaf oam-tracked {
            type boolean;
            description
              "Tunnel tracking state using OAM";
          }
          leaf oam-tracking-permitted {
            type boolean;
            description
              "OAM Tracking permit state";
          }
        }
      }
    }
    container mpls-label {
      when "../state/type = 'MPLS-LABEL'" {
        description
          "Applicable only when sub next-hop
           is MPLS label";
      }
      container state {
        leaf local-nexthop {
          type boolean;
          description
            "Local next-hop";
        }
        leaf address {
          type inet:ip-address;
          description
            "Nexthop address";
        }
        leaf interface {
          type string;
          description
            "Interface name";
        }
        leaf network-instance {
          type oc-netinst:network-instance-ref;
          description
            "Network instance for the tunnel";
        }
        leaf afi-safi {
          type identityref {
            base oc-bgp-types:AFI_SAFI_TYPE;
          }
          description
            "AFI-SAFI of tunnel user";
        }
      }
      container resolution {
        container state {
          leaf label {
            type uint32;
            description
              "MPLS Label";
          }
        }
      }
    }
    container srv6-sid {
      when "../state/type = 'SRV6-SID'" {
        description
          "Applicable only when sub next-hop
           is SRv6 SID";
      }
      container state {
        leaf local-nexthop {
          type boolean;
          description
            "Local next-hop";
        }
        leaf address {
          type inet:ip-address;
          description
            "Nexthop address";
        }
        leaf interface {
          type string;
          description
            "Interface name";
        }
        leaf network-instance {
          type oc-netinst:network-instance-ref;
          description
            "Network instance for the tunnel";
        }
        leaf afi-safi {
          type identityref {
            base oc-bgp-types:AFI_SAFI_TYPE;
          }
          description
            "AFI-SAFI of tunnel user";
        }
      }
      container resolution {
        container state {
          leaf srv6-sid {
            type inet:ip-prefix;
            description
              "SRv6 SID";
          }
        }
      }
    }
    container own-address {
      when "../state/type = 'OWN-ADDRESS'" {
        description
          "Applicable only when sub next-hop
           is of own-address type";
      }
      container state {
        leaf network-instance {
          type oc-netinst:network-instance-ref;
          description
            "Network instance of the IP address";
        }
        leaf interface {
          type string;
          description
            "Interface name";
        }
        leaf address {
          type inet:ip-address;
          description
            "Nexthop address";
        }
      }
      container resolution {
        container state {
          leaf is-own-address {
            type boolean;
            description
              "Indicates if the IP address belongs to this router";
          }
        }
      }
    }
    container evpn-imet {
      when "../state/type = 'EVPN-IMET'" {
        description
          "Applicable only when sub next-hop
           is of evpn-imet type";
      }
      container state {
        leaf route-distinguisher {
          type string;
          description
            "Route distinguisher";
        }
        leaf ethernet-tag-identifier {
          type uint32;
          description
            "Ethernet Tag Identifier";
        }
        leaf originator-ip {
          type inet:ip-address;
          description
            "Originator IP address";
        }
      }
    }
    container l2-attribute-extended-community {
      when "../state/type = 'L2-ATTRIBUTE-EXTENDED-COMMUNITY'" {
        description
          "Applicable only when sub next-hop
           is of l2-attr-extcomm type";
      }
      container state {
        leaf network-instance {
          type oc-netinst:network-instance-ref;
          description
            "The network-instance in which L2 Attributes Extended Community is received";
        }

        leaf domain {
          type leafref {
            path "/arc-evpn:evpn/arc-evpn:domains/arc-evpn:domain/arc-evpn:name";
          }
          description
            "The domain in which L2 Attributes Extended Community is received";
        }

        leaf control-word {
          type boolean;
          description
            "Received/Local control-word flag in IMET route";
        }

        leaf flow-label {
          type boolean;
          description
            "Received/Local flow-label flag in IMET route";
        }

        leaf l2-attr-received {
          type boolean;
          description
            "If the sub-nh is based on received l2 attributes for IMET route";
        }

      }
    }
  }

  grouping bgp-next-hops-list {
    description
      "The list of BGP next hops";

    container next-hops {
      config false;
      list next-hop {
        key "id";
        description
          "List of BGP next-hops";
        leaf id {
          type leafref {
            path "../state/id";
          }
        }
        uses next-hop-info;
      }
    }
  }

  grouping bgp-sub-next-hops-list {
    container sub-next-hops {
      config false;
      list sub-next-hop {
        key "id";
        description
          "List of BGP subsequent next-hops that have unique resolvability";
        leaf id {
          type leafref {
            path "../state/id";
          }
        }
        uses sub-next-hop-info;
      }
    }
  }

  augment "/oc-netinst:network-instances/oc-netinst:network-instance" +
          "/oc-netinst:protocols/oc-netinst:protocol" +
          "/oc-netinst:bgp/oc-netinst:global" +
          "/oc-netinst:afi-safis/oc-netinst:afi-safi" {
    uses bgp-next-hops-list;
  }

  augment "/oc-netinst:network-instances/oc-netinst:network-instance" +
          "/oc-netinst:protocols/oc-netinst:protocol" +
          "/oc-netinst:bgp/oc-netinst:global" {
    uses bgp-sub-next-hops-list {
      when "current()/../../../../oc-netinst:name = 'default'";
    }
  }
}
