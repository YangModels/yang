module arcos-rsvp-types {

  yang-version "1.1";

  namespace "http://yang.arrcus.com/arcos-rsvp-types";

  prefix "arc-rsvp-types";

  import ietf-yang-types { prefix "yang"; }
  import openconfig-extensions { prefix "oc-ext"; }

  organization
    "Arrcus, Inc";

  contact
    "Arrcus, Inc.
     2077 Gateway Place
     Suite 400
     San Jose, CA 95110

     E-mail: yang-support@arrcus.com";

  description
    "This module provides Type and Identity definitions for RSVP.

     Copyright (c) 2022 by Arrcus, Inc.
     All rights reserved.";

  revision "2022-06-06" {
    description
      "Initial version.";
  }


  /*
   * RSVP Priority Level
   */
  typedef rsvp-priority-level-type {

    type enumeration {
      enum PRIORITY-ALL {
        description
          "Union of all priority levels.";
      }
    }

    description
      "RSVP Priority Level.";
  }


  /*
   * RSVP Admin Status
   */
  identity RSVP-ADMIN-STATUS {
    description
      "RSVP Admin Status";
  }

  identity ADMIN-UNKNOWN {
    base "RSVP-ADMIN-STATUS";
    description
      "Admin status unknown.";
  }

  identity ADMIN-UP {
    base "RSVP-ADMIN-STATUS";
    description
      "Admin status UP.";
  }

  identity ADMIN-DOWN {
    base "RSVP-ADMIN-STATUS";
    description
      "Admin status DOWN.";
  }

  identity ADMIN-UP-IN-PROGRESS {
    base "RSVP-ADMIN-STATUS";
    description
      "Admin status UP.";
  }

  identity ADMIN-DOWN-IN-PROGRESS {
    base "RSVP-ADMIN-STATUS";
    description
      "Admin status DOWN.";
  }


  /*
   * RSVP Oper Status
   */
  identity RSVP-OPER-STATUS {
    description
      "RSVP Oper Status";
  }

  identity OPER-UNKNOWN {
    base "RSVP-OPER-STATUS";
    description
      "Oper status unknown.";
  }

  identity OPER-UP {
    base "RSVP-OPER-STATUS";
    description
      "Oper status UP.";
  }

  identity OPER-DOWN {
    base "RSVP-OPER-STATUS";
    description
      "Oper status DOWN.";
  }

  identity OPER-DORMANT {
    base "RSVP-OPER-STATUS";
    description
      "Oper status dormant.";
  }

  identity OPER-NOT-PRESENT {
    base "RSVP-OPER-STATUS";
    description
      "Oper status not present.";
  }


  /*
   * RSVP Hello Status
   */
  identity RSVP-HELLO-STATUS {
    description
      "RSVP Hello Status";
  }

  identity HELLO-ENABLED {
    base "RSVP-HELLO-STATUS";
    description
      "RSVP Hellos enabled.";
  }

  identity HELLO-DISABLED {
    base "RSVP-HELLO-STATUS";
    description
      "RSVP Hellos disabled.";
  }

  identity HELLO-RESTARTING {
    base "RSVP-HELLO-STATUS";
    description
      "RSVP restarting.";
  }

  identity HELLO-UNKNOWN {
    base "RSVP-HELLO-STATUS";
    description 
      "RSVP neighbor restored after restart, hello state unknown.";
  }

  identity HELLO-RESET {
    base "RSVP-HELLO-STATUS";
    description
      "RSVP neighbor assumed to have reset its state, waiting to receive hello msg.";
  }


  /*
   * RSVP Information Producer
   */
  identity RSVP-INFO-PRODUCER {
    description
      "RSVP information producer";
  }

  identity IGP-ISIS-L1 {
    base "RSVP-INFO-PRODUCER";
    description
      "ISIS Level-1 Adjacency.";
  }

  identity IGP-ISIS-L2 {
    base "RSVP-INFO-PRODUCER";
    description
      "ISIS Level-2 Adjacency.";
  }


  /*
   * RSVP Preemption Mode
   */
  identity RSVP-PREEMPTION-MODE {
    description
      "RSVP Preemption mode";
  }

  identity PREEMPTION-DISABLED {
    base RSVP-PREEMPTION-MODE;
    description
      "Preemption is disabled";
  }

  identity PREEMPTION-HARD {
    base RSVP-PREEMPTION-MODE;
    description
      "Hard Preemption mode";
  }

  identity PREEMPTION-SOFT {
    base RSVP-PREEMPTION-MODE;
    description
      "Soft Preemption mode";
  }


  /*
   * RSVP Neighbor Status
   */
  identity RSVP-NEIGHBOR-STATUS {
    description
      "RSVP Neighbor Status";
  }

  identity NEIGHBOR-UP {
    base "RSVP-NEIGHBOR-STATUS";
    description
      "Neighbor state up.";
  }

  identity NEIGHBOR-DOWN {
    base "RSVP-NEIGHBOR-STATUS";
    description
      "Neighbor state down.";
  }

  identity NEIGHBOR-HELLO-DISABLED {
    base "RSVP-NEIGHBOR-STATUS";
    description
      "RSVP Hellos disabled.";
  }

  identity NEIGHBOR-RESTARTING {
    base "RSVP-NEIGHBOR-STATUS";
    description
      "RSVP neighbor restarting.";
  }


  /*
   * RSVP Neighbor Refresh Reduction
   */
  identity RSVP-NEIGHBOR-RR-STATUS{
    description "RSVP Neighbor Refresh Reduction Status";
  }

  identity RR-ENABLED {
    base "RSVP-NEIGHBOR-RR-STATUS";
    description "RSVP Neighbor Refresh Reduction enabled";
  }

  identity RR-DISABLED {
    base "RSVP-NEIGHBOR-RR-STATUS";
    description "RSVP Neighbor Refresh Reduction disabled";
  }

  identity RR-UNSUPPORTED {
    base "RSVP-NEIGHBOR-RR-STATUS";
    description "RSVP Neighbor Refresh Reduction not supported";
  }


  /*
   * RSVP Reservation Style
   */
  identity RSVP-RESERVATION-STYLE {
    description
      "RSVP reservation style.";
  }

  identity RESERVATION-WILDCARD-FILTER {
    base RSVP-RESERVATION-STYLE;
    description
      "Wildcard-Filter (WF) Style.";
    reference
      "RFC2205";
  }

  identity RESERVATION-FIXED-FILTER {
    base RSVP-RESERVATION-STYLE;
    description
      "Fixed-Filter (FF) Style.";
    reference
      "RFC2205";
  }

  identity RESERVATION-SHARED-EXPLICIT {
    base RSVP-RESERVATION-STYLE;
    description
      "Shared Explicit (SE) Style.";
    reference
      "RFC2205";
  }


  /*
   * RSVP Session Status
   */
  identity RSVP-SESSION-STATUS {
    description
      "RSVP Session Status";
  }

  identity SESSION-DOWN {
    base "RSVP-SESSION-STATUS";
    description
      "Session status DOWN.";
  }

  identity SESSION-UP {
    base "RSVP-SESSION-STATUS";
    description
      "Session status UP.";
  }


  /*
   * RSVP Hop Strict/Loose Route Type
   */
  identity RSVP-HOP-ROUTE-TYPE {
    description
      "RSVP Hop Strict/Loose route type";
  }

  identity UNKNOWN-HOP {
    base "RSVP-HOP-ROUTE-TYPE";
    description
      "Unknown hop";
  }

  identity STRICT-HOP {
    base "RSVP-HOP-ROUTE-TYPE";
    description
      "Strict hop";
  }

  identity LOOSE-HOP {
    base "RSVP-HOP-ROUTE-TYPE";
    description
      "Loose hop";
  }


  /*
   * RSVP ERO Hop Type
   */
  identity RSVP-ERO-HOP-TYPE {
    description
      "RSVP ERO Hop Type";
  }

  identity ERO-HOP-UNKNOWN {
    base "RSVP-ERO-HOP-TYPE";
    description
      "Hop represents an IPv4 prefix.";
  }

  identity ERO-HOP-IPV4 {
    base "RSVP-ERO-HOP-TYPE";
    description
      "Hop represents an IPv4 prefix.";
  }

  identity ERO-HOP-IPV6 {
    base "RSVP-ERO-HOP-TYPE";
    description
      "Hop represents an IPv6 prefix.";
  }

  identity ERO-HOP-ASN {
    base "RSVP-ERO-HOP-TYPE";
    description
      "Hop represents 2-byte AS Number.";
  }

  identity ERO-HOP-ASN4 {
    base "RSVP-ERO-HOP-TYPE";
    description
      "Hop represents 4-byte AS Number.";
  }

  identity ERO-HOP-LABEL {
    base "RSVP-ERO-HOP-TYPE";
    description
      "Hop represents an MPLS Label.";
  }

  identity ERO-HOP-UNNUMBERED-INTERFACE {
    base "RSVP-ERO-HOP-TYPE";
    description
      "Hop represents an unnumbered interface.";
  }


  /*
   * RSVP RRO Hop Type
   */
  identity RSVP-RRO-HOP-TYPE {
    description
      "RSVP RRO Hop Type";
  }

  identity RRO-HOP-UNKNOWN {
    base "RSVP-RRO-HOP-TYPE";
    description
      "Hop represents an IPv4 prefix.";
  }

  identity RRO-HOP-IPV4 {
    base "RSVP-RRO-HOP-TYPE";
    description
      "Hop represents an IPv4 prefix.";
  }

  identity RRO-HOP-IPV6 {
    base "RSVP-RRO-HOP-TYPE";
    description
      "Hop represents an IPv6 prefix.";
  }

  identity RRO-HOP-ASN {
    base "RSVP-RRO-HOP-TYPE";
    description
      "Hop represents 2-byte AS Number.";
  }

  identity RRO-HOP-ASN4 {
    base "RSVP-RRO-HOP-TYPE";
    description
      "Hop represents 4-byte AS Number.";
  }

  identity RRO-HOP-LABEL {
    base "RSVP-RRO-HOP-TYPE";
    description
      "Hop represents an MPLS Label.";
  }

  identity RRO-HOP-UNNUMBERED-INTERFACE {
    base "RSVP-RRO-HOP-TYPE";
    description
      "Hop represents an unnumbered interface.";
  }
}
