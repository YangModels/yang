module tailf-aaa-deviations {
  yang-version 1.1;
  namespace "http://yang.arrcus.com/arcos/tailf/aaa/deviations";
  prefix arc-tailf-aaa-dev;

  import tailf-aaa {
    prefix aaa;
  }

  deviation "/aaa:session" {
    deviate not-supported;
  }

  deviation "/aaa:user" {
    deviate not-supported;
  }

}
