module arcos-openconfig-if-ip-deviations {
  yang-version 1.1;
  namespace "http://yang.arrcus.com/arcos/openconfig/interface/ip/deviations";
  prefix arc-oc-ip-dev;

  import openconfig-if-ip {
    prefix oc-ip;
  }
  import openconfig-interfaces {
    prefix oc-if;
  }
  import openconfig-vlan {
    prefix oc-vlan;
  }

  revision 2023-11-28 {
    description
      "Support IPv4 Unnumbered interface";
  }


  deviation "/oc-if:interfaces/oc-if:interface/oc-if:subinterfaces/" +
            "oc-if:subinterface/oc-ip:ipv4/oc-ip:config/oc-ip:mtu" {
    deviate not-supported;
    description "Not supported in this release";
  }
  deviation "/oc-if:interfaces/oc-if:interface/oc-if:subinterfaces/" +
            "oc-if:subinterface/oc-ip:ipv4/oc-ip:unnumbered/" +
            "oc-ip:config/oc-ip:enabled" {
    deviate not-supported;
    description "Not supported in this release";
  }

  deviation "/oc-if:interfaces/oc-if:interface/oc-if:subinterfaces/" +
            "oc-if:subinterface/oc-ip:ipv4/oc-ip:addresses/oc-ip:address" {
    deviate add {
      max-elements 2;
    }
    description "Only support two IP addresses (one primary and the other secondary) in this release";
  }

  deviation "/oc-if:interfaces/oc-if:interface/oc-if:subinterfaces/" +
            "oc-if:subinterface/oc-ip:ipv6/oc-ip:addresses/oc-ip:address" {
    deviate add {
      max-elements 2;
    }
    description "Only support two address(one global, one link local) in this release";
  }
  deviation "/oc-if:interfaces/oc-if:interface/oc-vlan:routed-vlan/" +
            "oc-ip:ipv4/oc-ip:neighbors" {
    deviate not-supported;
    description "Not supported in this release";
  }
  deviation "/oc-if:interfaces/oc-if:interface/oc-vlan:routed-vlan/" +
            "oc-ip:ipv4/oc-ip:unnumbered" {
    deviate not-supported;
    description "Not supported in this release";
  }
  deviation "/oc-if:interfaces/oc-if:interface/oc-if:subinterfaces/" +
            "oc-if:subinterface/oc-ip:ipv6/oc-ip:config/oc-ip:mtu" {
    deviate not-supported;
    description "Not supported in this release";
  }
  deviation "/oc-if:interfaces/oc-if:interface/oc-if:subinterfaces/" +
            "oc-if:subinterface/oc-ip:ipv6/oc-ip:unnumbered" {
    deviate not-supported;
    description "Not supported in this release";
  }
  deviation "/oc-if:interfaces/oc-if:interface/oc-vlan:routed-vlan/" +
            "oc-ip:ipv6/oc-ip:neighbors" {
    deviate not-supported;
    description "Not supported in this release";
  }
  deviation "/oc-if:interfaces/oc-if:interface/oc-vlan:routed-vlan/" +
            "oc-ip:ipv6/oc-ip:unnumbered" {
    deviate not-supported;
    description "Not supported in this release";
  }
  deviation "/oc-if:interfaces/oc-if:interface/oc-if:subinterfaces/" +
            "oc-if:subinterface/oc-ip:ipv6/oc-ip:config/" +
            "oc-ip:dup-addr-detect-transmits" {
    deviate not-supported;
    description "Not supported in this release";
  }
  deviation "/oc-if:interfaces/oc-if:interface/oc-if:subinterfaces/" +
            "oc-if:subinterface/oc-ip:ipv4/oc-ip:addresses/oc-ip:address/" +
            "oc-ip:vrrp/oc-ip:vrrp-group/oc-ip:config/" +
            "oc-ip:preempt" {
    deviate not-supported;
    description "Not supported in this release";
  }
  deviation "/oc-if:interfaces/oc-if:interface/oc-if:subinterfaces/" +
            "oc-if:subinterface/oc-ip:ipv4/oc-ip:addresses/oc-ip:address/" +
            "oc-ip:vrrp/oc-ip:vrrp-group/oc-ip:config/" +
            "oc-ip:preempt-delay" {
    deviate not-supported;
    description "Not supported in this release";
  }
  deviation "/oc-if:interfaces/oc-if:interface/oc-if:subinterfaces/" +
            "oc-if:subinterface/oc-ip:ipv6/oc-ip:addresses/oc-ip:address/" +
            "oc-ip:vrrp/oc-ip:vrrp-group/oc-ip:config/" +
            "oc-ip:preempt" {
    deviate not-supported;
    description "Not supported in this release";
  }
  deviation "/oc-if:interfaces/oc-if:interface/oc-if:subinterfaces/" +
            "oc-if:subinterface/oc-ip:ipv6/oc-ip:addresses/oc-ip:address/" +
            "oc-ip:vrrp/oc-ip:vrrp-group/oc-ip:config/" +
            "oc-ip:preempt-delay" {
    deviate not-supported;
    description "Not supported in this release";
  }
  deviation "/oc-if:interfaces/oc-if:interface/oc-if:subinterfaces/" +
            "oc-if:subinterface/oc-ip:ipv4/oc-ip:addresses/oc-ip:address/" +
            "oc-ip:vrrp/oc-ip:vrrp-group/oc-ip:interface-tracking" {
    deviate not-supported;
    description "Not supported in this release";
  }
  deviation "/oc-if:interfaces/oc-if:interface/oc-if:subinterfaces/" +
            "oc-if:subinterface/oc-ip:ipv6/oc-ip:addresses/oc-ip:address/" +
            "oc-ip:vrrp/oc-ip:vrrp-group/oc-ip:interface-tracking" {
    deviate not-supported;
    description "Not supported in this release";
  }
  deviation "/oc-if:interfaces/oc-if:interface/oc-if:subinterfaces/" +
            "oc-if:subinterface/oc-ip:ipv4/oc-ip:addresses/oc-ip:address/" +
            "oc-ip:vrrp/oc-ip:vrrp-group/oc-ip:config/" +
            "oc-ip:accept-mode" {
    deviate replace {
      type boolean;
      default true;
    }
    description
      "Configure whether packets destined for
      virtual addresses are accepted even when the virtual
      address is not owned by the router interface. Enabled
      by default.";
  }
  deviation "/oc-if:interfaces/oc-if:interface/oc-if:subinterfaces/" +
            "oc-if:subinterface/oc-ip:ipv6/oc-ip:addresses/oc-ip:address/" +
            "oc-ip:vrrp/oc-ip:vrrp-group/oc-ip:config/" +
            "oc-ip:accept-mode" {
    deviate replace {
      type boolean;
      default true;
    }
    description
      "Configure whether packets destined for
      virtual addresses are accepted even when the virtual
      address is not owned by the router interface. Enabled
      by default.";
  }
}
