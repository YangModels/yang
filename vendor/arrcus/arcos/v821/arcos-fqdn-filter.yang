module arcos-fqdn-filter {
  yang-version 1.1;
  namespace "http://yang.arrcus.com/arcos/fqdn/filter";
  prefix fqdn-filter;

  import ietf-inet-types {
    prefix inet;
  }
  import ietf-yang-types {
    prefix "yang";
  }  

  import arcos-platform {
    prefix arc-platform;
  }

  organization
    "Arrcus, Inc.";

  contact
    "Arrcus, Inc.
     2077 Gateway Place
     Suite 400
     San Jose, CA 95110
     E-mail: yang-support@arrcus.com";

  description
    "This module contains definitions for
     ArcOS Fqdn Discovery and Filter.
     Copyright (c) 2023 by Arrcus, Inc.
     All rights reserved.";

  revision "2023-09-25" {
    description
      "Add when statement for EDGE platform.";
  }

  revision "2023-03-08" {
    description
      "Initial commit for Fqdnfilter.";
  }

  container fqdn-filter {
    when "(/arc-platform:platform/arc-platform:type = 'arc-platform:EDGE')";

    leaf-list trusted-dns-servers {
      type inet:ip-address;
      description 
        "DNS queries to this list of IP addreses bypass fqdn filter";
    }
    leaf zero-trust-enabled {
      type boolean;
      default true;
      description 
        "Enables zerotrust operation for fqdns. If true all 
         DNS queries are blocked by default except those 
         whitelisted or going towards trusted-dns-servers.
         If false all DNS queries are allowed by default except those 
         blacklisted";
    }
    leaf enable-fqdn-discovery {
      type boolean;
      default true;
      description 
        "Enables discovering all fqdns based on DNS queries";
    }
    list fqdn-policy {
      key "name";
      leaf name {
        type string {
          length "1..31";
        }
        description 
          "Name for the fqdn policy like 'gaming' , 
          'gambling', 'socialnetworks' etc";
      } 
      leaf-list fqdns {
        type string;
        description 
          "List of fqdns that form a policy and 
           can act as a whitelist or blacklist";
      }
    }
    leaf-list active-fqdn-policies {
      type leafref {
          path "../fqdn-policy/name";
          require-instance true;
      }
    }
    leaf-list discovered-fqdns {
      type string;
      config false;
      description 
        "List of dns queries to fqdns seen by this gateway";        
    }
  }
  notification fqdns-discovered {
    leaf fqdns-list {
      type string ;
      description 
        "Modeled as a leaf, for now, this is a list of individual FQDNs
        seen by the gateway. Each entry within the list is sent as a
        separate notification.";
    }
  }
}
