module arcos-interfaces-debug {
  yang-version 1.1;
  namespace "http://yang.arrcus.com/arcos/interfaces/debug";
  prefix arc-if-dbg;

  organization
    "Arrcus, Inc.";

  contact
    "Arrcus, Inc.
     2077 Gateway Place
     Suite 400
     San Jose, CA 95110

     E-mail: yang-support@arrcus.com";

  description
    "This module contains definitions for the native 
     ArcOS Interface / IFMGR debug domain.

     Copyright (c) 2016-2023, by Arrcus, Inc.
     All rights reserved.";
  
  revision 2023-12-03 {
    description
      "Add model for tech-support debug state";
  } 

  typedef ifmgr-debug-state {
    type enumeration {
      enum on {
        description
          "Enable debug";
      }
      enum off {
        description
          "Disable debug";
      }
    }
  }

  typedef ifmgr-debug-type {
    type enumeration {
      enum control {
        description
          "Control processing debugs";
      }
    }
  }

  grouping ifmgr-debugs-state {
    description
      "ifmgr debugs information";

    leaf debug-flag {
      type ifmgr-debug-type;
      description
        "ifmgr debug flags";
    }
    leaf enabled {
      type boolean;
      description
        "Indicates whether the debug flag is enabled or not";
    }
  }

  grouping ifmgr-show-debug-top {
    container ifmgr-show-debugs {
      list ifmgr-debug {
        key "debug-flag";

        description
          "ifmgr debugs information";

        leaf debug-flag {
          type leafref {
            path "../state/debug-flag";
          }
          description
            "ifmgr Debug flags";
        }

        container state {
          uses ifmgr-debugs-state;
        }
      }
    }
  }

  container ifmgr-debug {
    description
      "Interface Manager debug control";

    action debug {
      input {
        leaf type {
          type ifmgr-debug-type;
          mandatory true;
          description
            "Debug to be controlled";
        }
        leaf op {
          type ifmgr-debug-state;
          mandatory true;
          description
            "Turn on/off operation";
        }
      }
      output {
        leaf result {
          type string;
          description
            "The status of operation";
        }
      }
    }
  }
}
