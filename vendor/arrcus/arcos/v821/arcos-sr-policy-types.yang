module arcos-sr-policy-types {
  yang-version 1.1;
  namespace "http://yang.arrcus.com/arcos/sr/policy/types";
  prefix arc-sr-pol-types;

  import openconfig-mpls-types {
    prefix oc-mpls-types;
  }
  import arcos-srv6-types {
    prefix arc-srv6-types;
  }

  organization
    "Arrcus, Inc.";

  contact
    "Arrcus, Inc.
     2077 Gateway Place
     Suite 400
     San Jose, CA 95110

     E-mail: yang-support@arrcus.com";

  description
    "This module contains definitions for the
     native ArcOS SR types..

     Copyright (c) 2022 by Arrcus, Inc.
     All rights reserved.";

  revision 2024-04-19 {
    description
      "Add type defintion for path metric-type";
  }

  revision 2024-02-01 {
    description
      "Remove unsupported segment types";
  }

  revision 2022-10-25 {
    description
      "Initial version";
  }

  /* Identities */
  identity candidate-path-not-selected-reason {
    description
      "Base identity for which reasons for not selecting
      candidate path are derived from";
  }
  identity candidate-path-not-selected-not-best {
    base candidate-path-not-selected-reason;
    description
      "Higher preference path exists";
  }
  identity candidate-path-not-selected-no-valid-segment-list {
    base candidate-path-not-selected-reason;
    description
      "Candidate path has no valid segment list(s)";
  }
  identity candidate-path-not-selected-empty-segment-list {
    base candidate-path-not-selected-reason;
    description
      "Candidate path has empty segment list(s)";
  }
  identity candidate-path-not-selected-invalid-binding-sid {
    base candidate-path-not-selected-reason;
    description
      "Candidate path has invalid binding SID";
  }

  identity policy-down-reason {
   description
      "Base identity for the reasons why SR policy is operationally down";
  }
  identity policy-down-reason-admin-down {
    base policy-down-reason;
    description "Policy is administrately down";
  }
  identity policy-down-reason-no-source-address {
    base policy-down-reason;
    description "Policy has no source address";
  }
  identity policy-down-reason-no-endpoint {
    base policy-down-reason;
    description "Policy has no end-point";
  }
  identity policy-down-reason-no-candidate-path {
    base policy-down-reason;
    description "Policy has no candidate path";
  }
  identity policy-down-reason-no-valid-candidate-path {
    base policy-down-reason;
    description "Policy has no valid candidate path";
  }
  identity policy-down-reason-candidate-path-invalid-segment-list {
    base policy-down-reason;
    description "Policy's candidate path has invalid segment list";
  }
  identity policy-down-reason-policy-unconfigured {
    base policy-down-reason;
    description "Policy is unconfigured";
  }
  identity policy-down-reason-policy-color-endpoint-updated {
    base policy-down-reason;
    description "Policy's color and end-point are updated";
  }
  identity policy-down-reason-local-label-setup-failed {
    base policy-down-reason;
    description "Policy's local label setup (allocation/rewrite) failed";
  }
  identity policy-down-reason-forwarding-rewrite-failed {
    base policy-down-reason;
    description "Policy's forwarding rewrite installation failed";
  }
  identity policy-down-reason-internal-error {
    base policy-down-reason;
    description "Infra related internal error";
  }

  identity binding-sid-unavailable-reason {
    description
      "Base identity for binding sid unavailable reason types";
  }
  identity binding-sid-allocation-error {
    base binding-sid-unavailable-reason;
    description "SID allocator returned an error";
  }
  identity binding-sid-already-exists {
    base binding-sid-unavailable-reason;
    description "Binding sid already exists/allocated";
  }
  identity binding-sid-internal-error {
    base binding-sid-unavailable-reason;
    description "Internal error with binding sid allocation";
  }
  identity binding-sid-color-endpoint-conflict {
    base binding-sid-unavailable-reason;
    description "Binding sid already allocated by another sr-policy with different color/endpoint";
  }
  identity binding-sid-rewrite-error {
    base binding-sid-unavailable-reason;
    description "Binding sid forwarding rewrite error";
  }
  identity binding-sid-outside-srlb-range {
    base binding-sid-unavailable-reason;
    description "Binding sid outside SRLB range";
  }

  identity path-disjointness {
    description
      "Base identity for the type of path disjointness computation";
  }
  identity path-disjointness-link {
    base path-disjointness;
    description "The computed path is link-disjoint with the existing path";
  }
  identity path-disjointness-node {
    base path-disjointness;
    description "The computed path is node-disjoint with the existing path";
  }
  identity path-disjointness-srlg {
    base path-disjointness;
    description "The computed path is srlg-disjoint with the existing path";
  }
  identity path-disjointness-srlg-node {
    base path-disjointness;
    description "The computed path is node and srlg disjoint with the existing path";
  }

  /* Typdefs */
  typedef sid-value-type {
    type union {
      type oc-mpls-types:mpls-label;
      type arc-srv6-types:srv6-sid;
    }
    description "The SID value type";
  }

  typedef binding-sid-oper-state {
    type enumeration {
      enum ALLOC-PENDING {
        value 1;
        description "SID allocation pending for Binding SID";
      }
      enum PROGRAMMED {
        value 3;
        description "Binding SID is programmed in forwarding";
      }
      enum CONFLICT {
        value 4;
        description "Binding SID is in-conflict state with
        regards to SID allocation. This also means that SID
        allocation is pending";
      }
    }
    description
      "Binding SID operational state type";
  }

  typedef policy-admin-state {
    type enumeration {
      enum UP {
        value 1;
        description "SR policy is administratively up";
      }
      enum DOWN {
        value 2;
        description "SR policy is administratively down";
      }
    }
    description "SR policy admin state";
  }

  typedef policy-oper-state {
    type enumeration {
      enum UP {
        value 1;
        description "SR policy is operationally up";
      }
      enum DOWN {
        value 2;
        description "SR policy is operationally down";
      }
    }
    description "SR policy oper state";
  }

  typedef segment-type {
    type enumeration {
      enum MPLS_LABEL {
        value 1;
        description "SR-MPLS Label";
      }
      enum SRV6_SID {
        value 2;
        description "SRv6 SID";
      }
    }
    description "SR segment type";
  }

  typedef binding-sid-alloc-mode {
    type enumeration {
      enum EXPLICIT_BSID {
        value 1;
        description "Explicitly specified BSID";
      }
      enum DYNAMIC_BSID {
        value 2;
        description "Dynamically allocated BSID";
      }
    }
    description "binding SID allocation mode";
  }

  typedef candidate-path-type {
    type enumeration {
      enum EXPLICIT_SEGMENT_LIST {
        value 1;
        description "Segment-lists are explicitly specified
                     for this candidate path type";
      }
      enum DYNAMIC_SEGMENT_LIST {
        value 2;
        description "Segment-lists are derived based on the
                     path constraints specified";
      }
    }
    description "SR policy candidate path type";
  }

  typedef protocol-origin-type {
    type enumeration {
      enum DYNAMIC_LOCAL {
        value 5;
        description "Dynamically generated local candidate path";
      }
      enum PCEP {
        value 10;
        description "PCEP used as signalling mechanism for the candidate path";
      }
      enum BGP {
        value 20;
        description "BGP used as signalling mechanism for the candidate path";
      }
      enum LOCAL {
        value 30;
        description "CLI, Yang model via Netconf, gRPC, etc used for candidate path instantiation";
      }
    }

    description "Originating protocol type";
  }

  typedef explicit-binding-sid-rule-type {
    type enumeration {
      enum ENFORCE_SRLB {
        value 1;
        description
            "Explicit Binding SID is enforced with no
             fallback if label does not fall in SRLB or
             if no SRLB is configured";
      }
      enum FALLBACK_DYNAMIC {
        value 2;
        description
            "Explicit Binding SID falls back to dynamic in
            case explicit label is not available.";
      }
    }
    description "Explicit binding sid rule types";
  }

  typedef metric-type {
    type enumeration {
      enum IGP_METRIC {
        value 1;
        description "TE metric";
      }
      enum TE_METRIC {
        value 2;
        description "IGP metric";
      }
      enum DELAY_METRIC {
        value 3;
        description "Latency metric";
      }
    }
    description "Path metric type";
  }

  typedef metric-filter-type {
    type enumeration {
      enum PATH_CALCULATION_METRIC {
        value 10;
        description "Calculation metric used in filtering";
      }
    }
    description "Path filter metric type";
  }
}
