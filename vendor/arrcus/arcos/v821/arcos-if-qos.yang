module arcos-if-qos {
  yang-version 1.1;
  namespace "http://yang.arrcus.com/arcos/interface/qos";
  prefix arc-if-qos;

  import openconfig-interfaces {
    prefix oc-if;
  }
  import arcos-platform {
    prefix arc-platform;
  }
  import openconfig-system {
    prefix oc-sys;
  }
  import arcos-openconfig-system-augments {
    prefix arc-oc-sys-aug;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for qos features on interfaces";
  
  revision 2024-11-07 {
    description "Modified the 'when' clause to enable CLI configuration on VM";
  }

  grouping if-qos-top {
    description
      "Top level grouping for interface-based QoS";
    container qos {
      description
        "Quality of Service";
    }
  }

  augment "/oc-if:interfaces/oc-if:interface" {
    uses if-qos-top {
      when "not(derived-from-or-self(/arc-platform:platform/arc-platform:asic, 'arc-platform:X86_64')) or " +
           "derived-from-or-self(/arc-platform:platform/arc-platform:deployment-type, 'arc-platform:DISTRIBUTED') or " +
           "(/oc-sys:system/arc-oc-sys-aug:cli/arc-oc-sys-aug:config/arc-oc-sys-aug:unhide-unsupported-cli = 'true')";
    }
  }

  augment "/oc-if:interfaces/oc-if:interface/oc-if:subinterfaces/oc-if:subinterface" {
    uses if-qos-top {
      when "not(derived-from-or-self(/arc-platform:platform/arc-platform:asic, 'arc-platform:X86_64')) or " +
           "derived-from-or-self(/arc-platform:platform/arc-platform:deployment-type, 'arc-platform:DISTRIBUTED') or " +
           "(/oc-sys:system/arc-oc-sys-aug:cli/arc-oc-sys-aug:config/arc-oc-sys-aug:unhide-unsupported-cli = 'true')";
    }
  }
}
