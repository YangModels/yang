module arcos-acl-knob {
  yang-version 1.1;
  namespace "http://yang.arrcus.com/arcos/acl/knob";
  prefix arc-acl-knb;

  container knob-acl {
    description
      "Top-level container for Global ACL knobs";

    container limit-ingress-ip-qualifiers {
      description
        "limit port ip v4/v6 acls to 5-tuple qualifiers (source-address is always there by default)";

      leaf destination-address {
        type empty;
      }
      leaf protocol {
        type empty;
      }
      leaf l4-ports {
        type empty;
      }
      leaf range {
        type empty;
      }
    }
  }
}
