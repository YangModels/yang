module arcos-qos {
  yang-version 1.1;
  namespace "http://yang.arrcus.com/arcos/qos";
  prefix arc-qos;

  import arcos-platform {
    prefix arc-platform;
  }
  import openconfig-system {
    prefix oc-sys;
  }
  import arcos-openconfig-system-augments {
    prefix arc-oc-sys-aug;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for top-level QoS";

  revision 2024-11-07 {
    description "Modified the 'when' clause to enable CLI configuration on VM";
  }

  grouping qos-top {
    description
      "Top level grouping for QoS";
    container qos {
      description
        "Quality of Service";
      action counters {
        description
          "Clear all QoS statistics";
        output {
          leaf result {
            type string;
            description
              "The status of the Clear operation";
          }
        }
      }
    }
  }

  uses qos-top {
    when "(/arc-platform:platform/arc-platform:asic != 'arc-platform:X86_64') or " +
        "(/arc-platform:platform/arc-platform:deployment-type = 'arc-platform:DISTRIBUTED')or "+
        "(/oc-sys:system/arc-oc-sys-aug:cli/arc-oc-sys-aug:config/arc-oc-sys-aug:unhide-unsupported-cli = 'true')";
  }
}
