module arcos-bridge {
  yang-version 1.1;
  namespace "http://yang.arrcus.com/arcos/bridge";
  prefix arc-brdg;

  import openconfig-interfaces {
    prefix oc-if;
  }

  import openconfig-vlan {
    prefix oc-vlan;
  }

  import ietf-yang-types {
    prefix yang;
  }

  organization
    "Arrcus, Inc.";

  contact
    "Arrcus, Inc.
     2077 Gateway Place
     Suite 400
     San Jose, CA 95110

     E-mail: yang-support@arrcus.com";

  description
    "This module contains definitions for the
     native ArcOS bridge domain.

     Copyright (c) 2016-2023 by Arrcus, Inc.
     All rights reserved.";

  revision 2023-05-18 {
    description
      "Add option to give specific mac address with 'address' leaf";
  }

  revision 2023-03-09 {
    description
      "Support L2 sub-interface zero under 'interface' leaf for clear " +
      "mac-address-table command";
  }

  revision 2023-01-06 {
    description
      "Move L2 subinterfaces under 'interface' leaf for clear " +
      "mac-address-table command";
  }

  revision 2022-11-17 {
    description
      "Add L2 subinterface option to clear mac-address-table command";
  }

  rpc clear-mac-address-table {
    description
      "Request to flush the dynamically learned MAC addresses for a
       specified VLAN and interface";

    input {
      leaf vlan {
        type leafref {
          path "/oc-vlan:vlans/oc-vlan:vlan/oc-vlan:config/oc-vlan:vlan-id";
        }
        description
          "VLAN ID of the MAC address table to clear";
      }

      /**
       * Interface name must be 1 of two things:
       * 1. A base L2 intf (exist in top level intf names with no subinterfaces) with vlan id
       * 2. A subinterface name with no VLAN ID parameter entered
       */
      leaf interface {
        when 'not(../address)';
        type union {
          type leafref {
            path "/oc-if:interfaces/oc-if:interface/oc-if:name";
          }
          type leafref {
            path "/oc-if:interfaces/oc-if:interface/oc-if:subinterfaces" +
                 "/oc-if:subinterface/oc-if:config/oc-if:name";
          }
        }
        must "(../vlan and . = /oc-if:interfaces/oc-if:interface/oc-if:name and " +
             "count(/oc-if:interfaces/oc-if:interface[oc-if:name=current()]" +
             "/oc-if:subinterfaces/oc-if:subinterface) = 0) or " +
             "(. = /oc-if:interfaces/oc-if:interface/oc-if:subinterfaces" +
             "/oc-if:subinterface/oc-if:config/oc-if:name and not(../vlan)) or " +
             "(/oc-if:interfaces/oc-if:interface/oc-if:subinterfaces" +
             "/oc-if:subinterface/oc-if:config/oc-if:index = 0 and not(../vlan)) or not(.)" {
          error-message "Interface name must be a valid base interface + VLAN ID specified, or a layer-2 subinterface";
        }
        description
          "Interface name to clear the MAC addresses from";
      }

      leaf address {
        type yang:mac-address;
        description
          "Specific Mac address to clear";
      }
    }
  }

}
