module openconfig-rpc {

  yang-version "1";

  // namespace
  namespace "http://openconfig.net/yang/rpc-api";

  prefix "oc-rpc";

  import openconfig-rpc-types { prefix oc-rpc-types; }
  import openconfig-telemetry { prefix oc-telemetry; }
  import openconfig-extensions { prefix oc-ext; }

  // meta
  organization "OpenConfig working group";

  contact
    "OpenConfig working group
    www.openconfig.net";

  description
    "This module documents a set of RPCs recommended for network
    management systems (NMS) based on OpenConfig models and
    conventions. The RPCs are intended to offer guidance for server
    implementors as a reference for service endpoints which can meet
    requirements for configuration and telemetry.

    These RPCs are meant to be independent of the
    specific RPC implementation or transport protocol (e.g.,
    NETCONF, RESTCONF, gRPC, Thrift/fbthrift, etc.)  That is,
    they provide a reference for the types of operations that would
    be needed to support model-based configuration and telemetry.

    This reference specification defines three primary categories
    of service endpoints:
      * metadata / capabilities exchange
      * streaming telemetry subscriptions
      * modify and retrieve configuration and operational state data

    Actual implementations may provide slightly different variations
    on parameters, naming, etc., or extensions which add additional
    service endpoints.  For example, a specific RPC protocol
    realization may provide its own built-in mechanisms for certain
    parameters such as request/response ids, service versioning,
    etc.";

  oc-ext:openconfig-version "0.2.0";

  revision "2016-04-05" {
    description
      "OpenConfig public release";
    reference "0.2.0";
  }



  // grouping statements

  grouping request-hdr {
    description
      "Common header for all RPC requests";

    leaf request-id {
      type uint64;
      description
        "Identifier sent in request messages";
    }
  }

  grouping reply-hdr {
    description
      "Common header for all RPC replies";

    leaf request-id {
      type uint64;
      description
        "The request id corresponding to the request";
    }
  }

  grouping operation-id {
    description
      "Definition of an operation id, associated with an
      individual command in a mult-command RPC.";

    leaf operation-id {
      type string;
      description
        "The operation id is used to identify a specific
        configuration command, e.g., when the set RPC
        may contain multiple commands.  The response for each
        command can be identified based on the operation-id
        returned by the target device.";
    }
  }

  grouping sub-id {
    description
      "Subscription id data definition";

    leaf subscription-id {
      type uint32;
      description
        "Unique id for the subscription on the device.  This is
        generated by the device and returned in a subscription
        request or when listing existing subscriptions.";
    }
  }

  grouping openconfig-path {
    description
      "Common definition for OpenConfig paths";

    leaf path {
      type oc-rpc-types:openconfig-path;
      description
        "Specifies a path in the data model path corresponding to
        the data in the message";
    }
  }

  grouping openconfig-path-value {
    description
      "Common elements of OpenConfig data instances";

    uses openconfig-path;

    leaf value {
      type string;
      description
        "Data encoded using the encoding specified in
        set-data-encoding, or the device's default encoding.  This
        data may be populated by the management system, e.g., when
        sending configuration data, or by the device when returning
        configuration or operational state / telemetry data.";
    }
  }

  grouping path-prefix {
    description
      "Common defintion for path prefix";

    leaf prefix {
      type oc-rpc-types:openconfig-path;
      description
        "The prefix specifies a common path prefix for all commands
        in a set or get RPC.  The prefix may be used to shorten /
        abbreviate the paths in each command.  If the prefix is not
        specified, path values in each command must be absolute.";
    }
  }

  grouping encoding-spec {
    description
      "Reusable definitions for specifying the data encoding format
      in RPCs";

    leaf encoding {
      type identityref {
        base oc-rpc-types:DATA_ENCODING_METHOD;
      }
      description
        "Specifies the data encoding scheme to be used for data
        sent to and from the target device.  The encoding may
        be specified for all data, or optionally on a per-RPC
        basis if supported by the target.";
    }
  }

  grouping response-code-message {
    description
      "Definitions of RPC response code and response message.";

    leaf response-code {
      type identityref {
        base oc-rpc-types:OPENCONFIG_RPC_RESPONSE_TYPES;
      }
      description
        "Response code indicating the result of the command.";
    }

    leaf message {
      type string;
      description
        "Error or information text associated with the return-code
        value.";
    }
  }


  grouping telemetry-path-list {
    description
      "List of data models paths and filters
       which are used in a telemetry operation.";

    list path {
      key path;
      description "List of data model paths, keyed by path name";

      uses openconfig-path;

      leaf exclude-filter {
        type string;
        description
          "Optional filter expression to be used in filtering data
          elements from the subtree specified by the corresponding
          path.";
      }
    }
  }

  grouping subscription-input {
    description
      "Data associated with a telemetry subscription";

    uses request-hdr;

    list destination {
      key "destination-address destination-port";
      description
      "List of optional collector destinations to send data for
      this subscription, specified as an ip+port combination.
      If no collector destinations are specified, the collector
      destination is assumed to be the requester on the rpc channel";

      uses oc-telemetry:telemetry-stream-destination-config;
    }
    uses telemetry-path-list;
    uses oc-telemetry:telemetry-stream-frequency-config;
    uses oc-telemetry:telemetry-heartbeat-config;
    uses oc-telemetry:telemetry-suppress-redundant-config;
    uses oc-telemetry:telemetry-qos-marking-config;
    uses encoding-spec;

  }

  grouping subscription-response {
    description
      "Response message to a telemetry subscription creation or
       get request.";

    uses request-hdr;

    uses response-code-message;
  }

  grouping model-metadata-common {
    description
      "Metadata associated with YANG modules and bundles supported
      on target devices.";

    leaf name {
      type string;
      description
        "Name of the YANG module, model/bundle, augmentation, or
        deviation module.

        In requests for model data, the name may be a
        regular expression (e.g., POSIX, RE2, etc.) to match against
        supported models on the system.";
    }

    leaf namespace {
      type string;
      description
        "Namespace the model belongs to, whether standard or
        ad-hoc.

        In requests for model data, the namespace may be a
        regular expression (e.g., POSIX, RE2, etc.) to match against
        namespaces in models present on the system (e.g., openconfig
        ietf, etc.";
    }

    leaf version {
      type string;
      description
        "Model version -- for YANG models this should be at least the
        OpenConfig semantic version number, but but could also
        include the YANG revision date.

        In requests for model data, the version may be a
        regular expression (e.g., POSIX, RE2, etc.) to match against
        model versions present on the system.";
    }
  }

  grouping get-models-request {
    description
      "Input parameters for the get-models RPC to retrieve
      information from the target device about its supported
      models.";

    leaf request-type {
      type identityref {
        base oc-rpc-types:MODEL_REQUEST_TYPE;
      }
      description
        "Specifies the type of data that should be returned by the
        get-models request, e.g., metadata only, or the full YANG
        modules.";
    }

  }

  grouping get-models-reply {
    description
      "Data associated with requests for information about the
      data models supported by the device";


    leaf model-type {
      type identityref {
        base oc-rpc-types:GET_MODEL_TYPE;
      }
      description
        "Indicates whether the returned model is an augmentation
        or deviation.";
    }

    leaf model-data {
      type string;
      description
        "If the model code is requested by the client
        (i.e., request-type is 'DETAIL'), this leaf
        contains the YANG module(s) in a text-based encoding";
    }

  }


  grouping config-data-reply {
    description
      "Return values in a reply to requests for configuration
      data: standard reply header and a list of data values with
      the corresponding paths.";

    uses reply-hdr;

    list data {
      key path;
      description
        "List of configuration data items, each consisting of the
        data model path, and corresponding data encoded based on
        the requested format";

      uses openconfig-path-value;
    }

  }

  grouping config-request {
    description
      "Data included in configuration update requests";

    uses request-hdr;

    uses encoding-spec;
    uses path-prefix;

    list operation {
      description
        "List of configuration data items, each consisting of the
        data model path, and corresponding data encoded based on
        the requested format.

        All individual operations in the RPC request should be
        treated collectively as a single transaction. The target
        device should return a successful response only if all
        operations are successful.  If any one of the operations
        fails for any reason, the resulting state of the device
        should be as if none of the operations were applied, i.e.,
        any successful operations should be rolled back.";

      leaf opcode {
        type identityref {
          base oc-rpc-types:SET_CONFIG_COMMANDS;
        }
        description
          "The type of configuration modification requested for the
          corresponding path.  Note that some commands, such as
          'delete' do not specify any associated data with the
          path.";
      }

      uses openconfig-path-value;
    }
  }


  grouping config-reply {
    description
      "Data included in replies to configuration update requests";

    uses reply-hdr;
    uses response-code-message;

  }

  grouping get-data-request {
    description
      "Data items for requests for operational data";

    uses request-hdr;
    uses encoding-spec;
    uses path-prefix;

    leaf data-type {
      type identityref {
        base oc-rpc-types:GET_TYPE;
      }
      description
        "Command indicates what type of data should be
        returned from the specified paths, e.g., configuration,
        opstate, etc.";
    }

    leaf-list path {
      type oc-rpc-types:openconfig-path;
      description
        "List of paths indicating the data to
        be returned.";

    }
  }

  grouping get-data-reply {
    description
      "Data contained in replies to requests for operational data";

    uses reply-hdr;

    list response {
      description
        "List of operational state data items, each consisting of the
        data model path, corresponding data encoded based on
        the requested format, and a response code for each requested
        path.";

      uses openconfig-path-value;
    }

    uses response-code-message;
  }


  // data definition statements

  // augment statements

  // rpc statements


  rpc get-models {
    description
      "Returns a repeated structure of supported data models";
    input {

      uses request-hdr;
      uses model-metadata-common;
      uses get-models-request;
    }
    output {

      uses request-hdr;

      list model {

        key "name version";
        description
          "list of supported schemas";

        uses model-metadata-common;
        uses get-models-reply;
      }

      uses response-code-message;
    }
  }

  rpc set-data-encoding {
    description
      "Select and set one of the data encodings returned by
      getDataEncodings.  This RPC sets the global encoding /
      serialization for all data exchanged with the target
      device.  The global data encoding may be optionally overriden
      by setting the encoding for an individual RPC if supported
      by the target.";
    input {

      uses request-hdr;
      uses encoding-spec;
    }
    output {
      uses request-hdr;
      uses response-code-message;
    }
  }

  rpc get-data-encodings {
    description
      "Return the set of data encodings supported by the device for
      configuration and telemetry data modeled in YANG";

    input {

      uses request-hdr;
    }
    output {

      uses request-hdr;

      leaf-list encoding {
        type identityref {
          base oc-rpc-types:DATA_ENCODING_METHOD;
        }
        description
          "List of supported encoding schemes on the target
          device";
      }

      uses response-code-message;
    }
  }

  rpc subscribe {
    description
      "Request an inline subscription for data at the specified path.
      The device should send telemetry data back on the same
      connection as the subscription request.";
    input {
      uses subscription-input;
    }

    output {

      uses sub-id;
      uses subscription-response;
    }
  }

  rpc cancel {
    description
      "Terminates and removes an exisiting telemetry subscription";
    input {
      uses request-hdr;
      uses sub-id;

    }
    output {

      uses request-hdr;
      uses response-code-message;
    }
  }

  rpc set {
    description
      "Modify configuration on the target device. The set
      RPC accepts a combination of commands, each with an
      associated path specification to indicate which data should
      be modified.

      The commands in a set request should be fully validated and
      accepted by the device before a response is returned.  The
      application of the configuration commands may or may not be
      complete when the command returns.  The NMS is expected to be
      able to track the application of the configuration using the
      operational state data in the telemetry stream, or by
      retrieving the state data using an RPC.";

    input {
      uses config-request;
    }
    output {
      uses config-reply;
    }
  }

  rpc get {
    description
      "Requests data from the network device.  The get RPC
      request should include a subcommand to indicate the type of
      data desired by the requestor.  Supported types of data
      include:

      * configuration data (config: true nodes in the schema)
      * operational state data (config: false nodes)
      * derived operational state only (config: false nodes that
        represent derived operational state, exluding config: false
        nodes that represent applied configuration.
      * all data (config: true and config: false nodes)

      A get RPC can contain multiple requests for data.  Each
      request includes a path specifying a subtree in the data
      model, and a command to indicate which type of data should be
      returned.";
    reference
      "IETF draft-openconfig-netmod-opstate";
    input {
      uses get-data-request;
    }

    output {
      uses get-data-reply;
    }
  }

}
