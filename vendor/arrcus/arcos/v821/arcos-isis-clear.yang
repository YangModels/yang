module arcos-isis-clear {
  yang-version 1.1;
  namespace "http://yang.arrcus.com/arcos/isis/clear";
  prefix arc-isis-clear;

  import openconfig-network-instance {
    prefix oc-ni;
  }

  import openconfig-interfaces {
    prefix oc-if;
  }

  import openconfig-isis-types {
    prefix oc-isis-types;
  }

  import arcos-isis-types {
    prefix arc-isis-types;
  }

  organization
    "Arrcus, Inc.";

  contact
    "Arrcus, Inc.
     Customer Service
     Postal: 2077 Gateway Place
     San Jose, CA 95110
     Tel: +1 408 884-1965
     E-mail: yang-support@arrcus.com";

  description
    "This module defines Arrcus implementation
     of the clear actions for IS-IS.

     Copyright (c) 2023 by Arrcus, Inc.
     All rights reserved.";

  revision 2023-05-15 {
    description
      "Initial module for clear IS-IS";
  }

  grouping clear-adjacency-group {
    container clear-adjacencies {
      action clear-isis-adjacency {
        description
          "Clear all or specific adjacencies";
        input {
          leaf interface {
            when 'not(../system-id)';
            type oc-if:interface-id;
            mandatory false;
            description "Interface to clear";
          }
          leaf level {
            when 'not(../system-id)';
            type oc-isis-types:level-number;
            mandatory false;
            description "IS-IS level";
          }
          leaf af {
            when 'not(../system-id)';
            type identityref {
              base oc-isis-types:AFI_SAFI_TYPE;
            }
            must "current() = 'oc-isis-types:IPV4_UNICAST' or " +
                 "current() = 'oc-isis-types:IPV6_UNICAST'";
            mandatory false;
            description "AFI/SAFI type";
          }
          leaf system-id {
            when 'not(../interface) and not(../af) and not(../level)';
            type arc-isis-types:system-name;
            mandatory false;
            description "System-id to clear";
          }
        }
        output {
          leaf result {
            type string;
            description "Clear adjacency result";
          }
        }
      }
    }
  }

  augment "/oc-ni:network-instances/oc-ni:network-instance" +
          "/oc-ni:protocols/oc-ni:protocol/oc-ni:isis" {
    uses clear-adjacency-group;
  }
}
