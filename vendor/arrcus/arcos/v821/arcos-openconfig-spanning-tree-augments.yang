module arcos-openconfig-spanning-tree-augments {
  yang-version 1.1;
  namespace "http://yang.arrcus.com/arcos/openconfig/spanning-tree/augments";
  prefix arc-oc-stp-aug;

  import openconfig-spanning-tree {
    prefix oc-stp;
  }

  import openconfig-spanning-tree-types {
    prefix oc-stp-types;
  }

  organization
    "Arrcus, Inc.";

  contact
    "Arrcus, Inc.
     2077 Gateway Place
     Suite 400
     San Jose, CA 95110

     E-mail: yang-support@arrcus.com";

  description
    "This module defines augment statements for Arrcus
     implemention of the openconfig-spanning-tree module.

     Copyright (c) 2017-2022 by Arrcus, Inc.
     All rights reserved.";


  revision 2022-09-16 {
    description
      "Add new NONE value for STP_PROTOCOL type";
  }

  identity NONE {
    base oc-stp-types:STP_PROTOCOL;
    description
      "Disables Spanning Tree Protocol";
  }

  augment "/oc-stp:stp/oc-stp:rapid-pvst/oc-stp:vlan/oc-stp:config" {
    leaf edge-only {
      type boolean;
      default "false";
      description
        "Enables Arrcus edge-only mode, disabling full STP operation";
    }
  }

  augment "/oc-stp:stp/oc-stp:rapid-pvst/oc-stp:state/oc-stp:vlan" {
    leaf edge-only {
      type boolean;
      description
        "Enables Arrcus edge-only mode, disabling full STP operation";
    }
  }

}
