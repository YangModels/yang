module arcos-version {
  yang-version 1.1;
  namespace "http://yang.arrcus.com/arcos/version";
  prefix arc-version;

  organization
    "Arrcus, Inc.";

  contact
    "Arrcus, Inc.
     2077 Gateway Place
     San Jose, CA 95110
     Tel: +1 (408) 884-1965
     E-mail: yang-support@arrcus.com";

  description
    "This module contains definitions for ArcOS version information.
     Copyright (c) 2016-2025 by Arrcus, Inc.
     All rights reserved.";

  revision 2025-05-29 {
    description
      "Added hotfix version to show system version output";
  }

  revision 2023-07-28 {
    description
      "Added system uptime to  show system version output";
  }
  

  grouping platform-info {
    description
      "Top-level grouping for platform specific
       data nodes";

    leaf platform {
      type string;
      description
        "Platform Information";
    }

    leaf serial-number {
      type string;
      description
        "Serial number";
    }

    leaf mac-address {
      type string;
      description
        "Device mac address";
    }

    leaf form-factor {
      type string;
      description
        "Form factor of device";
    }

    leaf num-cpu-cores {
      type uint8;
      description
        "Number of CPU cores";
    }

    leaf cpu-info {
      type string;
      description
        "Device CPU information";
    }

    leaf total-memory {
      type string;
      description
        "Total available CPU memory";
    }
  }

  grouping version-state {
    description
      "Top-level grouping for version specific state
       data nodes";

    uses platform-info;

    leaf software {
      type string;
      description
        "Software information";
    }

    leaf sw-version {
      type string;
      description
        "Version number";
    }

    leaf firmware-mu-version {
      type string;
      description
        "Firmware MU version";
    }

    leaf hotfix-version {
      type string;
      description
        "Hotfix version";
    }
    
    leaf uptime {
      type string;
      description
        "System Uptime value";
    }
  }

  grouping version-dependencies-state {
    description
      "Top-level grouping for version dependency state
       data nodes";

    leaf package {
      type string {
        length "1..31";
      }
      description
        "Package name";
    }

    leaf version {
      type string {
        length "1..31";
      }
      description
        "Package version";
    }
  }


  grouping version-dependencies-top {
    container dependencies {
      description
        "Dependency information";

      list dependency {
        key "package";

        description
          "Package information";

        leaf package {
          type leafref {
            path "../state/package";
          }
          description
            "Package name";
        }

        container state {
          uses version-dependencies-state;
        }
      }
    }
  }

  grouping version-top {
    description
      "Top-level grouping for version specific data";

    container version {

      config false;

      container state {
        description
          "Operational state for version specific data";

        uses version-state;
      }

      uses version-dependencies-top;
    }
  }

}
