module arcos-openconfig-bfd-augments {
  yang-version 1.1;
  namespace "http://yang.arrcus.com/arcos/openconfig/bfd/augments";
  prefix arc-oc-bfd-aug;

  import openconfig-bfd {
    prefix oc-bfd;
  }
  import ietf-inet-types {
    prefix inet;
  }
  import ietf-yang-types {
    prefix yang;
  }
  import openconfig-interfaces {
    prefix oc-if;
  }
  import arcos-platform {
    prefix arc-platform;
  }

  organization
    "Arrcus, Inc.";

  contact
    "Arrcus, Inc.
     2077 Gateway Place
     Suite 400
     San Jose, CA 95110
     E-mail: yang-support@arrcus.com";

  description
    "This module defines augmentation for Arrcus
     implementation of the openconfig BFD module.

     Copyright (c) 2016-2023 by Arrcus, Inc.
     All rights reserved.";
  
  revision 2025-09-04 {
    description
      "Add negotiated tx/rx interval to session state";
  }
  
  revision 2025-04-14 {
    description
      "Display BFD last flap timestamp in session state";
  }
  revision 2024-03-21 {
    description 
      "Remove ability to configure local TC value for BFD profiles";
  }

  revision 2023-11-29 {
    description
      "Update the model to support MH and MPLS BFD in the
       future.";
  }

  revision 2023-11-25 {
    description 
      "Ability to configure DSCP and local TC value for BFD profiles";
  }

  revision 2023-09-12 {
    description "Display BFD related config based on interface name";
  }

  revision 2023-08-15 {
    description
      "Disable offload configuration for distributed platforms";
  }

  revision 2018-11-14 {
    description
      "Initial Revision
      ";
  }

  identity session-type {
    description
      "Base identity for BFD session types.";
  }

  identity BFD_SESSION_TYPE_UDP_IPV4 {
    base session-type;
    description
      "BFD session type for IPv4 over UDP";
  }

  identity BFD_SESSION_TYPE_UDP_IPV6 {
    base session-type;
    description
      "BFD session type for IPv6 over UDP";
  }

  identity BFD_SESSION_TYPE_MICRO_UDP_IPV4 {
    base session-type;
    description
      "BFD session type for Micro IPv4 over UDP";
  }

  identity BFD_SESSION_TYPE_MICRO_UDP_IPV6 {
    base session-type;
    description
      "BFD session type for Micro IPv6 over UDP";
  }

  identity BFD_SESSION_TYPE_MULTI_HOP_UDP_IPV4 {
    base session-type;
    description
      "BFD session type for Multi Hop IPv4 over UDP";
  }

  identity BFD_SESSION_TYPE_MULTI_HOP_UDP_IPV6 {
    base session-type;
    description
      "BFD session type for Multi Hop IPv6 over UDP";
  }

  grouping bfd-single-hop-config {
    description
      "Grouping for single-hop BFD sessions config.";

    leaf interface {
      type oc-if:base-interface-ref;
      description
        "Reference to interface that will be used for this BFD
         session.";
    }

    leaf dest-addr {
      type inet:ip-address-no-zone;
      description
        "Destination IP address of this BFD session.";
    }
  }

  grouping bfd-common-state {
    description
      "Grouping for common state of BFD.";

    leaf local-address {
      type inet:ip-address-no-zone;
      description
        "Local IP address used to establish this BFD session.";
    }
  }

  grouping bfd-config {
    description
      "Grouping for BFD config/state.";

    leaf desired-minimum-tx-interval {
      type uint32;
      units microseconds;
      description
        "The minimum interval between transmission of BFD control
        packets that the operator desires. This value is advertised to
        the peer, however the actual interval used specified by
        taking the maximum of desired-minimum-tx-interval and the
        value of the remote required-minimum-receive interval value.

        This value is specified as an integer number of microseconds.";
    }

    leaf required-minimum-receive {
      type uint32;
      units microseconds;
      description
        "The minimum interval between received BFD control packets that
        this system should support. This value is advertised to the
        remote peer to indicate the maximum frequency (i.e., minimum
        inter-packet interval) between BFD control packets that is
        acceptable to the local system";
    }

    leaf detection-multiplier {
      type uint16 {
        range "1..max";
      }
      description
        "The number of packets that must be missed to declare this
        session as down. The detection interval for the BFD session
        is calculated by multiplying the value of the negotiated
        transmission interval by this value";
    }

    leaf enabled {
      type boolean;
      default false;
      description
        "When set to true, this BFD session is enabled.";
    }

    leaf profile {
      type leafref {
        path "/oc-bfd:bfd/oc-bfd:interfaces/oc-bfd:interface" +
            "/oc-bfd:config/oc-bfd:id";
      }
      description
        "Reference to profile that will be used as part of
         this session.";
    }
  }

  grouping bfd-top {
    container single-hop {
      container sessions {
        list session {
          key "intf";
          description
            "List of all single-hop BFD sessions.";

          leaf intf {
            type oc-if:base-interface-ref;
            description
              "Interface that is used by single-hop BFD.";
          }

          container config {
            description
              "Container for config portion of BFD.";

            uses bfd-config {
              when "not(starts-with(/oc-bfd:bfd/arc-oc-bfd-aug:single-hop/arc-oc-bfd-aug:sessions/arc-oc-bfd-aug:session, 'loopback'))";
            }
          }

          container state {
            config false;
            description
              "Container for state portion of BFD.";

            uses bfd-config;
          }
        }
      }
    }
  }

  grouping bfd-peer-state-top {
    leaf hw-offload-status {
      type boolean;
      description
        "Hardware offload status.";
    }
    leaf interface {
      type leafref {
        path "/oc-if:interfaces/oc-if:interface/oc-if:name";
      }
      description "Micro BFD interface";
    }
    leaf parent-interface {
      type leafref {
        path "/oc-if:interfaces/oc-if:interface/oc-if:name";
      }
      description "Micro BFD Parent interface";
    }
    leaf hw-endpoint-id {
      type int32;
      description
        "Hardware Endpoint ID.";
    }
    leaf network-instance {
      type string;
      description
        "Network Instance Name.";
    }
    leaf local-desired-minimum-tx-interval {
      type uint32;
      description
        "Local Desied Minimum Tx Interval configured for this session.";
    }
    leaf local-required-minimum-receive {
      type uint32;
      description
        "Local Required Minimum Rx Interval configured for this session.";
    }
    leaf local-detection-multiplier {
      type uint16;
      description
        "Local Detection Multiplier configured for this session.";
    }
    leaf negotiated-tx-interval {
      type uint32;
      description
        "Negotiated Tx Interval for this session.";
    }
    leaf negotiated-rx-interval {
      type uint32;
      description
        "Negotiated Rx Interval for this session.";
    }
    leaf session-type {
      type identityref {
        base session-type;
      }
      description
        "BFD session-type";
    }
    leaf session-up-time {
      type string;
      description
        "Time since the session became UP.";
    }
  }

  grouping bfd-micro-remote-address-top {
    container remote-address {
      leaf ipv4 {
          type inet:ipv4-address-no-zone;
          description "Destination IPV4 address for the micro BFD sessions";
      }
      leaf ipv6 {
          type inet:ipv6-address-no-zone;
          description "Destination IPV6 address for the micro BFD sessions";
      }
    }
  }

  grouping bfd-micro-profile-top {
    leaf profile {
      type leafref {
        path "/oc-bfd:bfd/oc-bfd:interfaces/oc-bfd:interface/oc-bfd:config" +
             "/oc-bfd:id";
      }
      description
        "A reference to the BFD profile.";
    }
  }
  grouping bfd-micro-intf-config {
    uses bfd-micro-remote-address-top;
    uses bfd-micro-profile-top;
    leaf enabled {
      type boolean;
      description "Enable Micro BFD sessions";
    }
  }
  grouping bfd-dscp-config {
    leaf dscp-value {
      type uint32 {
        range "0..63";
      }
      default 48;
      description
        "The DSCP/Traffic class value that we want the BFD packets to use";
    }
  }

  augment "/oc-if:interfaces/oc-if:interface" {
    when "starts-with(current()/oc-if:name, 'bond')" {
      description "Micro BFD configs for LAG interface";
    }

    container bfd {
      description "BFD interface specific configurations";
      container micro {
        description "Micro BFD interface specific configurations";
        container config {
          description "Micro BFD interface configurations";
          uses bfd-micro-intf-config;
        }
        container state {
          description "Micro BFD interface sessions states";
          config false;
          uses bfd-micro-intf-config;
        }
      }
    }
  }

  augment "/oc-bfd:bfd/oc-bfd:interfaces/oc-bfd:interface/oc-bfd:peers" +
          "/oc-bfd:peer/oc-bfd:state" {
    uses bfd-peer-state-top;
  }

  augment "/oc-bfd:bfd/oc-bfd:interfaces/oc-bfd:interface/oc-bfd:config" {
    leaf v4-hw-offload {
      when "not(derived-from-or-self(" +
           "/arc-platform:platform/arc-platform:deployment-type, " +
           "'arc-platform:DISTRIBUTED'))";
      type boolean;
      description "BFDv4 Hardware offload";
    }
    leaf v6-hw-offload {
      when "not(derived-from-or-self(" +
           "/arc-platform:platform/arc-platform:deployment-type, " +
           "'arc-platform:DISTRIBUTED'))";
      type boolean;
      description "BFDv6 Hardware offload";
    }
    uses bfd-dscp-config;
  }

  augment "/oc-bfd:bfd/oc-bfd:interfaces/oc-bfd:interface/oc-bfd:state" {
    leaf v4-hw-offload {
      type boolean;
      description "BFDv4 Hardware offload";
    }
    leaf v6-hw-offload {
      type boolean;
      description "BFDv6 Hardware offload";
    }
    uses bfd-dscp-config;
  }
  augment "/oc-bfd:bfd" {
    uses bfd-top;
  }

}
