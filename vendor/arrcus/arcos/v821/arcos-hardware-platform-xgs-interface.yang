module arcos-hardware-platform-xgs-interface {
  yang-version 1.1;
  namespace "http://yang.arrcus.com/arcos/hardware/platform/xgs/interface";
  prefix arc-hw-platform-xgs-if;

  import arcos-hardware {
    prefix arc-hw;
  }

  import arcos-hardware-platform-types {
    prefix arc-hw-platform-types;
  }

  grouping mmu-queue-attrs {
    leaf threshold {
      type arc-hw-platform-types:MMU_QUEUE_ALPHA_VALUE;
      description "Dynamic threshold value setting for queue";
    }
    leaf rsvd-buf {
      type uint32;
      description "Reserved buffer space for queue in bytes";
    }
    leaf instantaneous-buf-occupancy {
      type uint32;
      description "Buffer utilization for queue in bytes";
    }
  }

  grouping xgs-intf-mmu-profile {
    list mmu {
      description "Interface level MMU configuration options";
      key "direction";

      leaf direction {
        description "Direction of traffic on this interface to bind the queue profile to";
        type enumeration {
          enum EGRESS;
        }
      }

      container queue {

        container config {
          leaf profile {
            description "MMU queue profile applied to interface";
            type leafref {
              path "/arc-hw:hardware/arc-hw:config/arc-hw:platform" +
                   "/arc-hw:mmu/arc-hw:config/arc-hw:queue" +
                   "/arc-hw:profile/arc-hw:name";
            }
          }
        }

        container state {
          config false;

          leaf profile {
            type string {
              length "0..64";
            }
            description "Name of MMU queue profile";
          }
          container ucast-queue-0 {
            uses mmu-queue-attrs;
          }
          container ucast-queue-1 {
            uses mmu-queue-attrs;
          }
          container ucast-queue-2 {
            uses mmu-queue-attrs;
          }
          container ucast-queue-3 {
            uses mmu-queue-attrs;
          }
          container ucast-queue-4 {
            uses mmu-queue-attrs;
          }
          container ucast-queue-5 {
            uses mmu-queue-attrs;
          }
          container ucast-queue-6 {
            uses mmu-queue-attrs;
          }
          container ucast-queue-7 {
            uses mmu-queue-attrs;
          }
          container mcast-queue-0 {
            uses mmu-queue-attrs;
          }
          container mcast-queue-1 {
            uses mmu-queue-attrs;
          }
          container mcast-queue-2 {
            uses mmu-queue-attrs;
          }
          container mcast-queue-3 {
            uses mmu-queue-attrs;
          }
          container mcast-queue-4 {
            uses mmu-queue-attrs;
          }
          container mcast-queue-5 {
            uses mmu-queue-attrs;
          }
          container mcast-queue-6 {
            uses mmu-queue-attrs;
          }
          container mcast-queue-7 {
            uses mmu-queue-attrs;
          }
        }
      }
    }
  }
}
