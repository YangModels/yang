module arcos-datapath-asic {
  yang-version 1.1;
  namespace "http://yang.arrcus.com/arcos/datapath/asic";
  prefix arcos-dp-asic;

  import arcos-platform {
    prefix arc-platform;
  }

  import arcos-features {
    prefix arc-features;
  }

  organization
    "Arrcus, Inc.";

  contact
    "Arrcus, Inc.
     Customer Service
     Postal: 2077 Gateway Place
     San Jose, CA 95110
     Tel: +1 1XXX XXX-XXXX
     E-mail: xxx@arrcus.com";

  description
    "YANG data-model for counters read from ASIC.

     Copyright (c) 2022 by Arrcus, Inc.
     All rights reserved.";

  revision "2022-03-01" {
    description
      "Initial version";
    reference "0.1.0";
  }

  grouping asic-pipeline-pkt-drops {
    description
      "Group for packet drop counters in ASIC pipeline";

    container asic-packet-drops {
      config false;
      description
        "Top level container for all packet drops in ASIC pipeline";

      leaf queue-not-found {
        type uint64;
        description
          "Packet drops due to queue not found";
      }
      leaf sram-enqueue-reject {
        type uint64;
        description
          "Packet drops due to SRAM enqueue rejected";
      }
      leaf data-copy-errors {
        type uint64;
        description
          "Packet drops due data copy failure in DRAM";
      }
      leaf dram-crc-errors {
        type uint64;
        description
          "Packet drops due DRAMC CRC error";
      }
      leaf dram-crc-flipped-errors {
        type uint64;
        description
          "Packet drops due DRAMC CRC flipped error";
      }
      leaf pkt-crc-errors {
        type uint64;
        description
          "Packet drops due packet CRC error";
      }
      leaf tx-ucast-drops {
        type uint64;
        description
          "Unicast Packet drops on egress pipeline";
      }
      leaf tx-mcast-drops {
        type uint64;
        description
          "Multicast Packet drops on egress pipeline";
      }
    }

    container asic-cmic-packet-drops {
      config false;
      description
        "Top level container for CMIC error counters";

      leaf cmic-out-errors {
        type uint64;
        description
          "Packet errors to ASIC from CMIC";
      }
      leaf cmic-in-errors {
        type uint64;
        description
          "Packet errors from ASIC to CMIC";
      }
    }
  }

  grouping asic-pipeline-pkt-count {
    description
      "Group for packet counters from ASIC pipeline";

    container asic-packet-count {
      config false;
      description
        "Top level container for all pipeline counters";

      leaf rx-intf-packets {
        type uint64;
        description
          "NIF interface stats";
      }
      leaf rx-recycle-intf-packets {
        type uint64;
        description
          "Recycle port stats";
      }
      leaf cpu-injected-packets {
        type uint64;
        description
          "CPU injected packets";
      }
      leaf tx-total-packets {
        type uint64;
        description
          "Total TX packets";
      }
      leaf rx-total-packets {
        type uint64;
        description
          "Total RX packets";
      }
      leaf fabric-in-packets {
        type uint64;
        description
          "Packets from fabric";
      }
      leaf fabric-out-packets {
        type uint64;
        description
          "Packets to fabric";
      }
    }

    container asic-cmic-packet-count {
      config false;
      description
        "Top level container for CMIC counters";

      leaf cmic-out-packets {
        type uint64;
        description
          "Packets to ASIC from CMIC";
      }
      leaf cmic-in-packets {
        type uint64;
        description
          "Packets from ASIC to CMIC";
      }
    }
  }

  grouping external-tcam-counter-group {
    description
      "Group for counters in external TCAM";

    container external-tcam-interface-counters {
      config false;
      description
        "Top level container for all external TCAM interface counters in ASIC pipeline";

      leaf tx-pkt-counter {
        type uint64;
        description
          "Packet sent to external TCAM";
      }

      leaf rx-pkt-counter {
        type uint64;
        description
          "Packet received from external TCAM";
      }

      leaf tx-byte-counter {
        type uint64;
        description
          "Bytes sent to external TCAM";
      }

      leaf rx-byte-counter {
        type uint64;
        description
          "Bytes received from external TCAM";
      }
    }

    container external-tcam-runtime-counters {
      config false;
      description
        "Top level container for all external TCAM interface counters in ASIC pipeline";

      leaf unresolved-errors {
        type uint64;
        description
          "External TCAM errors that were not resolved";
      }

      leaf resolved-errors {
        type uint64;
        description
          "External TCAM errors that were resolved";
      }

      leaf pkt-and-intf-errors {
        type uint64;
        description
          "External TCAM packet or interface errors";
      }

      leaf device-uncorrectable-errors {
        type uint64;
        description
          "External TCAM device level uncorrectable errors";
      }

      leaf device-uncorrectable-fcs-errors {
        type uint64;
        description
          "External TCAM device level FCS uncorrectable errors";
      }

      leaf-list intf-unresolved-errors {
        type uint64;
        description
          "KBP interface unresolved errors";
      }

      leaf-list intf-resolved-errors {
        type uint64;
        description
          "KBP interface resolved errors";
      }
    }
  }

  grouping external-tcam-counter-top {
    description
      "Group for external TCAM counters";

    container external-tcam-counters {
      config false;
      description
        "Top level container for all external tcam counters";

      when " ((/arc-platform:platform/arc-platform:family = 'arc-platform:BROADCOM_DNX') or "
          + " (/arc-platform:platform/arc-platform:deployment-type = 'arc-platform:DISTRIBUTED')) and "
          + "(/arc-features:features/arc-features:feature[arc-features:name='arc-features:ARCOS_EXTERNAL_TCAM']"
          + "/arc-features:supported = 'true')";

      uses external-tcam-counter-group;
    }
  }

  grouping asic-pkt-count {
    description
      "Group for ASIC packet count";

    container asic-counters {
      config false;
      description
        "Top level container for all pipeline counters and drops";

      when " ((/arc-platform:platform/arc-platform:family = 'arc-platform:BROADCOM_DNX') or "
         + "  (/arc-platform:platform/arc-platform:deployment-type = 'arc-platform:DISTRIBUTED'))";

      uses asic-pipeline-pkt-drops;
      uses asic-pipeline-pkt-count;
    }
  }
}
