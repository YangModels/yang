module arcos-ietf-ipsec-ike-deviations {
  yang-version 1.1;
  namespace "http://yang.arrcus.com/arcos/ipsec/deviations";
  prefix arc-ipsec-dev;

  import tailf-common {
    prefix tailf;
  }

  import ietf-ipsec-ike {
    prefix ietf-ipsec;
  }

  deviation "/ietf-ipsec:ipsec-ike/ietf-ipsec:pad/ietf-ipsec:pad-entry" +
            "/ietf-ipsec:identity/ietf-ipsec:ipv6-address" {
    deviate not-supported;
    description "Not supported in this release";
  }

  deviation "/ietf-ipsec:ipsec-ike/ietf-ipsec:pad/ietf-ipsec:pad-entry" +
            "/ietf-ipsec:identity/ietf-ipsec:fqdn-string" {
    deviate not-supported;
    description "Not supported in this release";
  }

  deviation "/ietf-ipsec:ipsec-ike/ietf-ipsec:pad/ietf-ipsec:pad-entry" +
            "/ietf-ipsec:identity/ietf-ipsec:rfc822-address-string" {
    deviate not-supported;
    description "Not supported in this release";
  }

  deviation "/ietf-ipsec:ipsec-ike/ietf-ipsec:pad/ietf-ipsec:pad-entry" +
            "/ietf-ipsec:identity/ietf-ipsec:dnx509" {
    deviate not-supported;
    description "Not supported in this release";
  }

  deviation "/ietf-ipsec:ipsec-ike/ietf-ipsec:pad/ietf-ipsec:pad-entry" +
            "/ietf-ipsec:identity/ietf-ipsec:gnx509" {
    deviate not-supported;
    description "Not supported in this release";
  }

  deviation "/ietf-ipsec:ipsec-ike/ietf-ipsec:pad/ietf-ipsec:pad-entry" +
            "/ietf-ipsec:identity/ietf-ipsec:id-key" {
    deviate not-supported;
    description "Not supported in this release";
  }

  deviation "/ietf-ipsec:ipsec-ike/ietf-ipsec:pad/ietf-ipsec:pad-entry" +
            "/ietf-ipsec:identity/ietf-ipsec:id-null" {
    deviate not-supported;
    description "Not supported in this release";
  }

  deviation "/ietf-ipsec:ipsec-ike/ietf-ipsec:pad/ietf-ipsec:pad-entry" +
            "/ietf-ipsec:peer-authentication/ietf-ipsec:eap-method" {
    deviate not-supported;
    description "Not supported in this release";
  }

  deviation "/ietf-ipsec:ipsec-ike/ietf-ipsec:pad/ietf-ipsec:pad-entry" +
            "/ietf-ipsec:peer-authentication/ietf-ipsec:digital-signature" {
    deviate not-supported;
    description "Not supported in this release";
  }

  deviation "/ietf-ipsec:ipsec-ike/ietf-ipsec:pad/ietf-ipsec:pad-entry" +
            "/ietf-ipsec:peer-authentication/ietf-ipsec:auth-method" {
    deviate replace {
      type enumeration {
        enum pre-shared {
          description "Select pre-shared key as the authentication method.";
          tailf:code-name "auth-method-pre-shared";
        }
      }
    }
    description "Authentication Method";
  }

  deviation "/ietf-ipsec:ipsec-ike/ietf-ipsec:conn-entry" +
            "/ietf-ipsec:authalg" {
    deviate replace {
      type enumeration {
        enum md5 {
          description "MD5 HMAC";
        }
        enum md5_128 {
          description "MD5_128 HMAC";
        }
        enum sha1 {
          description "SHA1 HMAC";
        }
        enum sha1_160 {
          description "SHA1_160 HMAC";
        }
        enum aesxcbc {
          description "AES XCBC";
        }
        enum aescmac {
          description "AES CMAC";
        }
        enum aes128gmac {
          description "128-bit AES GMAC";
          tailf:code-name authalg-aes128gmac;
        }
        enum aes192gmac {
          description "192-bit AES GMAC";
          tailf:code-name authalg-aes192gmac;
        }
        enum aes256gmac {
          description "256-bit AES GMAC";
          tailf:code-name authalg-aes256gmac;
        }
        enum sha2_256 {
          description "SHA2_256 128 bit HMAC";
        }
        enum sha2_384 {
          description "SHA2_384 192 bit HMAC";
        }
        enum sha2_512 {
          description "SHA2_512 256 bit HMAC";
        }
        enum sha2_256_96 {
          description "SHA2_256 96 bit HMAC";
        }
      }
    }
    deviate delete {
      default 12;
    }
    deviate add {
      default sha2_256;
      max-elements 3;
    }
    description "Integrity algorithms";
  }

  deviation "/ietf-ipsec:ipsec-ike/ietf-ipsec:conn-entry" +
            "/ietf-ipsec:encalg" {
    deviate replace {
      type enumeration {
        enum 3des {
          description "168 bit 3DES-EDE-CBC";
        }
        enum aes128 {
          description "128 bit AES-CBC";
        }
        enum aes192 {
          description "192 bit AES-CBC";
        }
        enum aes256 {
          description "256 bit AES-CBC";
        }
        enum aes128ctr {
          description "128 bit AES-COUNTER";
        }
        enum aes192ctr {
          description "192 bit AES-COUNTER";
        }
        enum aes256ctr {
          description "256 bit AES-COUNTER";
        }
        enum aes128ccm64 {
          description "128 bit AES-CCM with 64 bit ICV";
        }
        enum aes192ccm64 {
          description "192 bit AES-CCM with 64 bit ICV";
        }
        enum aes256ccm64 {
          description "256 bit AES-CCM with 64 bit ICV";
        }
        enum aes128ccm96 {
          description "128 bit AES-CCM with 96 bit ICV";
        }
        enum aes192ccm96 {
          description "192 bit AES-CCM with 96 bit ICV";
        }
        enum aes256ccm96 {
          description "256 bit AES-CCM with 96 bit ICV";
        }
        enum aes128ccm128 {
          description "128 bit AES-CCM with 128 bit ICV";
        }
        enum aes192ccm128 {
          description "192 bit AES-CCM with 128 bit ICV";
        }
        enum aes256ccm128 {
          description "256 bit AES-CCM with 128 bit ICV";
        }
        enum aes128gcm64 {
          description "128 bit AES-GCM with 64 bit ICV";
        }
        enum aes192gcm64 {
          description "192 bit AES-GCM with 64 bit ICV";
        }
        enum aes256gcm64 {
          description "256 bit AES-GCM with 64 bit ICV";
        }
        enum aes128gcm96 {
          description "128 bit AES-GCM with 96 bit ICV";
        }
        enum aes192gcm96 {
          description "192 bit AES-GCM with 96 bit ICV";
        }
        enum aes256gcm96 {
          description "256 bit AES-GCM with 96 bit ICV";
        }
        enum aes128gcm128 {
          description "128 bit AES-GCM with 128 bit ICV";
        }
        enum aes192gcm128 {
          description "192 bit AES-GCM with 128 bit ICV";
        }
        enum aes256gcm128 {
          description "256 bit AES-GCM with 128 bit ICV";
        }
        enum aes128gmac {
          description "Null encryption with 128 bit AES-GMAC";
        }
        enum aes192gmac {
          description "Null encryption with 192 bit AES-GMAC";
        }
        enum aes256gmac {
          description "Null encryption with 256 bit AES-GMAC";
        }
      }
    }
    deviate delete {
      default 12;
    }
    deviate add {
      default aes256ctr;
      max-elements 3;
    }
    description "Encryption algorithms";
  }

  deviation "/ietf-ipsec:ipsec-ike/ietf-ipsec:conn-entry" +
            "/ietf-ipsec:initial-contact" {
    deviate not-supported;
    description "Not supported in this release";
  }

  deviation "/ietf-ipsec:ipsec-ike/ietf-ipsec:conn-entry" +
            "/ietf-ipsec:fragmentation" {
    deviate not-supported;
    description "Not supported in this release";
  }

  deviation "/ietf-ipsec:ipsec-ike/ietf-ipsec:conn-entry" +
            "/ietf-ipsec:ike-sa-lifetime-soft/ietf-ipsec:reauth-time" {
    deviate not-supported;
    description "Not supported in this release";
  }

  deviation "/ietf-ipsec:ipsec-ike/ietf-ipsec:conn-entry" +
            "/ietf-ipsec:ike-sa-lifetime-hard" {
    deviate not-supported;
    description "Not supported in this release";
  }

  deviation "/ietf-ipsec:ipsec-ike/ietf-ipsec:conn-entry" +
            "/ietf-ipsec:half-open-ike-sa-timer" {
    deviate not-supported;
    description "Not supported in this release";
  }

  deviation "/ietf-ipsec:ipsec-ike/ietf-ipsec:conn-entry" +
            "/ietf-ipsec:half-open-ike-sa-cookie-threshold" {
    deviate not-supported;
    description "Not supported in this release";
  }

  deviation "/ietf-ipsec:ipsec-ike/ietf-ipsec:conn-entry" +
            "/ietf-ipsec:local" {
    deviate not-supported;
    description "Not supported in this release";
  }

  deviation "/ietf-ipsec:ipsec-ike/ietf-ipsec:conn-entry" +
            "/ietf-ipsec:remote" {
    deviate not-supported;
    description "Not supported in this release";
  }

  deviation "/ietf-ipsec:ipsec-ike/ietf-ipsec:conn-entry" +
            "/ietf-ipsec:encapsulation-type" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:anti-replay-window" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:traffic-selector" +
            "/ietf-ipsec:inner-protocol" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:traffic-selector" +
            "/ietf-ipsec:local-ports" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:traffic-selector" +
            "/ietf-ipsec:remote-ports" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:traffic-selector" +
            "/ietf-ipsec:local-subnet" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:traffic-selector" +
            "/ietf-ipsec:remote-subnet" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:processing-info" +
            "/ietf-ipsec:ipsec-sa-cfg/ietf-ipsec:pfp-flag" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:processing-info" +
            "/ietf-ipsec:ipsec-sa-cfg/ietf-ipsec:ext-seq-num" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:processing-info" +
            "/ietf-ipsec:action" {
    deviate replace {
      type enumeration {
        enum protect {
                description
                    "PROTECT the traffic with IPsec.";
        }
      }
    }
    deviate delete {
      default discard;
    }
    description "Action when traffic matches an IPsec policy";
  }

  deviation "/ietf-ipsec:ipsec-ike/ietf-ipsec:conn-entry" +
            "/ietf-ipsec:spd/ietf-ipsec:spd-entry" +
            "/ietf-ipsec:ipsec-policy-config/ietf-ipsec:processing-info" +
            "/ietf-ipsec:ipsec-sa-cfg/ietf-ipsec:seq-overflow" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:processing-info" +
            "/ietf-ipsec:ipsec-sa-cfg/ietf-ipsec:stateful-frag-check" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:processing-info" +
            "/ietf-ipsec:ipsec-sa-cfg/ietf-ipsec:mode" {
    deviate replace {
      default tunnel;
    }
    description "Type definition of IPsec mode";
  }

  deviation "/ietf-ipsec:ipsec-ike/ietf-ipsec:conn-entry" +
            "/ietf-ipsec:spd/ietf-ipsec:spd-entry" +
            "/ietf-ipsec:ipsec-policy-config/ietf-ipsec:processing-info" +
            "/ietf-ipsec:ipsec-sa-cfg/ietf-ipsec:esp-algorithms" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:processing-info" +
            "/ietf-ipsec:ipsec-sa-cfg/ietf-ipsec:protocol-parameters" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:processing-info" +
            "/ietf-ipsec:ipsec-sa-cfg/ietf-ipsec:tunnel" +
            "/ietf-ipsec:df-bit" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:processing-info" +
            "/ietf-ipsec:ipsec-sa-cfg/ietf-ipsec:tunnel" +
            "/ietf-ipsec:bypass-dscp" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:processing-info" +
            "/ietf-ipsec:ipsec-sa-cfg/ietf-ipsec:tunnel" +
            "/ietf-ipsec:dscp-mapping" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:processing-info" +
            "/ietf-ipsec:ipsec-sa-cfg/ietf-ipsec:tunnel" +
            "/ietf-ipsec:ecn" {
    deviate not-supported;
    description "Not supported in this release";
  }

  deviation "/ietf-ipsec:ipsec-ike/ietf-ipsec:conn-entry" +
            "/ietf-ipsec:spd/ietf-ipsec:spd-entry" +
            "/ietf-ipsec:ipsec-policy-config/ietf-ipsec:spd-mark" +
            "/ietf-ipsec:mask" {
    deviate not-supported;
    description "Not supported in this release";
  }

  deviation "/ietf-ipsec:ipsec-ike/ietf-ipsec:conn-entry" +
            "/ietf-ipsec:child-sa-info" {
    deviate not-supported;
    description "Not supported in this release";
  }

  deviation "/ietf-ipsec:ipsec-ike/ietf-ipsec:conn-entry" +
            "/ietf-ipsec:state/ietf-ipsec:nat-local" {
    deviate not-supported;
    description "Not supported in this release";
  }

  deviation "/ietf-ipsec:ipsec-ike/ietf-ipsec:conn-entry" +
            "/ietf-ipsec:state/ietf-ipsec:nat-remote" {
    deviate not-supported;
    description "Not supported in this release";
  }

  deviation "/ietf-ipsec:ipsec-ike/ietf-ipsec:conn-entry" +
            "/ietf-ipsec:state/ietf-ipsec:encapsulation-type" +
            "/ietf-ipsec:espencap" {
    deviate not-supported;
    description "Not supported in this release";
  }

  deviation "/ietf-ipsec:ipsec-ike/ietf-ipsec:conn-entry" +
            "/ietf-ipsec:state/ietf-ipsec:encapsulation-type" +
            "/ietf-ipsec:oaddr" {
    deviate not-supported;
    description "Not supported in this release";
  }

  deviation "/ietf-ipsec:ipsec-ike/ietf-ipsec:number-ike-sas" {
    deviate not-supported;
    description "Not supported in this release";
  }
}
