module arcos-icmp-types {
  yang-version 1.1;
  namespace "http://yang.arrcus.com/arcos/icmp/types";
  prefix arc-icmp-types;

  organization
    "Arrcus, Inc.";

    contact
        "Email: eng@arrcus.com";

  description
    "This module defines Internet Control Message Protocol (ICMP) message
    types and codes for use in models requiring data definitions related
    to ICMP.";

  revision 2023-08-30 {
      description 
        "Removed icmp type/code range restriction";
  }

  identity ICMP_TYPE {
    description
      "Base identity for ICMP message type values used in ICMP packet header.
      The deprecated, reserved and experimental types are not defined in this
      identity.";
    reference
      "RFC 792";
  }

  identity ICMP_ECHO_REPLY {
    base ICMP_TYPE;
    description
      "Echo Reply (0)";
  }

  identity ICMP_DST_UNREACH {
    base ICMP_TYPE;
    description
      "Destination Unreachable (3)";
  }

  identity ICMP_REDIRECT {
    base ICMP_TYPE;
    description
      "Redirect Message (5)";
  }

  identity ICMP_ECHO_REQUEST {
    base ICMP_TYPE;
    description
      "Echo Request (8)";
  }

  identity ICMP_ROUTER_ADVERT {
    base ICMP_TYPE;
    description
      "Router Advertisement (9)";
  }

  identity ICMP_ROUTER_SOLICIT {
    base ICMP_TYPE;
    description
      "Router Solicitation (10)";
  }

  identity ICMP_TIME_EXCEEDED {
    base ICMP_TYPE;
    description
      "Time Exceeded (11)";
  }

  identity ICMP_PARAM_PROBLEM {
    base ICMP_TYPE;
    description
      "Paramter Problem: Bad IP header (12)";
  }

  identity ICMP_TIMESTAMP {
    base ICMP_TYPE;
    description
      "Timestamp (13)";
  }

  identity ICMP_TIMESTAMP_REPLY {
    base ICMP_TYPE;
    description
      "Timestamp Reply (14)";
  }


  identity ICMP_DST_UNREACH_CODE {
    description
      "Base identity for ICMP message code values for type Destination
      Unreachable used in ICMP packet header.";
    reference
      "RFC 792";
  }

  identity ICMP_NET_UNREACH {
    base ICMP_DST_UNREACH_CODE;
    description
      "Net Unreachable (0)";
  }

  identity ICMP_HOST_UNREACH {
    base ICMP_DST_UNREACH_CODE;
    description
      "Host Unreachable (1)";
  }

  identity ICMP_PROTO_UNREACH {
    base ICMP_DST_UNREACH_CODE;
    description
      "Protocol Unreachable (2)";
  }

  identity ICMP_PORT_UNREACH {
    base ICMP_DST_UNREACH_CODE;
    description
      "Port Unreachable (3)";
  }

  identity ICMP_FRAGMENT {
    base ICMP_DST_UNREACH_CODE;
    description
      "Fragmentation Needed and Don't Fragment was Set (4)";
  }

  identity ICMP_SRC_ROUTE_FAIL {
    base ICMP_DST_UNREACH_CODE;
    description
      "Source Route Failed (5)";
  }

  identity ICMP_DST_NET_UNKNOWN {
    base ICMP_DST_UNREACH_CODE;
    description
      "Destination Network Unknown (6)";
  }

  identity ICMP_DST_HOST_UNKNOWN {
    base ICMP_DST_UNREACH_CODE;
    description
      "Destination Host Unknown (7)";
  }

  identity ICMP_SRC_HOST_UNKNOWN {
    base ICMP_DST_UNREACH_CODE;
    description
      "Source Host Unknown (8)";
  }

  identity ICMP_NET_PROHIBITED {
    base ICMP_DST_UNREACH_CODE;
    description
      "Communication with Destination Network is Administratively
      Prohibited (9)";
  }

  identity ICMP_HOST_PROHIBITED {
    base ICMP_DST_UNREACH_CODE;
    description
      "Communication with Destination HOST is Administratively
      Prohibited (10)";
  }

  identity ICMP_NET_UNREACH_TOS {
    base ICMP_DST_UNREACH_CODE;
    description
      "Destination Network Unreachable for Type of Service (11)";
  }

  identity ICMP_HOST_UNREACH_TOS {
    base ICMP_DST_UNREACH_CODE;
    description
      "Destination HOST Unreachable for Type of Service (12)";
  }

  identity ICMP_COMM_PROHIBITED {
    base ICMP_DST_UNREACH_CODE;
    description
      "Communication Administratively Prohibited (13)";
  }

  identity ICMP_PRECEDENCE_VIOLATE {
    base ICMP_DST_UNREACH_CODE;
    description
      "Host Precedence Violation (14)";
  }

  identity ICMP_PRECEDENCE_CUTOFF {
    base ICMP_DST_UNREACH_CODE;
    description
      "Precedence Cutoff in Effect (15)";
  }


  identity ICMP_REDIRECT_CODE {
    description
      "Base identity for ICMP message code values for type Redirect
      used in ICMP packet header.";
    reference
      "RFC 792";
  }

  identity ICMP_REDIRECT_NETWORK {
    base ICMP_REDIRECT_CODE;
    description
      "Redirect Datagram for the Network (0)";
  }

  identity ICMP_REDIRECT_HOST {
    base ICMP_REDIRECT_CODE;
    description
      "Redirect Datagram for the Host (1)";
  }

  identity ICMP_REDIRECT_TOS_NETWORK {
    base ICMP_REDIRECT_CODE;
    description
      "Redirect Datagram for the Type of Service and Network (2)";
  }

  identity ICMP_REDIRECT_TOS_HOST {
    base ICMP_REDIRECT_CODE;
    description
      "Redirect Datagram for the Type of Service and Host (3)";
  }


  identity ICMP_ROUTER_ADVERT_CODE {
    description
      "Base identity for ICMP message code values for type Router
      Advertisement used in ICMP packet header.";
    reference
      "RFC 1256";
  }

  identity ICMP_NORMAL_ADVERT {
    base ICMP_ROUTER_ADVERT_CODE;
    description
      "Normal Router Advertisement (0)";
  }

  identity ICMP_NO_COMMON_TRAFFIC {
    base ICMP_ROUTER_ADVERT_CODE;
    description
      "Does not route common traffic (16)";
  }


  identity ICMP_TIME_EXCEEDED_CODE {
    description
      "Base identity for ICMP message code values for type Time
      Exceeded used in ICMP packet header.";
    reference
      "RFC 792";
  }

  identity ICMP_TTL_EXCEEDED {
    base ICMP_TIME_EXCEEDED_CODE;
    description
      "Time to Live Exceeded in Transit (0)";
  }

  identity ICMP_REASSEMBLY_TIME_EXCEEDED {
    base ICMP_TIME_EXCEEDED_CODE;
    description
      "Fragment Reassembly Time Exceeded (1)";
  }


  identity ICMP_PARAM_PROB_CODE {
    description
      "Base identity for ICMP message code values for type Parameter
      Problem used in ICMP packet header.";
    reference
      "RFC 792";
  }

  identity ICMP_POINTER_ERR {
    base ICMP_PARAM_PROB_CODE;
    description
      "Pointer Indicates the Error (0)";
  }

  identity ICMP_MISS_OPTION {
    base ICMP_PARAM_PROB_CODE;
    description
      "Missing a Required Option (1)";
  }

  identity ICMP_BAD_LENGTH {
    base ICMP_PARAM_PROB_CODE;
    description
      "Bad Length (2)";
  }


  typedef icmp-type {
    type union {
      type uint8 {
        range 0..255;
      }
      type identityref {
        base ICMP_TYPE;
      }
      type string {
        pattern '(2[0-5][0-5]|[0-1]?[0-9]?[0-9]?)\.\.(2[0-5][0-5]|[0-1]?' +
                '[0-9]?[0-9]?)';
      }
    }
    description
      "The ICMP message type value(s) may be represented as a single
      valid number (integer [0, 255]), using a type defined by the
      ICMP_TYPE identity.";
  }

  typedef icmp-dst-unreach-code {
    type union {
      type uint8 {
        range 0..15;
      }
      type identityref {
        base ICMP_DST_UNREACH_CODE;
      }
      type string {
        pattern '(1[0-5]|[0-9])\.\.(1[0-5]|[0-9])';
      }
    }
    description
      "The ICMP Destination Unreachable code value(s) may be represented
      as a single valid number (integer [0, 15]), using a type defined by
      the ICMP_DST_UNREACH_CODE identity, or using a string to indicate a
      range of code as <lower>..<higher>.";
  }

  typedef icmp-redirect-code {
    type union {
      type uint8 {
        range 0..3;
      }
      type identityref {
        base ICMP_REDIRECT_CODE;
      }
      type string {
        pattern '([0-3])\.\.([0-3])';
      }
    }
    description
      "The ICMP REDIRECT code value(s) may be represented as a
      single valid number (integer [0, 3]), using a type defined
      by the ICMP_REDIRECT_CODE identity, or using a string to
      indicate a range of codes as <lower>..<higher>.";
  }

  typedef icmp-router-advert-code {
    type union {
      type uint8 {
        range 0..16;
      }
      type identityref {
        base ICMP_ROUTER_ADVERT_CODE;
      }
      type string {
        pattern '(1[0-6]|[0-9])\.\.(1[0-6]|[0-9])';
      }
    }
    description
      "The ICMP Router Advertisement code value(s) may be represented
      as a single valid number (integer 0 or 16), using a type defined
      by the ICMP_ROUTER_ADVERT_CODE identity, or using a string to
      indicate a range of codes as <lower>..<higher>."; 
  }

  typedef icmp-time-exceeded-code {
    type union {
      type uint8 {
        range 0..1;
      }
      type identityref {
        base ICMP_TIME_EXCEEDED_CODE;
      }
      type string {
        pattern '(0|1)\.\.(0|1)';
      }
    }
    description
      "The ICMP Time Exceeded code value(s) may be represented as
      a single valid number (integer 0 or 1), using a type defined
      by the ICMP_TIME_EXCEEDED_CODE identity, or using a string to
      indicate a range of codes as <lower>..<higher>.";
  }

  typedef icmp-param-problem-code {
    type union {
      type uint8 {
        range 0..2;
      }
      type identityref {
        base ICMP_PARAM_PROB_CODE;
      }
      type string {
        pattern '([0-2])\.\.([0-2])';
      }
    }
    description
      "The ICMP Parameter Problem code value(s) may be represented
      as a single valid number (integer [0, 2]), using a type defined
      by the ICMP_PARAM_PROB_CODE identity, or using a string to
      indicate a range of codes as <lower>..<higher>."; 
  }
}
