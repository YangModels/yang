module arcos-openconfig-network-instance-augments {
  yang-version 1.1;
  namespace "http://yang.arrcus.com/arcos/openconfig/network-instance/augments";
  prefix arc-oc-netinst-aug;

  import openconfig-network-instance {
    prefix oc-netinst;
  }

  import openconfig-interfaces {
    prefix oc-if;
  }

  import arcos-openconfig-system-augments {
    prefix arc-oc-sys-aug;
  }

  import openconfig-system {
    prefix oc-sys;
  }

  import openconfig-aft {
    prefix oc-aft;
  }

  import openconfig-aft-types {
    prefix oc-aftt;
  }

  import arcos-aft-types {
    prefix arc-aft-types;
  }

  import ietf-inet-types {
    prefix inet;
  }

  import arcos-mpls-ldp {
    prefix arc-mpls-ldp;
  }
  
  import arcos-platform {
    prefix arc-platform;
  }

  import openconfig-network-instance-types {
    prefix oc-ni-types;
  }

  import arcos-openconfig-network-instance-types { 
    prefix "arc-oc-ni-types"; 
  }

  import openconfig-routing-policy {
    prefix "oc-rpol";
  }

  organization
    "Arrcus, Inc.";

  contact
    "Arrcus, Inc.
     2077 Gateway Place
     Suite 400
     San Jose, CA 95110

     E-mail: yang-support@arrcus.com";

  description
    "This module contains definitions for the
      ArcOS Network instance augments.

     Copyright (c) 2016-2022 by Arrcus, Inc.
     All rights reserved.";

  revision 2025-01-23 {
    description "Enable l2ni-fdb config for XGS";
  }

  revision 2024-11-08 {
    description " Add mac-learning configuration.";
  }

  revision 2024-11-07 {
    description "Modified the 'when' clause to enable CLI configuration on VM";
  }
  
  revision "2024-07-01" {
    description
       "Arrcus extension to table-connect CLI to support redistribution";
  }

  revision 2024-01-24 {
    description " Add duplicate mac action configuration.";
  }

  revision 2023-10-05 {
    description " Add l3vrf container.";
  }
  revision 2023-05-31 {
    description "Add platform constraint for mac-limit, pkt-action attributes.";
  }

  revision 2023-05-13 {
    description
      "Add LDP targeted hellos to neighbor config";
  }

  revision 2023-04-10 {
    description
      "Add LDP global enable config";
  }

  revision 2023-03-29 {
    description "Add l2ni config for mac-limit, pkt-action";
  }

  revision 2023-03-08 {
    description
      "Add LDP preference config";
  }

  grouping ip-tunnel-state {
    description
      "Operational state parameters for IP tunnels";
    list tunnels {
      key tunnel-id;
      description
        "List of IP tunnels";

      leaf tunnel-id {
        type uint32;
        description
          "Tunnel identifier";
      }

      container state {
        leaf tunnel-type {
          type oc-aftt:encapsulation-header-type;
          description
            "Type of IP tunnel";
        }

        leaf src-ip-address {
          type inet:ip-address;
          description
            "Source IP address of tunnel";
        }

        leaf dst-ip-address {
          type inet:ip-address;
          description
            "Destination IP address of tunnel";
        }

        leaf-list sid-list {
          type inet:ipv6-address-no-zone;
          description
            "The list of SIDs added to SRv6 tunnel header";
        }

        leaf-list hw-id-list {
          type uint32;
          description
            "The list of ASIC specific IDs";
        }

        leaf ing-ucast-packets {
          type uint64;
          description
            "Destination ingress packets of ucast";
        }

        leaf ing-mcast-packets {
          type uint64;
          description
            "Destination ingress packets of mcast";
        }

        leaf ing-bcast-packets {
          type uint64;
          description
            "Destination ingress packets of bcast";
        }

        leaf egr-ucast-packets {
          type uint64;
          description
            "Destination egress packets of ucast";
        }

        leaf egr-mcast-packets {
          type uint64;
          description
            "Destination egress packets of mcast";
        }

        leaf egr-bcast-packets {
          type uint64;
          description
            "Destination egress packets of bcast";
        }

        leaf ing-ucast-bytes {
          type uint64;
          description
            "Destination ingress bytes of ucast";
        }

        leaf ing-mcast-bytes {
          type uint64;
          description
            "Destination ingress bytes of mcast";
        }

        leaf ing-bcast-bytes {
          type uint64;
          description
            "Destination ingress bytes of bcast";
        }

        leaf egr-ucast-bytes {
          type uint64;
          description
            "Destination egress bytes of ucast";
        }

        leaf egr-mcast-bytes {
          type uint64;
          description
            "Destination egress bytes of mcast";
        }

        leaf egr-bcast-bytes {
          type uint64;
          description
            "Destination egress bytes of bcast";
        }
      }

      uses oc-aft:aft-common-nhop-structural;
    }
  }

  grouping ip-tunnel-state-units {
    description
      "Per forwarding unit view of ip tunnels";

    container ip-tunnels-units {
      config false;
      description
        "Per forwarding unit view of ip tunnels";

      list ip-tunnel-unit-entry {
        key "unit-id";
        description
          "List of forwarding units";

        leaf unit-id {
          type uint32;
          description
            "Uniquely identifies a forwarding unit";
        }

        uses ip-tunnel-state;
      }
    }
  }

  grouping l2ni-mac-table-state-top {
    description
      "Top-level grouping for MAC table state list";


    container mac-table-state {
      config false;

      description
        "Table of learned or statically configured MAC addresses and
        corresponding VLANs in the bridge domain";

      container entries {
        description
          "Enclosing container for list of MAC table entries";

        list entry {
          key "mac-address";
          description
            "List of learned MAC addresses";

          leaf mac-address {
            type leafref {
              path "../state/mac-address";
            }
            description
              "Reference to mac-address list key";
          }

          container state {


            description
              "Operational state data for MAC table entries";

            uses oc-netinst:l2ni-mac-table-config;
            uses oc-netinst:l2ni-mac-table-state;
            leaf nexthop-ecmp-id {
              type uint32;
              description 
                "Ecmp id of the nexthop";
            }
            leaf nexthop-tunnel-id {
              type leafref {
                path "/oc-netinst:network-instances/oc-netinst:network-instance/" +
                     "arc-oc-netinst-aug:ip-tunnels/arc-oc-netinst-aug:tunnels/" +
                     "arc-oc-netinst-aug:tunnel-id";
                }
              description
                "ID of tunnel that nexthop recurses over";
             }
          }
          container interface {
            description
              "Reference to the base and/or subinterface for the
              MAC table entry";

            uses oc-if:interface-ref;
          }
        }
      }
    }
  }

  grouping fdb-units-top {
    description
      "Top-level grouping for MAC table state list per unit";


    container fdb-units {
      config false;

      description
        "Table of learned or statically configured MAC addresses and
        corresponding VLANs in the bridge domain per asic unit";

      list fdb-unit-entry {
        key "unit-id";
        description
          "List of learned MAC addresses";

        leaf unit-id {
          type uint32;
          description
            "Device unit number";
        }
        uses l2ni-mac-table-state-top;
      }
    }
  }
  identity MAC_LIMIT_PACKET_ACTION_TYPE {
    description "Base identity for Mac limit packet action type.";
  }

  identity FLOOD_ACTION {
    base MAC_LIMIT_PACKET_ACTION_TYPE;
    description "Flood unknown Destination Mac packets.";
  }

  identity DROP_ACTION {
    base MAC_LIMIT_PACKET_ACTION_TYPE;
    description "Drop all packets.";
  }

  identity DUPLICATE_MAC_ACTION_TYPE {
    description "Base identity for the action to be taken when duplicate MAC state is detected";
  }

  identity LOG {
    base DUPLICATE_MAC_ACTION_TYPE;
    description "Generate a Log entry upon duplicate MAC detection.";
  }

  identity SHUTDOWN {
    base DUPLICATE_MAC_ACTION_TYPE;
    description "Shutdown the vlan interface and log upon duplicate MAC detection.";
  }

  grouping l2ni-fdb-mac-config {
    description
      "Parameters relating to FDB behaviour relating to MAC
      addresses";

    leaf maximum-entries {
      type uint16 {
        range 1..65535;
      }
      default 65535;
      description
        "The maximum number of MAC address entries that should be
        accepted into the FDB";
    }
    leaf packet-action {
      type identityref {
        base MAC_LIMIT_PACKET_ACTION_TYPE;
      }
      default FLOOD_ACTION;
      description
        "Packet action when number of learnt mac entries exceed the configured limit";
    }
    leaf mac-learning {
      type boolean;
      default true;
      description
        "When set to false, MAC learning is disabled for the network
        instance, such that MAC addresses are not learned from ingress
        frames";
    }
  }

  grouping l2ni-fdb-mac-top {
    container config {
      description
        "Configuration parameters relating to the FDB";
      uses l2ni-fdb-mac-config;
    }
  }

  augment "/oc-netinst:network-instances/oc-netinst:network-instance" {
    container ip-tunnels {
      config false;
      description
        "Operation state parameters for IP tunnels";
      uses ip-tunnel-state;
    }
  }

  augment "/oc-netinst:network-instances/oc-netinst:network-instance" {
    uses ip-tunnel-state-units;
  }

  augment "/oc-netinst:network-instances/oc-netinst:network-instance" +
           "/oc-netinst:config" {
    leaf resolve-dns-in-network-instance {
      type leafref {
        path "/oc-sys:system/oc-sys:dns/arc-oc-sys-aug:server-groups/arc-oc-sys-aug:server-group/arc-oc-sys-aug:name";
      }
      must "not(current() = ../oc-netinst:name)" {
        error-message "Cannot self reference and resolve in the same network instance.";
      }
      must "/oc-netinst:network-instances/oc-netinst:network-instance[oc-netinst:name=current()]/oc-netinst:config" {
        error-message "Cannot resolve DNS in a network instance which does not exist. 
                       Remove any server groups referring to nonexistent network-instances.";
      }
      description "Use the designated network instance server group for the current
                   network instance's DNS configuration";
    }

    leaf duplicate-mac-action {
      when "../oc-netinst:type = 'oc-ni-types:L2VLAN' or " +
           "../oc-netinst:type = 'arc-oc-ni-types:L2VLAN_AWARE_BUNDLE'" {
        description
          "Control duplicate mac detection based action for 
            Layer 2 network instance";
      }
      type identityref {
        base DUPLICATE_MAC_ACTION_TYPE;
      }
      default LOG;
      description
        "Indicates the action to be taken when duplicate MAC state is detected.";
    }
  }

  augment "/oc-netinst:network-instances/oc-netinst:network-instance" +
          "/arc-oc-netinst-aug:ip-tunnels/arc-oc-netinst-aug:tunnels" +
          "/arc-oc-netinst-aug:next-hops/arc-oc-netinst-aug:next-hop" +
          "/arc-oc-netinst-aug:state" {
    leaf nexthop-type {
      type arc-aft-types:dpal-nexthop-type;
      description
        "nexthop type";
    }
  }

  augment "/oc-netinst:network-instances/oc-netinst:network-instance" +
          "/arc-oc-netinst-aug:ip-tunnels-units" +
          "/arc-oc-netinst-aug:ip-tunnel-unit-entry/arc-oc-netinst-aug:tunnels" +
          "/arc-oc-netinst-aug:next-hops/arc-oc-netinst-aug:next-hop" +
          "/arc-oc-netinst-aug:state" {
    leaf nexthop-type {
      type arc-aft-types:dpal-nexthop-type;
      description
        "nexthop type";
    }
  }

  augment "/oc-netinst:network-instances/oc-netinst:network-instance/oc-netinst:fdb" {
    uses l2ni-fdb-mac-top {
          when "(derived-from-or-self(/arc-platform:platform/arc-platform:family, 'arc-platform:BROADCOM_DNX_JPLUS')) or "
            + "(derived-from-or-self(/arc-platform:platform/arc-platform:family, 'arc-platform:BROADCOM_DNX')) or "
            + "(derived-from-or-self(/arc-platform:platform/arc-platform:family, 'arc-platform:BROADCOM_XGS')) or "
            + "(/oc-sys:system/arc-oc-sys-aug:cli/arc-oc-sys-aug:config/arc-oc-sys-aug:unhide-unsupported-cli = 'true')";
    }
    uses l2ni-mac-table-state-top;
  }

  augment "/oc-netinst:network-instances/oc-netinst:network-instance" {
    uses fdb-units-top;
  }

  augment "/oc-netinst:network-instances/oc-netinst:network-instance" +
          "/oc-netinst:mpls/oc-netinst:signaling-protocols/oc-netinst:ldp" +
          "/oc-netinst:global" {
    uses arc-mpls-ldp:mpls-ldp-fec-filter;
    uses arc-mpls-ldp:mpls-ldp-transport-address-config;
    uses arc-mpls-ldp:mpls-ldp-max-local-binding-config;
    uses arc-mpls-ldp:mpls-ldp-preference-config;
    uses arc-mpls-ldp:mpls-ldp-global-enable-config;
    uses arc-mpls-ldp:mpls-ldp-session-protection-config;
  }

  augment "/oc-netinst:network-instances/oc-netinst:network-instance" +
          "/oc-netinst:mpls/oc-netinst:signaling-protocols/oc-netinst:ldp" +
          "/oc-netinst:neighbors/oc-netinst:neighbor" {
    uses arc-mpls-ldp:mpls-ldp-max-remote-binding-config;
    uses arc-mpls-ldp:mpls-ldp-neighbor-targeted-hello-config;
  }

  augment "/oc-netinst:network-instances/oc-netinst:network-instance" +
          "/oc-netinst:mpls/oc-netinst:signaling-protocols/oc-netinst:ldp" {
    uses arc-mpls-ldp:mpls-ldp-sessions;
    uses arc-mpls-ldp:mpls-ldp-label-mapping;
    uses arc-mpls-ldp:mpls-ldp-hello-adjacency;
  }

  augment "/oc-netinst:network-instances/oc-netinst:network-instance" +
          "/oc-netinst:mpls/oc-netinst:signaling-protocols/oc-netinst:ldp" +
          "/oc-netinst:targeted" {
    uses arc-mpls-ldp:mpls-ldp-strict-targeted-hellos-config;
  }

  grouping mpls-oam {
    description
      "Configuration relating to MPLS-OAM";

    leaf icmp-tunnelling {
      type boolean;
      default true;
      description
        "Enable/Disable ICMP Tunnelling.";
    }

    leaf mpls-oam {
      type boolean;
      default true;
      description
        "Enable/Disable MPLS-OAM LSP verification";
    }
  }
  augment "/oc-netinst:network-instances/oc-netinst:network-instance" +
          "/oc-netinst:mpls/oc-netinst:global/oc-netinst:config" {
    uses mpls-oam;
  }
  augment "/oc-netinst:network-instances/oc-netinst:network-instance" +
          "/oc-netinst:mpls/oc-netinst:global/oc-netinst:state" {
    uses mpls-oam;
  }

  grouping l3vrf_top {
    description
    "Linux name for network-instance";
    container l3vrf {
      container state {
        config false;
        leaf vrf-interface {
          type string;
          description
            "Interface name for network-instance";
        }
        leaf table-id {
          type uint32;
        }
      }
    }
  }
  augment "/oc-netinst:network-instances/oc-netinst:network-instance" {
    uses l3vrf_top {
      when "oc-netinst:config/oc-netinst:type = 'oc-ni-types:L3VRF' and " +
           "oc-netinst:config/oc-netinst:name != 'default'";
    }
  }

  grouping redis-config-top-policies-config {
    description
      "Import policy config for redistribution";

    uses oc-rpol:apply-policy-import-config;
  }

  grouping redis-config-top {
    description
      "Inter instance redistribution";
    container src-dst-instances {
      description
        "Instance of the src protocol to be redistributed";

      list src-dst-instance {
        key "src-instance dst-instance";

        leaf src-instance {
          type string;
          description
            "Instance of the src protocol to be redistributed";
          must "current()/../../../../.." +
               "/oc-netinst:protocols/oc-netinst:protocol" +
               "[oc-netinst:identifier=current()/../../../oc-netinst:src-protocol]" +
               "[oc-netinst:name=current()] or " +
               "current()='directly_connected' or " +
               "current()='adjacency' or " +
               "current()='sidmgr'" {
            error-message "Source protocol must be configured";
          }
        }

        leaf dst-instance {
          type string;
          description
            "Instance of the dst protocol";
          must "current()/../../../../.." +
               "/oc-netinst:protocols/oc-netinst:protocol" +
               "[oc-netinst:identifier=current()/../../../oc-netinst:dst-protocol]" +
               "[oc-netinst:name=current()]" {
            error-message "Destination protocol must be configured";
          }
        }

        container config {
          description
            "Configuration parameters relating to the connection
            between tables";
          uses oc-rpol:apply-policy-import-config;
        }
        container state {
          config false;
          description
            "State parameters relating to the connection between
            tables";
          uses oc-rpol:apply-policy-import-config;
        }
      }
    }
  }
  augment "/oc-netinst:network-instances/oc-netinst:network-instance" +
          "/oc-netinst:table-connections/oc-netinst:table-connection" {
    uses redis-config-top;
  }
}
