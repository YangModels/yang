module arcos-openconfig-if-ethernet-augments {
  yang-version 1.1;
  namespace "http://yang.arrcus.com/arcos/openconfig/if/ethernet/augments";
  prefix arc-oc-if-eth-aug;

  import openconfig-interfaces {
    prefix oc-if;
  }

  import openconfig-if-ethernet {
    prefix oc-eth;
  }

  import arcos-openconfig-interfaces-augments {
    prefix arc-oc-int;
  }

  organization "Arrcus, Inc.";

  contact
    "Arrcus, Inc.
     2077 Gateway Place
     Suite 400
     San Jose, CA 95110
     E-mail: yang-support@arrcus.com";

  description
    "This module defines augments statements for the
     for OpenConfig If Ethernet module.
     Copyright (c) 2024 by Arrcus, Inc.
     All rights reserved.";

  revision 2024-11-28 {
    description
        "Add support for displaying effective-fec per interface.";
  }

  grouping interface-ethernet-common {
    leaf-list advertise-fec {
      type arc-oc-int:fec-types;
      description
      "Forward error correction type to advertise use for this ethernet interface";
    }

    leaf-list advertise-speed {
      type identityref {
        base oc-eth:ETHERNET_SPEED;
      }
      description
      "Speeds advertise for this ethernet interface";
    }
  }

  grouping interface-ethernet-state {
    leaf effective-fec {
      type arc-oc-int:fec-types;
      config false;
      description
        "Effective Forward Error Correction type of the interface.";
    }
  }

  augment "/oc-if:interfaces/oc-if:interface/oc-eth:ethernet/oc-eth:state" {
    uses interface-ethernet-common;
    uses interface-ethernet-state;
  }

  augment "/oc-if:interfaces/oc-if:interface/oc-eth:ethernet/oc-eth:config" {
    uses interface-ethernet-common;
  }
}
