module arcos-hardware-platform-pfc {
  yang-version 1.1;
  namespace "http://yang.arrcus.com/arcos/hardware/platform/pfc";
  prefix arc-hw-platform-pfc;

  import ietf-yang-types {
    prefix yang;
  }

  import arcos-platform {
    prefix arc-platform;
  }

  import arcos-hardware-platform-pfc-stats {
    prefix arcos-pfc-stats;
  }

  organization
    "Arrcus, Inc.";

  contact
    "Arrcus, Inc.
     2077 Gateway Place
     Suite 400
     San Jose, CA 95110

     E-mail: yang-support@arrcus.com";

  description
    "This module contains the PFC profile configurations

     Copyright (c) 2016-2024 by Arrcus, Inc.
     All rights reserved.";

  revision "2025-03-14" {
    description
      "Change xon to xon-offset. Add cable-length.";
  }

  grouping lossless-config {
    container lossless {
      leaf enable {
        type boolean;
        default false;
        description "Enable lossless traffic class";
      }
      leaf xoff {
        type uint32;
        description "Xoff Threshold values";
      }
      leaf xon-offset {
        type uint32;
        description "Xon offset Threshold values";
      }
      leaf hdrm {
        type uint32;
        description "Headroom buffer values";
      }
    }
  }
  grouping watchdog-config {
    container watchdog {
      leaf enable {
        type boolean;
        default false;
        description "Enable watchdog configs";
      }
      leaf detection-time {
        type uint32;
        default 200;
        description "Time in ms";
      }
      leaf recovery-time {
        type uint32;
        default 200;
        description "Time in ms";
      }
    }
  }

  grouping tc-configs-top {
    uses lossless-config;
    uses watchdog-config;
  }

  grouping pfc-profile-configs {
    leaf name {
      type string {
        length "0..64";
      }
      description "Name of PFC profile";
    }

    container tx {
      leaf enable {
        type boolean;
        default false;
      }
    }

    container rx {
      leaf enable {
        type boolean;
        default false;
      }
    }

    leaf cable-length {
      type uint32;
      default 100;
      description "Cable length in meters";
    }

    container traffic-class-0 {
      uses tc-configs-top;
    }
    container traffic-class-1 {
      uses tc-configs-top;
    }
    container traffic-class-2 {
      uses tc-configs-top;
    }
    container traffic-class-3 {
      uses tc-configs-top;
    }
    container traffic-class-4 {
      uses tc-configs-top;
    }
    container traffic-class-5 {
      uses tc-configs-top;
    }
    container traffic-class-6 {
      uses tc-configs-top;
    }
    container traffic-class-7 {
      uses tc-configs-top;
    }
  }

  grouping pfc-profile-top {
    list profile {
      description "pfc profile configuration";
      key "name";

      leaf name {
        description "Name of PFC profile";
        type leafref {
          path ../config/name;
        }
      }
      container config {
        uses pfc-profile-configs;
      }
    }
  }

  grouping pfc-configs {
    container pfc {
      description "PFC specific configuration/state";
      container config {
        uses pfc-profile-top;
      }
      container state {
        config false;
        uses arcos-pfc-stats:pfc-stats-top;
      }
    }
  }
}
