module arcos-aft-types {
  yang-version 1.1;
  namespace "http://yang.arrcus.com/arcos/aft/types";
  prefix arc-aft-types;

  organization
    "Arrcus, Inc.";

  contact
     "Arrcus, Inc.
      2077 Gateway Place
      Suite 400
      San Jose, CA 95110
      E-mail: yang-support@arrcus.com";

  description
    "Types related to the ArcOS Abstract Forwarding
     Table (AFT) model

     Copyright (c) 2016-2024 by Arrcus, Inc. All rights reserved.";

  revision 2024-01-02 {
    description
      "Adding mandatory statements for
         - contact
         - organization
         - description
         - revision";
  }

  typedef dpal-nexthop-type {
    type enumeration {
      enum GLEAN {
        value 1;
      }
      enum DROP {
        value 2;
      }
      enum LOCAL {
        value 3;
      }
      enum CONNECTED {
        value 4;
      }
      enum MPLS_CONNECTED {
        value 5;
      }
      enum PUNT_TO_CPU {
        value 6;
      }
      enum VXLAN {
        value 7;
      }
      enum UNRESOLVED {
        value 8;
      }
    }
  }

}
