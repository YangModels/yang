module arcos-system-management {
  yang-version 1.1;
  namespace "http://yang.arrcus.com/arcos/system/management";
  prefix arc-sys-mgmt;

  import openconfig-system-logging {
    prefix oc-sys-log;
  }

  import arcos-system-types {
    prefix arc-sys-types;
  }

  import ietf-yang-types {
    prefix yang;
    reference
      "RFC 6991: Common YANG Data Types.";
  }

  organization
    "Arrcus, Inc.";

  contact
    "Arrcus, Inc.
     2077 Gateway Place
     Suite 400
     San Jose, CA 95110

     E-mail: yang-support@arrcus.com";

  description
    "This module contains definitions for the
     native ArcOS system management domain.

     Copyright (c) 2016-2025 by Arrcus, Inc.
     All rights reserved.";

  revision 2025-09-27 {
    description
      "Removed constraint check for protocols leaf list";
  }

  revision 2024-02-02 {
    description
      "Added grpc-server state sensor statistics";
  }
  
  revision 2024-01-29 {
    description
      "Added list paths with leaf path and subscription-mode under system-clients-state";
  }

  revision 2023-03-19 {
    description
      "Separate out tls-config into individual nodes under config and state. Cannot be shared due to 'must' statements";
  }

  revision 2022-09-30 {
    description
      "Added leaf-list protocols under tls";
  }

  revision 2019-10-15 {
    description "Initial version";
  }

  grouping system-tls-top {
    description
      "Top-level grouping for system TLS attributes";

    container tls {
      description
        "Top-level container for TLS attributes";

      container config {
        description
          "Configuration data for TLS related attributes";

        leaf certificate-file {
          type string {
            length "1..100";
          }
          default "/mnt/onl/config/pki/certificate";
          must 'boolean(../key-file)' {
            error-message
              "If certificate-file is configured, key-file must be configured";
          }
          description
            "Absolute file path of the server certificate";
        }

        leaf key-file {
          type string {
            length "1..100";
          }
          default "/mnt/onl/config/pki/key.pem";
          must 'boolean(../certificate-file)' {
            error-message
              "If key-file is configured, certificate-file must be configured";
          }
          description
            "Absolute file path to the corresponding private key file for the
             server certificate";
        }

        leaf-list protocols {
          type arc-sys-types:tls-versions;
          ordered-by user;
          default "DEFAULT";
          description
            "An ordered list of TLS protocol versions that the agent supports";
        }
      }

      container state {
        config false;

        description
          "Operational state data for TLS related attributes";

        leaf certificate-file {
          type string {
            length "1..100";
          }
          default "/mnt/onl/config/pki/certificate";
          description
            "Absolute file path of the server certificate";
        }

        leaf key-file {
          type string {
            length "1..100";
          }
          default "/mnt/onl/config/pki/key.pem";
          description
            "Absolute file path to the corresponding private key file for the
             server certificate";
        }

        leaf-list protocols {
          type arc-sys-types:tls-versions;
          default "DEFAULT";
          description
            "An ordered list of TLS protocol versions that the agent supports";
        }
      }
    }
  }

  grouping system-grpc-server-state-statistics {
    description
      "Statistics for different sensors";

    list statistics{
      key sensor;
      leaf sensor {
        type string;
        description "Table name";
      }

      leaf notifications-generated {
        type yang:zero-based-counter64;
        description "Total number of notifications generated by this sensor";
      }

    }
  }

  grouping system-clients-state {
    description
      "Operational state data of connected clients";

    list paths {
      key path;
      leaf path {
        type string;
        description
          "Subscribed Paths";
      }

      leaf subscription-mode {
        type enumeration {
          enum TARGET_DEFINED {
            value 0;
            description "TARGET_DEFINED subscription mode";
          }
          enum ON_CHANGE {
            value 1;
            description "ON_CHANGE subscription mode";
          }
          enum SAMPLE {
            value 2;
            description "SAMPLE subscription mode";
          }
        }
        description "Subscription mode types";
      }
    }
  }

  grouping system-clients-top {
    description
      "Top-level grouping for system client data";

    container clients {
      description
        "Top level container for connected clients";
      container state {
        config false;
        description
          "Operational state data for the clients";
        list client {
          leaf peer-address {
            type string;
            description
              "IP address and port of the connected client";
          }
          uses system-clients-state;
        }
      }
    }
  }

  grouping logType {
    description
      "Common log configuration parameters. These parameters
       take effect for both existing and new sessions.";
    container syslog {
      leaf enabled {
        type boolean;
        default "false";
        description
          "enabled is either 'true' or 'false'. If 'true', syslog
           messages are sent.";
      }
      leaf facility {
        type identityref {
          base oc-sys-log:SYSLOG_FACILITY;
        }
        must "derived-from-or-self(current(), 'oc-sys-log:SYSTEM_DEAMON') or " +
             "derived-from-or-self(current(), 'oc-sys-log:AUTHPRIV') or " +
             "derived-from-or-self(current(), 'oc-sys-log:LOCAL0') or " +
             "derived-from-or-self(current(), 'oc-sys-log:LOCAL1') or " +
             "derived-from-or-self(current(), 'oc-sys-log:LOCAL2') or " +
             "derived-from-or-self(current(), 'oc-sys-log:LOCAL3') or " +
             "derived-from-or-self(current(), 'oc-sys-log:LOCAL4') or " +
             "derived-from-or-self(current(), 'oc-sys-log:LOCAL5') or " +
             "derived-from-or-self(current(), 'oc-sys-log:LOCAL6') or " +
             "derived-from-or-self(current(), 'oc-sys-log:LOCAL7')" {
          error-message "audit log facility is either SYSTEM_DAEMON,
                         AUTHPRIV, LOCAL0, LOCAL1, LOCAL2, LOCAL3, LOCAL4,
                         LOCAL5, LOCAL6, LOCAL7";
        }
        description
          "facility is either 'daemon', 'authpriv',
           'local0', ..., 'local7'";
      }
    }
  }

  grouping audit-log-top {
    container auditLog {
      description
        "auditLog is an audit log recording successful and failed
         logins to the ConfD backplane and also user operations
         performed from the CLI or northbound interfaces. This log
         is enabled by default. This configuration parameter takes
         effect for both existing and new sessions.";
      uses logType;
    }
  }
}
