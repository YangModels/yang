module arcos-ietf-ipsec-ike-augments {
  yang-version 1.1;
  namespace "http://yang.arrcus.com/arcos/ipsec/augments";
  prefix "arc-ipsec-aug";

  import ietf-inet-types {
    prefix inet;
  }

  import ietf-ipsec-ike {
    prefix ietf-ipsec;
  }

  import tailf-common {
    prefix tailf;
  }

  grouping ipsec-ike-connection {
    leaf unique-id {
      type uint64;
      description "IKE session ID";
    }

    leaf ike-state {
      type string;
      description "IKE state";
    }

    leaf ike-version {
      type uint64;
      description "IKE Version";
    }

    leaf local-host {
      type string;
      description "IP address of the local tunnel endpoint";
    }

    leaf local-id {
      type string;
      description "ID of the local tunnel endpoint";
    }

    leaf remote-host {
      type string;
      description "IP address of the remote tunnel endpoint";
    }

    leaf remote-id {
      type string;
      description "ID of the remote tunnel endpoint";
    }

    leaf encryption-algo {
      type string;
      description "Encryption algorithm used for the IKE tunnel";
    }

    leaf encryption-keysize {
      type uint64;
      description "Key size used for encryption";
    }

    leaf integrity-algo {
      type string;
      description "Integrity algorithm used for the IKE tunnel";
    }

    leaf integrity-keysize {
      type uint64;
      description "Key size used for encryption";
    }

    leaf prf-algo {
      type string;
      description "PRF algorithm used for the IKE tunnel";
    }

    leaf dh-group {
      type string;
      description "DH Group used for the IKE tunnel";
    }
  }

  grouping ipsec-ike-child-sas {
    list child-sa {
      key "name";
      tailf:callpoint child-sa-entries;

      leaf name {
        type string;
        description "Name of the policy";
      }

      leaf reqid {
        type string;
        description "Req id of the policy";
      }

      leaf state {
        type string;
        description "State of the policy";
      }

      leaf mode {
        type string;
        description "Mode used for the policy";
      }

      leaf protocol {
        type string;
        description "Protocol used for the policy";
      }

      leaf spi-in {
        type string;
      }

      leaf spi-out {
        type string;
      }

      leaf encryption-algo {
        type string;
        description "Encryption algorithm used for the policy";
      }

      leaf encryption-keysize {
        type string;
        description "Encryption algorithm keysize used for the policy";
      }

      leaf integrity-algo {
        type string;
        description "Integrity algorithm used for the policy";
      }

      leaf install-time {
        type string;
        description "Time since the policy was installed";
      }

      leaf-list local-ts {
        type string;
        min-elements 1;
        max-elements 10;
        description "Local subnet protected";
      }

      leaf-list remote-ts {
        type string;
        min-elements 1;
        max-elements 10;
        description "Remote subnet protected";
      }

      leaf bytes-in {
        type uint64;
        description "Number of ingress bytes to the tunnel";
      }

      leaf bytes-out {
        type uint64;
        description "Number of egress bytes from the tunnel";
      }

      leaf packets-in {
        type uint64;
        description "Number of ingress packets to the tunnel";
      }

      leaf packets-out {
        type uint64;
        description "Number of egress packets out of the tunnel";
      }
    }
  }

  augment "/ietf-ipsec:ipsec-ike/ietf-ipsec:conn-entry/ietf-ipsec:spd/" +
          "ietf-ipsec:spd-entry/ietf-ipsec:ipsec-policy-config/" +
          "ietf-ipsec:processing-info/ietf-ipsec:ipsec-sa-cfg" {
    leaf force-encapsulation {
      type boolean;
      default false;
      description
        "Force encapsulation of ESP into UDP datagrams.
         Useful in case if between local and remote side is firewall or NAT,
         which not allows passing plain ESP packets between them";
    }
  }

  augment "/ietf-ipsec:ipsec-ike/ietf-ipsec:conn-entry" {
    leaf enable {
      type boolean;
      default true;
      description
        "Enable or disable the VPN connection";
    }
  }

  augment "/ietf-ipsec:ipsec-ike/ietf-ipsec:conn-entry" +
            "/ietf-ipsec:spd/ietf-ipsec:spd-entry" +
            "/ietf-ipsec:ipsec-policy-config/ietf-ipsec:traffic-selector" {
    leaf-list local-subnets {
      type inet:ip-prefix;
      max-elements 10;
      description
        "Local IP address subnets.";
    }
  }

  augment "/ietf-ipsec:ipsec-ike/ietf-ipsec:conn-entry" +
            "/ietf-ipsec:spd/ietf-ipsec:spd-entry" +
            "/ietf-ipsec:ipsec-policy-config/ietf-ipsec:traffic-selector" {
    leaf-list remote-subnets {
      type inet:ip-prefix;
      max-elements 10;
      description
        "Remote IP address subnets.";
    }
  }

  augment "/ietf-ipsec:ipsec-ike/ietf-ipsec:conn-entry/ietf-ipsec:state" {
    uses ipsec-ike-connection;
    uses ipsec-ike-child-sas;
  }
}
