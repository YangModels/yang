module arcos-openconfig-keychain-augments {
  yang-version 1.1;
  namespace "http://yang.arrcus.com/arcos/openconfig/keychain/augments";
  prefix arc-oc-kc-aug;

  import openconfig-keychain {
    prefix oc-kc;
  }

  import openconfig-keychain-types {
    prefix oc-kc-types;
  }

  organization
    "Arrcus, Inc.";

  contact
    "Arrcus, Inc.
     2077 Gateway Place
     Suite 400
     San Jose, CA 95110
     E-mail: yang-support@arrcus.com";

  description
    "This module defines augmentation for Arrcus
     implemention of the openconfig keychain module.
     Copyright (c) 2022-2023 by Arrcus, Inc.
     All rights reserved.";

  revision 2022-12-15 {
    description
      "Initial Revision";
  }

  identity HMAC_SHA_224 {
    base oc-kc-types:CRYPTO_TYPE;
      description
        "HMAC-SHA-224 keyed hash algorithm constructed from SHA-224 hash
        function and used as a HMAC.";
  }

  identity HMAC_SHA_384 {
    base oc-kc-types:CRYPTO_TYPE;
      description
        "HMAC-SHA-384 keyed hash algorithm constructed from SHA-384 hash
        function and used as a HMAC.";
  }

  identity HMAC_SHA_512 {
    base oc-kc-types:CRYPTO_TYPE;
      description
        "HMAC-SHA-512 keyed hash algorithm constructed from SHA-512 hash
        function and used as a HMAC.";
  }

  grouping key-lifetime-always {
    leaf always {
      type boolean;
      description
        "Indicates key lifetime is always valid.";
    }
  }

  augment "/oc-kc:keychains/oc-kc:keychain" +
          "/oc-kc:keys/oc-kc:key" +
          "/oc-kc:send-lifetime/oc-kc:config" {
    uses key-lifetime-always;
  }

  augment "/oc-kc:keychains/oc-kc:keychain" +
          "/oc-kc:keys/oc-kc:key" +
          "/oc-kc:send-lifetime/oc-kc:state" {
    uses key-lifetime-always;
  }

  grouping key-active-status {
    leaf send-active {
      type boolean;
      description
        "Indicates this key is active for sending
         authentication information.";
    }

    leaf receive-active {
      type boolean;
      description
        "Indicates this key is active for validating received
         authentication information.";
    }
  }

  augment "/oc-kc:keychains/oc-kc:keychain" +
          "/oc-kc:keys/oc-kc:key" +
          "/oc-kc:state" {
    uses key-active-status;
  }
}
