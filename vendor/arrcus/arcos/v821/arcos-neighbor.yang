module arcos-neighbor {
  yang-version 1.1;
  namespace "http://yang.arrcus.com/arcos/neighbor";
  prefix arc-nbr;

  import arcos-neighbor-types {
    prefix arc-nbr-types;
  }

  import openconfig-yang-types {
    prefix oc-yang;
  }

  import ietf-yang-types {
    prefix yang;
  }

  import ietf-inet-types {
    prefix inet;
  }

  organization
    "Arrcus, Inc.";

  contact
    "Arrcus, Inc.
     2077 Gateway Place
     Suite 400
     San Jose, CA 95110

     E-mail: yang-support@arrcus.com";

  description
    "This module contains definitions for the
     native ArcOS neighbor domain.

     Copyright (c) 2016-2024 by Arrcus, Inc.
     All rights reserved.";

  revision 2024-12-11 {
    description
      "Add additional status flags for ARP entry";
  }

  revision 2024-06-14 {
    description
      "Add status flags for ARP entry";
  }

  revision 2023-12-03 {
    description
      "Add model for tech-support debug state";
  }
 
  revision 2019-10-29 {
    description "Initial version";
  }

  identity NEIGHBOR_STATE_TYPE {
    description
      "Base identity for defining reachability state of ARP entry";
  }

  identity PERMANENT {
    base NEIGHBOR_STATE_TYPE;
    description "Permanent ARP entry";
  }

  identity REACHABLE {
    base NEIGHBOR_STATE_TYPE;
    description "Reachable ARP entry";
  }

  identity PROBE {
    base NEIGHBOR_STATE_TYPE;
    description "Probe ARP entry";
  }

  identity STALE {
    base NEIGHBOR_STATE_TYPE;
    description "Stale ARP entry";
  }

  identity FAILED {
    base NEIGHBOR_STATE_TYPE;
    description "Failed ARP entry";
  }

  container arp-entries {
    description
      "Address Resolution Protocol (ARP) table entries";

    config false;

    list arp-entry {
      key "ip ifname";

      description
        "IP Address and Interface of entry";

      leaf ip {
        type inet:ipv4-address-no-zone;
        description
          "Layer 3 IPv4 Address";
      }

      leaf ifname {
        type string;
        description
          "Interface over which ARP learned";
      }

      leaf hwaddr {
        mandatory true;
        type oc-yang:mac-address;
        description
          "Layer 2 address";
      }

      leaf last-updated {
        type yang:date-and-time;
        description
          "Last update time";
      }

      leaf age {
        type string;
        description
        "Time Elapsed since last change";
      }

      leaf state {
        type identityref {
          base NEIGHBOR_STATE_TYPE;
        }
        description "ARP reachability state";
      }
    }
  }

  container arp-clear {
    description
      "Clear ARP entries";

    action all {
      description
        "Clear all ARP entries";

      output {
        leaf result {
          type string;
          description
            "The status of the operation";
        }
      }
    }

    action arp {
      description
        "Clear specific ARP entries";

      input {
        leaf ip {
          mandatory true;
          type inet:ipv4-address-no-zone;
          description
            "The IPv4 address to be cleared";
        }
      }
      output {
        leaf result {
          type string;
          description
            "The status of the operation";
        }
      }
    }

    action interface {
      description
        "Clear interface specific ARP entries";

      input {
        leaf name {
          mandatory true;
          type string;
          description
            "Interface to be cleared";
        }
      }
      output {
        leaf result {
          type string;
          description
            "The status of the operation";
        }
      }
    }

  }

  container ndp-entries {
    description
      "IPv6 Neighbor Discovery Protocol (NDP) table entries";

    config false;

    list ndp-entry {
      key "ip ifname";

      description
        "IP Address and Interface of entry";

      leaf ip {
        type inet:ipv6-address-no-zone;
        description
          "Layer 3 IPv6 Address";
      }

      leaf ifname {
        type string;
        description
          "Interface over which NDP learned";
      }

      leaf hwaddr {
        mandatory true;
        type oc-yang:mac-address;
        description
          "Layer 2 address";
      }

      leaf last-updated {
        type yang:date-and-time;
        description
          "Last update time";
      }

      leaf age {
        type string;
        description
        "Time Elapsed since last change";
      }

      leaf state {
        type identityref {
          base NEIGHBOR_STATE_TYPE;
        }
        description "ARP reachability state";
      }
    }
  }

  container ndp-clear {
    description
      "Clear NDP entries";

    action all {
      description
        "Clear NDP entries for all interfaces";

      input {
        leaf global-only {
          default true;
          type boolean;
          description
            "If only the ipv6 global addresses need to be cleared. 
            Both global and link-local address entries are cleared when set to false.";
        }
      }

      output {
        leaf result {
          type string;
          description
            "The status of the operation";
        }
      }
    }

    action ndp {
      description
        "Clear specific NDP entries";

      input {
        leaf ipv6 {
          mandatory true;
          type inet:ipv6-address-no-zone;
          description
            "The IPv6 address to be cleared";
        }
      }
      output {
        leaf result {
          type string;
          description
            "The status of the operation";
        }
      }
    }
    action interface {
      description
        "Clear interface specific NDP entries";

      input {
        leaf global-only {
          default true;
          type boolean;
          description
            "If only the ipv6 global addresses need to be cleared. 
            Both global and link-local address entries are cleared when set to false.";
        }
        leaf name {
          mandatory true;
          type string;
          description
            "Interface to be cleared";
        }
      }
      output {
        leaf result {
          type string;
          description
            "The status of the operation";
        }
      }
    }
  }

  container adj-debug {
    description
      "Adjacency manager debug control";

    action ipv4 {
      input {
        leaf debug {
          mandatory true;
          type arc-nbr-types:adj-debug-type;
          description
            "Debug to be controlled";
        }

        leaf op {
          mandatory true;
          type arc-nbr-types:adj-debug-state;
          description
            "Turn on/off operation";
        }
      }
      output {
        leaf result {
          type string;
          description
            "The status of the operation";
        }
      }
    }

    action ipv6 {
      input {
        leaf debug {
          mandatory true;
          type arc-nbr-types:adj-debug-type;
          description
            "Debug to be controlled";
        }

        leaf op {
          mandatory true;
          type arc-nbr-types:adj-debug-state;
          description
            "Turn on/off operation";
        }
      }
      output {
        leaf result {
          type string;
          description
            "The status of the operation";
        }
      }
    }
  }

  grouping adj-debugs-state {
    description
      "adj debugs information";

    leaf debug-flag {
      type arc-nbr-types:adj-debug-type;
      description
        "adj debug flags";
    }
    leaf enabled {
      type boolean;
      description
        "Indicates whether the debug flag is enabled or not";
    }
  }

  grouping adj-show-debug-top {
    container adj-debug {
      description
        "adj show debugs information";

      list adj-ipv4-debug {
        key "debug-flag";

        description
          "adj ipv4 debugs information";

        leaf debug-flag {
          type leafref {
            path "../state/debug-flag";
          }
          description
            "adj Debug flags";
        }

        container state {
          uses adj-debugs-state;
        }
      }

      list adj-ipv6-debug {
        key "debug-flag";

        description
          "adj ipv4 debugs information";

        leaf debug-flag {
          type leafref {
            path "../state/debug-flag";
          }
          description
            "adj Debug flags";
        }

        container state {
          uses adj-debugs-state;
        }
      }
    }
  }

}
