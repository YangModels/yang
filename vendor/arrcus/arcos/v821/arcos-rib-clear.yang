module arcos-rib-clear {
  yang-version 1.1;
  namespace "http://yang.arrcus.com/arcos/rib/clear";
  prefix arc-rib-clr;

  import ietf-inet-types { prefix inet; }
  import arcos-common-types {
    prefix arc-common-types;
  }

  organization
    "Arrcus, Inc.";

  contact
    "Arrcus, Inc.
     2077 Gateway Place
     Suite 400
     San Jose, CA 95110

     E-mail: yang-support@arrcus.com";

  description
    "This module contains clear command definitions
      pertaining to RIB.

     Copyright (c) 2016-2024 by Arrcus, Inc.
     All rights reserved.";

  revision 2024-05-20 {
    description
      "Add clear command for label stats";
  }
  revision 2019-10-29 {
    description "Initial version";
  }

  container rib-clear {
    action v4-route {
      input {
        leaf prefix {
        type inet:ipv4-prefix;
        mandatory true;
          description
          "The IPv4 prefix to be deleted from RIB";
        }
      }
      output {
        leaf result {
        type string;
          description
          "The status of operation"; 
        }
      }
    }
    action v6-route {
      input {
        leaf prefix {
        type inet:ipv6-prefix;
        mandatory true;
          description
          "The IP64 prefix to be deleted from RIB";
        }
      }
      output {
        leaf result {
        type string;
          description
          "The status of operation"; 
        }
      }
    }
  }

  container label-stats-clear {
    description
      "Clear Label statistics";

    action all {
      description
        "Clear all label statistics";

      output {
        leaf result_code {
          type arc-common-types:generic-status-code;
          description
            "Result of the operation";
        }
        leaf result {
          type string;
          description
            "The status of the operation";
        }
      }
    }
    action label {
      description
        "Clear statistics for specific label";

      input {
        leaf value {
          mandatory true;
          type uint32;
          description
            "The label for which statistics need to be cleared";
        }
      }
      output {
        leaf result_code {
          type arc-common-types:generic-status-code;
          description
            "Result of the operation";
        }
        leaf result {
          type string;
          description
            "The status of the operation";
        }
      }
    }
  }
}
