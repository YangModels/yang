submodule arcos-hardware-common {
  yang-version 1.1;

  belongs-to arcos-hardware {
    prefix arc-hw;
  }

  include arcos-hardware-ecmp;
  include arcos-hardware-scale;

  grouping hardware-common {
    description
      "Common hardware configuration";

    container ecmp {
      uses hardware-ecmp;
      description "ECMP configuration";
    }

    container scale {
      uses hardware-scale;
      description "HW scale profile";
    }
  }
}
