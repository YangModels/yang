module arcos-puntpath {
  yang-version 1.1;
  namespace "http://yang.arrcus.com/arcos/puntpath";
  prefix arc-puntpath;

  import arcos-runtime {
    prefix arc-runtime;
  }
  import ietf-inet-types {
    prefix inet;
  }

  grouping puntpath-tunnel-state {
    container tunnels {
      list tunnel {
        key "id";
        description
          "The list of punt path tunnels.";

        leaf id {
          type leafref {
            path "../state/id";
          }
          description
            "Tunnel Id for the puntpath tunnel.";
        }
        container state {
          description
            "Puntpath tunnel state.";
          leaf id {
            type uint32;
            description
              "Puntpath tunnel id.";
          }
          leaf remote-node-name {
            type string;
            description
              "Puntpath tunnel remote node name.";
          }
          leaf local-endpoint-address {
            type inet:ipv4-address-no-zone;
            description
              "Puntpath tunnel local endpoint address.";
          }
          leaf remote-endpoint-address {
            type inet:ipv4-address-no-zone;
            description
              "Puntpath tunnel remote endpoint address.";
          }
          leaf oper-state {
            type enumeration {
              enum UP {
                description
                  "Tunnel endpoints are reachable.";
              }
              enum DOWN {
                description
                  "Tunnel endpoints are not reachable.";
              }
            }
            description
              "This leaf contains the reachability state of the tunnel";
          }
        }
      }
    }
  }

  grouping puntpath-top {
    container puntpath {
      description
        "Arrcus Punt Path internals";

      container state {
        leaf active {
          type boolean;
          description
            "Puntpath tunnel state.";
        }
        uses puntpath-tunnel-state;
      }
    }
  }

  augment "/arc-runtime:runtime-instances" +
          "/arc-runtime:runtime-instance" {
    uses puntpath-top;
  }
}
