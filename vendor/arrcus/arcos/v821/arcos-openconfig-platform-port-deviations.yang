module arcos-openconfig-platform-port-deviations {
  yang-version 1.1;
  namespace "http://yang.arrcus.com/arcos/openconfig/platform/port/deviations";
  prefix arc-oc-platform-port-dev;

  import openconfig-platform {
    prefix oc-platform;
  }

  import openconfig-platform-port {
    prefix oc-platform-port;
  }

  organization
    "Arrcus, Inc.";

  contact
    "Email: eng@arrcus.com";

  description
    "This module defines deviation statements for Arrcus
     implemention of the openconfig platform module.";

  revision 2018-08-14 {
    description "ArcOS release 2.2.1";
  }

  revision 2017-07-10 {
    description
      "Initial Revision
       * xxx not supported.
      ";

    reference
      "RFC 6020: YANG - A Data Modeling Language for the
       Network Configuration Protocol (NETCONF)";
  }

  deviation "/oc-platform:components/oc-platform:component/oc-platform:port/oc-platform-port:breakout-mode" {
    deviate not-supported;
    description "Not supported in this release";
  }
}
