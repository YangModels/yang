module arcos-hardware-platform-pfc-interface {
  yang-version 1.1;
  namespace "http://yang.arrcus.com/arcos/hardware/platform/pfc/interface";
  prefix arc-hw-platform-pfc-intf;

  import ietf-yang-types {
    prefix yang;
  }

  import arcos-hardware {
    prefix arc-hw;
  }

  import arcos-platform {
    prefix arc-platform;
  }

	organization
    "Arrcus, Inc.";

  contact
    "Arrcus, Inc.
     2077 Gateway Place
     Suite 400
     San Jose, CA 95110

     E-mail: yang-support@arrcus.com";

  description
    "This module contains the interface level PFC configurations
     Copyright (c) 2016-2024 by Arrcus, Inc.
     All rights reserved.";

  grouping pfc-intf-profile {
    container pfc {
      container config {
        leaf profile {
          type leafref {
            path "/arc-hw:hardware/arc-hw:config/arc-hw:platform" +
                 "/arc-hw:pfc/arc-hw:config" +
                 "/arc-hw:profile/arc-hw:name";
          }
        }
      }
      container state {
        config false;
      }
    }
  }
}
