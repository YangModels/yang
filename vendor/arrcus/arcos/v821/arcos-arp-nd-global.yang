module arcos-arp-nd-global {
  yang-version 1.1;
  namespace "http://yang.arrcus.com/arcos/ip-neighbor";
  prefix arc-ip-nbr;

  grouping system-cache-limit-config {
    leaf arp-cache-limit {
      type uint32 {
        range "1..100000";
      }
      description "System cache limit for ARP neighbor entries";
   }

   leaf ndp-cache-limit {
      type uint32 {
       range "1..100000";
      }
      description "System cache limit for NDP neighbor entries";
   }
 }

 grouping system-cache-limit-top {
   container system {
     description
       "Global ARP and NDP cache limit";

     container config {
       uses system-cache-limit-config;
     }

     container state {
       config false;
       uses system-cache-limit-config;
       leaf arp-cache-count {
         description "ARP system cache count.";
         type uint32;
       }
       leaf ndp-cache-count {
          description "NDP system cache count.";
          type uint32;
       }
     }
   }
 }

  container ip-neighbor {
    description
      "Global ARP and ND neighbor configuration";

    leaf persistence {
      type uint8 {
        range "5..255";
      }
      description "neighbor persistence sampling time in sec";
    }
    uses system-cache-limit-top;
  }
}
