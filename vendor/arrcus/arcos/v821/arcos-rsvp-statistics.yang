submodule arcos-rsvp-statistics {

  yang-version "1.1";

  belongs-to arcos-rsvp {
    prefix "arc-rsvp";
  }

  import ietf-yang-types { prefix "yang"; }
  import openconfig-types { prefix "oc-types"; }
  import arcos-rsvp-types { prefix "arc-rsvp-types"; }
  import arcos-system-types { prefix arc-sys-types; }

  description
    "This submodule provides RSVP statistics.";


  /*
   * RSVP Packet Statistics
   */

  grouping rsvp-pkt-receive-statistics {
    description
      "This grouping defines RSVP packet receive statistics.";
  }

  grouping rsvp-pkt-send-statistics {
    description
      "This grouping defines RSVP packet send statistics.";
  }

  grouping rsvp-pkt-common-statistics {
    description
      "This grouping defines RSVP packet statistics.";

    leaf total-packets {
      type yang:counter64;
      description
        "RSVP total packet count.";
    }

    leaf total-errors {
      type yang:counter64;
      description
        "RSVP total packets that encountered errors.";
    }

    leaf total-messages {
      type yang:counter64;
      description
        "RSVP total message count.";
    }

    leaf bundle-messages {
      type yang:counter64;
      description
        "RSVP Bundle message count.";
    }

    leaf hellos {
      type yang:counter64;
      description
        "RSVP Hello message count.";
    }

    leaf hellos-with-capability {
      type yang:counter64;
      description
        "This value specifies the total number of
         Hello messages with Capability object sent
         on this interface.";
    }

    leaf hellos-with-restart-capability {
      type yang:counter64;
      description
        "This value specifies the total number of
         Hello messages with Restart_Cap object sent on
         this interface.";
    }

    leaf paths {
      type yang:counter64;
      description
        "RSVP Path message count.";
    }

    leaf path-errs {
      type yang:counter64;
      description
        "RSVP Path error message count.";
    }

    leaf path-tears {
      type yang:counter64;
      description
        "RSVP Path tear message count.";
    }

    leaf recovery-paths {
      type yang:counter64;
      description
        "This value specifies the total number of
         RecoveryPath messages sent on this interface.";
    }

    leaf paths-with-recovery-label {
      type yang:counter64;
      description
        "This value specifies the total number of
         Path messages with Recovery label object sent
         on this interface.";
    }

    leaf paths-with-suggested-label {
      type yang:counter64;
      description
        "This value specifies the total number of
         Path messages with Suggested label object sent
         on this interface.";
    }

    leaf resvs {
      type yang:counter64;
      description
        "RSVP Resv message count.";
    }

    leaf resv-confirms {
      type yang:counter64;
      description
        "RSVP Confirm message count.";
    }

    leaf resv-errs {
      type yang:counter64;
      description
        "RSVP Resv error message count.";
    }

    leaf resv-tears {
      type yang:counter64;
      description
        "RSVP Resv tear message count.";
    }

    leaf resv-confs {
      type yang:counter64;
      description
        "This value specifies the total number of
         Resv Conf messages sent on this interface.";
    }

    leaf notifys {
      type yang:counter64;
      description
        "RSVP Notify message count.";
    }

    leaf srefreshs {
      type yang:counter64;
      description
        "RSVP Srefresh message count.";
    }
  }

  grouping rsvp-pkt-statistics-structure {
    description
      "This grouping defines RSVP packet statistics.";

    container packet {
      config false;
      description
        "Packet statistics.";

      container send {
        description
          "Packet send statistics.";

        uses rsvp-pkt-common-statistics;
        uses rsvp-pkt-send-statistics;
      }

      container receive {
        description
          "Packet receive statistics.";

        uses rsvp-pkt-common-statistics;
        uses rsvp-pkt-receive-statistics;
      }
    }
  }

  /*
   * RSVP Interface General Statistics
   */
  grouping rsvp-interface-statistics {
    description
      "This grouping defines RSVP interface statistics.";

    leaf l3-link-notifications {
      type yang:counter32;
      description
        "Number of L3 link updates";
    }

    leaf l3-address-notifications {
      type yang:counter32;
      description
        "Number of L3 IP address updates";
    }

    leaf te-igp-update-notifications {
      type yang:counter32;
      description
        "Number of TE Interface Update notifications sent to IGP";
    }

    leaf te-igp-delete-notifications {
      type yang:counter32;
      description
        "Number of TE Interface Delete notifications sent to IGP";
    }
  }

  /*
   * RSVP Interface Statistics
   */
  grouping rsvp-interface-statistics-structure {
    description
      "This grouping defines RSVP interface statistics.";

    container statistics {
      config false;
      description
        "Interface statistics.";

      uses rsvp-interface-statistics;
      uses rsvp-pkt-statistics-structure;
    }
  }

  /*
   * RSVP IGP Statistics
   */
  grouping rsvp-igp-statistics {
    description
      "This grouping defines RSVP IGP statistics";

    leaf isis-adj-update-notifications {
      type yang:counter32;
      description
        "Number of Adjacency Update notification received from ISIS";
    }

    leaf isis-adj-delete-notifications {
      type yang:counter32;
      description
        "Number of Adjacency Delete notification received from ISIS";
    }
  }

  /*
   * RSVP Global General Statistics
   */
  grouping rsvp-global-statistics {
    description
      "This grouping defines RSVP global statistics.";

  }

  /*
   * RSVP Global Statistics
   */
  grouping rsvp-global-statistics-structure {
    description
      "This grouping defines RSVP global statistics.";

    container statistics {
      config false;
      description
        "Global statistics.";

      uses rsvp-global-statistics;
    }
  }
}
