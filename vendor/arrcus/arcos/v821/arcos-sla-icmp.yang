module arcos-sla-icmp {
  yang-version "1.1";
  namespace "http://yang.arrcus.com/arcos/sla-icmp";
  prefix "arc-sla-icmp";

  import ietf-yang-types { prefix "ietf-types"; }
  import ietf-inet-types { prefix "inet"; }
  import openconfig-network-instance { prefix "oc-netinst"; }
  import arcos-common-types { prefix arc-common-types; }

  organization
    "Arrcus, Inc";

  contact
    "Arrcus, Inc.
     2077 Gateway Place
     Suite 400
     San Jose, CA 95110
     Email: yang-support@arrcus.com";

  description
    "This YANG module is for model for the
      SLA monitoring with ICMP.

      Copyright (c) 2022-2023 by Arrcus, Inc.
      All rights reserved.";

  revision 2024-04-18 {
    description
      "DSCP values in session.";
  }

  revision 2023-03-01 {
    description
      "Initial revision.";
  }

  grouping sla-icmp-dscp-config {
    leaf dscp {
      type inet:dscp;
      description
        "The value of Differentiated Services Code Point (DSCP)
        for SLA ICMP packets";
      reference
        "RFC 2474 Definition of the Differentiated Services Field
        (DS Field) in the IPv4 and IPv6 Headers";
    }
  }

  grouping sla-icmp-probe-common {
    description
      "SLA ICMP per probe config.";

    leaf probe-interval {
      type uint64;
      units microseconds;
      mandatory true;
      description
        "Time interval between probe";
    }

    leaf probe-count {
      type uint32;
      mandatory true;
      description
        "Number of probes to be sent";
    }

    leaf payload-size {
      type uint32;
      description
        "Payload size of each probe";
    }
  }

  grouping sla-icmp-threshold-common {
    description
      "SLA ICMP per probe config.";

    leaf successive-loss {
      type uint32;
      description
        "Number of successive pkt loss";
    }

    leaf current-successive-loss {
      type uint32;
      config false;
      description
        "Current Number of successive pkt loss";
    }

    leaf trap-successive-loss {
      type boolean;
      default false;
      description
        "Generate trap on successive loss exceeding threshold";
    }

    leaf excessive-rtd {
      type uint64;
      units nanoseconds;
      description
        "Round Trip Delay threshold";
    }

    leaf trap-excessive-rtd {
      type boolean;
      default false;
      description
        "Generate trap on exceeding RTD threshold";
    }
  }

  grouping sla-icmp-session-common {
    description
      "List of SLA-ICMP sessions.";

    leaf name {
      type string;
      description
        "Unique SLA-ICMP session name";
    }

    leaf admin-state {
      type boolean;
      default true;
      description
        "Indicates the Session-Sender test session state.";
    }

    leaf target-address {
      type inet:ip-address;
      mandatory true;
      description
        "The IP address on the remote device";
    }

    leaf source-address {
      type inet:ip-address;
      description
        "The IP address on the source";
    }

    leaf session-interval {
      type uint32;
      units seconds;
      mandatory true;
      description
        "Time interval between sessions";
    }

    container probe {
      description
        "SLA-ICMP per session probe config";
      uses sla-icmp-probe-common;
    }

    container threshold {
      description
        "SLA-ICMP per session threshold config";
      uses sla-icmp-threshold-common;
    }

    uses sla-icmp-dscp-config;
  }

  grouping sla-icmp-stats {
    leaf sent-packets {
      type ietf-types:zero-based-counter64;
      config false;
      description
        "Indicates the number of packets sent.";
    }

    leaf rx-packets {
      type ietf-types:zero-based-counter64;
      config false;
      description
        "Indicates the number of packets received.";
    }

    leaf min-rtd {
      type ietf-types:zero-based-counter64;
      config false;
      description
        "Indicates the minimum RTD(round trip delay)(nano seconds).";
    }

    leaf max-rtd {
      type ietf-types:zero-based-counter64;
      config false;
      description
        "Indicates the maximum RTD(round trip delay)(nano seconds).";
    }

    leaf ave-rtd {
      type ietf-types:zero-based-counter64;
      config false;
      description
        "Indicates the average RTD(round trip delay)(nano seconds) of all recved pkt.";
    }

    leaf std-rtd {
      type ietf-types:zero-based-counter64;
      config false;
      description
        "Indicates the standard deviation RTD(round trip delay)(nano seconds).";
    }

    leaf current-successive-loss {
      type ietf-types:gauge32;
      config false;
      description
        "Current Number of successive pkt loss";
    }

    leaf last-excessive-rtd {
      type ietf-types:gauge64;
      units nanoseconds;
      config false;
      description
        "last excessive Round Trip Delay";
    }

    leaf jitter-rtd {
      type ietf-types:zero-based-counter64;
      config false;
      description
        "Indicates the jitter RTD(round trip delay)(nano seconds). Max_rtd - Min_rtd ";
    }

    leaf is-trap-excessive-rtd {
      type string;
      config false;
      description
        "Indicates trap for excessive rtd raised";
    }

    leaf is-trap-successive-loss {
      type string;
      config false;
      description
        "Indicates trap for successive loss";
    }

    description
      "Used for SLA-ICMP statistics.";
  }

  grouping sla-icmp-base {
    description
      "Configuration of the sla-icmp session";

    leaf admin-state {
      type boolean;
      default true;
      description
        "Indicates administrative state IP SLA-ICMP";
    }

    container icmp-sessions {
      list icmp-session {
        key name;
        description
          "List of SLA ICMP sessions.";

        leaf name {
          type leafref {
            path "../config/name";
          }
          description
            "A unique name for this SLA-ICMP session to be used
              for identifying this ICMP session by the logical
              name.";
        }

        container config {
          description
            "SLA-ICMP per session config";
          uses sla-icmp-session-common;
        }

        container state {
          config false;
          description
            "SLA-ICMP per session statistics";
          uses sla-icmp-session-common;
          uses sla-icmp-stats;
        }
      }
    }
  }

  grouping sla {
    container sla {
      description
        "Service Level Agreement[SLA]";

      container icmp {
        description
          "SLA Service Level Agreement with ICMP";
        uses sla-icmp-base;
      }
    }
  }

  augment "/oc-netinst:network-instances/oc-netinst:network-instance" {
    description
      "SLA monitoring using ICMP";
    uses sla;
  }

  grouping clear-sla-input {
    leaf network-instance {
      mandatory true;
      description
        "Network-instances  name";
      type leafref {
        path "/oc-netinst:network-instances/oc-netinst:network-instance/oc-netinst:name";
      }
    }

    leaf session {
      mandatory true;
      description
        "ALL network-instances or the name or one network-instance";

      type union {
        type enumeration {
          enum ALL {
            description
              "All SLA ICMP sessions";
          }
        }
        type leafref {
          path "/oc-netinst:network-instances/oc-netinst:network-instance/sla/icmp/icmp-sessions/icmp-session/name";
        }
      }
    }

    leaf counter {
      description
        "clear SLA ICMP session counter";
      type boolean;
    }

    leaf trap{
      description
        "clear SLA ICMP session trap";
      type boolean;
    }
  }

  rpc clear-sla-ses-cnt {
    description
      "clear SLA ICMP session counter";
    input {
      uses clear-sla-input;
    }
    output {
      uses arc-common-types:generic-rpc-response;
    }
  }
}
