module arcos-ietf-nat-deviations {
  yang-version 1.1;
  namespace "http://yang.arrcus.com/arcos/ietf/nat/deviations";
  prefix arc-ietf-nat-dev;

  import ietf-nat{
    prefix nat;
  }

  import openconfig-interfaces {
    prefix oc-if;
  }

  import arcos-ietf-nat-augments {
    prefix arc-nat-aug;
  }

  organization
    "Arrcus, Inc.";

  contact
    "Arrcus, Inc.
     2077 Gateway Place
     Suite 400
     San Jose, CA 95110

     E-mail: yang-support@arrcus.com";

  description
    "This module defines ArcOS deviations to the
     IETF NAT  module.

     Copyright (c) 2016-2021  by Arrcus, Inc.
     All rights reserved.";

  revision 2021-09-24 {
    description "Initial revision";
  }

  deviation "/nat:nat-pool-event" {
    deviate not-supported;
    description "Not supported in this release.";
  }
  deviation "/nat:nat-instance-event" {
    deviate not-supported;
    description "Not supported in this release.";
  }
  deviation "/nat:nat/nat:instances/nat:instance/nat:capabilities" {
    deviate not-supported;
    description "Not supported in this release.";
  }
  deviation "/nat:nat/nat:instances/nat:instance/nat:per-interface-binding" {
    deviate not-supported;
    description "Not supported in this release.";
  }
  deviation "/nat:nat/nat:instances/nat:instance/nat:nat-pass-through" {
    deviate not-supported;
    description "Not supported in this release.";
  }
  deviation "/nat:nat/nat:instances/nat:instance/nat:mapping-limits" {
    deviate not-supported;
    description "Not supported in this release.";
  }
  deviation "/nat:nat/nat:instances/nat:instance/nat:connection-limits" {
    deviate not-supported;
    description "Not supported in this release.";
  }
  deviation "/nat:nat/nat:instances/nat:instance/nat:notification-limits" {
    deviate not-supported;
    description "Not supported in this release.";
  }
  deviation "/nat:nat/nat:instances/nat:instance/nat:mapping-table/nat:mapping-entry/nat:type" {
    deviate not-supported;
    description "Not supported in this release.";
  }
  deviation "/nat:nat/nat:instances/nat:instance/nat:mapping-table/nat:mapping-entry/nat:lifetime" {
    deviate not-supported;
    description "Not supported in this release.";
  }
  deviation "/nat:nat/nat:instances/nat:instance/nat:mapping-table/nat:mapping-entry/nat:transport-protocol" {
    deviate not-supported;
    description "Not supported in this release.";
  }
  deviation "/nat:nat/nat:instances/nat:instance/nat:mapping-table/nat:mapping-entry/nat:internal-src-port" {
    deviate not-supported;
    description "Not supported in this release.";
  }
  deviation "/nat:nat/nat:instances/nat:instance/nat:mapping-table/nat:mapping-entry/nat:external-src-address" {
    deviate not-supported;
    description "Not supported in this release.";
  }
  deviation "/nat:nat/nat:instances/nat:instance/nat:mapping-table/nat:mapping-entry/nat:external-src-port" {
    deviate not-supported;
    description "Not supported in this release.";
  }
  deviation "/nat:nat/nat:instances/nat:instance/nat:mapping-table/nat:mapping-entry/nat:internal-dst-address" {
    deviate not-supported;
    description "Not supported in this release.";
  }
  deviation "/nat:nat/nat:instances/nat:instance/nat:mapping-table/nat:mapping-entry/nat:internal-dst-port" {
    deviate not-supported;
    description "Not supported in this release.";
  }
  deviation "/nat:nat/nat:instances/nat:instance/nat:mapping-table/nat:mapping-entry/nat:external-dst-address" {
    deviate not-supported;
    description "Not supported in this release.";
  }
  deviation "/nat:nat/nat:instances/nat:instance/nat:mapping-table/nat:mapping-entry/nat:external-dst-port" {
    deviate not-supported;
    description "Not supported in this release.";
  }

  deviation "/nat:nat/nat:instances/nat:instance/nat:statistics/nat:discontinuity-time" {
    deviate not-supported;
    description "Not supported in this release.";
  }
  deviation "/nat:nat/nat:instances/nat:instance/nat:statistics/nat:traffic-statistics/nat:sent-packets" {
    deviate not-supported;
    description "Not supported in this release.";
  }
  deviation "/nat:nat/nat:instances/nat:instance/nat:statistics/nat:traffic-statistics/nat:sent-bytes" {
    deviate not-supported;
    description "Not supported in this release.";
  }
  deviation "/nat:nat/nat:instances/nat:instance/nat:statistics/nat:traffic-statistics/nat:rcvd-packets" {
    deviate not-supported;
    description "Not supported in this release.";
  }
  deviation "/nat:nat/nat:instances/nat:instance/nat:statistics/nat:traffic-statistics/nat:rcvd-bytes" {
    deviate not-supported;
    description "Not supported in this release.";
  }
  deviation "/nat:nat/nat:instances/nat:instance/nat:statistics/nat:traffic-statistics/nat:dropped-packets" {
    deviate not-supported;
    description "Not supported in this release.";
  }
  deviation "/nat:nat/nat:instances/nat:instance/nat:statistics/nat:traffic-statistics/nat:dropped-bytes" {
    deviate not-supported;
    description "Not supported in this release.";
  }
  deviation "/nat:nat/nat:instances/nat:instance/nat:statistics/nat:traffic-statistics/nat:dropped-fragments" {
    deviate not-supported;
    description "Not supported in this release.";
  }
  deviation "/nat:nat/nat:instances/nat:instance/nat:statistics/nat:traffic-statistics/nat:dropped-address-limit-packets" {
    deviate not-supported;
    description "Not supported in this release.";
  }
  deviation "/nat:nat/nat:instances/nat:instance/nat:statistics/nat:traffic-statistics/nat:dropped-address-limit-bytes" {
    deviate not-supported;
    description "Not supported in this release.";
  }
  deviation "/nat:nat/nat:instances/nat:instance/nat:statistics/nat:traffic-statistics/nat:dropped-address-packets" {
    deviate not-supported;
    description "Not supported in this release.";
  }
  deviation "/nat:nat/nat:instances/nat:instance/nat:statistics/nat:traffic-statistics/nat:dropped-address-bytes" {
    deviate not-supported;
    description "Not supported in this release.";
  }
  deviation "/nat:nat/nat:instances/nat:instance/nat:statistics/nat:traffic-statistics/nat:dropped-port-limit-packets" {
    deviate not-supported;
    description "Not supported in this release.";
  }
  deviation "/nat:nat/nat:instances/nat:instance/nat:statistics/nat:traffic-statistics/nat:dropped-port-limit-bytes" {
    deviate not-supported;
    description "Not supported in this release.";
  }
  deviation "/nat:nat/nat:instances/nat:instance/nat:statistics/nat:traffic-statistics/nat:dropped-port-packets" {
    deviate not-supported;
    description "Not supported in this release.";
  }
  deviation "/nat:nat/nat:instances/nat:instance/nat:statistics/nat:traffic-statistics/nat:dropped-port-bytes" {
    deviate not-supported;
    description "Not supported in this release.";
  }
  deviation "/nat:nat/nat:instances/nat:instance/nat:statistics/nat:traffic-statistics/nat:dropped-subscriber-limit-packets" {
    deviate not-supported;
    description "Not supported in this release.";
  }
  deviation "/nat:nat/nat:instances/nat:instance/nat:statistics/nat:traffic-statistics/nat:dropped-subscriber-limit-bytes" {
    deviate not-supported;
    description "Not supported in this release.";
  }
  deviation "/nat:nat/nat:instances/nat:instance/nat:statistics/nat:mappings-statistics" {
     deviate not-supported;
     description "Not supported in this release.";
  }
  deviation "/nat:nat/nat:instances/nat:instance/nat:statistics/nat:pools-stats" {
     deviate not-supported;
     description "Not supported in this release.";
  }
  deviation "/nat:nat/nat:instances/nat:instance" {
    deviate add {
      max-elements 32;
    }
    description "maximum allowed instances 32";
  }
  deviation "/nat:nat/nat:instances/nat:instance/nat:mapping-table/nat:mapping-entry" {
    deviate add {
      min-elements 1;
      max-elements 32;
    }
    description "must have at least mapping rule";
  }
  deviation "/nat:nat/nat:instances/nat:instance/nat:policy" {
    deviate add {
      min-elements 1;
      max-elements 1;
    }
    description "must have one and only policy per instance";
  }
  deviation "/nat:nat/nat:instances/nat:instance/nat:enable" {
    deviate add {
       default "true";
    }
    description "default enable true";
  }
  deviation "/nat:nat/nat:instances/nat:instance/nat:type" {
    deviate add {
       default "basic-nat44";
    }
    description "default source nat";
  }
  deviation "/nat:nat/nat:instances/nat:instance" {
    deviate add {
       must "string-length(name) > 0" {
         error-message "NAT Instance must have a name";
       }
    }
    description "please specify a name for NAT instance";
  }
  deviation "/nat:nat/nat:instances/nat:instance/nat:policy/nat:clat-parameters" {
    deviate not-supported;
    description "Not supported in this release.";
  }
  deviation "/nat:nat/nat:instances/nat:instance/nat:policy/nat:nptv6-prefixes" {
    deviate not-supported;
    description "Not supported in this release.";
  }
  deviation "/nat:nat/nat:instances/nat:instance/nat:policy/nat:eam" {
    deviate not-supported;
    description "Not supported in this release.";
  }
  deviation "/nat:nat/nat:instances/nat:instance/nat:policy/nat:nat64-prefixes" {
    deviate not-supported;
    description "Not supported in this release.";
  }
  deviation "/nat:nat/nat:instances/nat:instance/nat:policy/nat:external-ip-address-pool" {
    deviate not-supported;
    description "Not supported in this release.";
  }
  deviation "/nat:nat/nat:instances/nat:instance/nat:policy/nat:port-set-restrict" {
    deviate not-supported;
    description "Not supported in this release.";
  }
  deviation "/nat:nat/nat:instances/nat:instance/nat:policy/nat:dst-nat-enable" {
    deviate not-supported;
    description "Not supported in this release.";
  }
  deviation "/nat:nat/nat:instances/nat:instance/nat:policy/nat:dst-ip-address-pool" {
    deviate not-supported;
    description "Not supported in this release.";
  }
  deviation "/nat:nat/nat:instances/nat:instance/nat:policy/nat:transport-protocols" {
    deviate not-supported;
    description "Not supported in this release.";
  }
  deviation "/nat:nat/nat:instances/nat:instance/nat:policy/nat:subscriber-mask-v6" {
    deviate not-supported;
    description "Not supported in this release.";
  }
  deviation "/nat:nat/nat:instances/nat:instance/nat:policy/nat:subscriber-match" {
    deviate not-supported;
    description "Not supported in this release.";
  }
  deviation "/nat:nat/nat:instances/nat:instance/nat:policy/nat:address-allocation-type" {
    deviate not-supported;
    description "Not supported in this release.";
  }
  deviation "/nat:nat/nat:instances/nat:instance/nat:policy/nat:port-allocation-type" {
    deviate not-supported;
    description "Not supported in this release.";
  }
  deviation "/nat:nat/nat:instances/nat:instance/nat:policy/nat:external-realm/nat:realm-type/nat:interface/nat:external-interface" {
    deviate replace {
       type oc-if:base-interface-ref;
    }
  }
  deviation "/nat:nat/nat:instances/nat:instance/nat:policy/nat:mapping-type" {
    deviate not-supported;
    description "Not supported in this release.";
  }
  deviation "/nat:nat/nat:instances/nat:instance/nat:policy/nat:filtering-type" {
    deviate not-supported;
    description "Not supported in this release.";
  }
  deviation "/nat:nat/nat:instances/nat:instance/nat:policy/nat:fragment-behavior" {
    deviate not-supported;
    description "Not supported in this release.";
  }
  deviation "/nat:nat/nat:instances/nat:instance/nat:policy/nat:port-quota" {
    deviate not-supported;
    description "Not supported in this release.";
  }
  deviation "/nat:nat/nat:instances/nat:instance/nat:policy/nat:port-set" {
    deviate not-supported;
    description "Not supported in this release.";
  }
  deviation "/nat:nat/nat:instances/nat:instance/nat:policy/nat:timers" {
    deviate not-supported;
    description "Not supported in this release.";
  }
  deviation "/nat:nat/nat:instances/nat:instance/nat:policy/nat:fragments-limit" {
    deviate not-supported;
    description "Not supported in this release.";
  }
  deviation "/nat:nat/nat:instances/nat:instance/nat:policy/nat:algs" {
    deviate not-supported;
    description "Not supported in this release.";
  }
  deviation "/nat:nat/nat:instances/nat:instance/nat:policy/nat:all-algs-enable" {
    deviate not-supported;
    description "Not supported in this release.";
  }
  deviation "/nat:nat/nat:instances/nat:instance/nat:policy/nat:notify-pool-usage" {
    deviate not-supported;
    description "Not supported in this release.";
  }
}
