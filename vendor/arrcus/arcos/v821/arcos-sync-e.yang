module arcos-sync-e {
  yang-version 1.1;
  namespace "http://yang.arrcus.com/arcos/sync-e/";
  prefix arc-sync-e;

  import tailf-common {
    prefix tailf;
  }

  import openconfig-interfaces {
    prefix oc-if;
  }

  import ietf-yang-types {
    prefix yang;
  }

  import arcos-features {
    prefix arc-features;
  }

  import ietf-interfaces {
    prefix if;
    reference
      "RFC 8343: A YANG Data Model for Interface Management";
  }
  import arcos-openconfig-system-augments {
    prefix arc-oc-sys-aug;
  }

  import openconfig-system {
    prefix oc-sys;
  }

  organization
    "Arrcus, Inc";

  contact
    "Arrcus, Inc.
     2077 Gateway Place
     Suite 400
     San Jose, CA 95110
     E-mail: yang-support@arrcus.com";

  description
    "This module lists arrcus sync-e related information.
     Copyright (c) 2023 by Arrcus, Inc.
     All rights reserved.";
  
  revision 2023-11-03 {
    description
      "Set the default value as option-1 for synchronization-network-option";
  }

  revision 2023-07-24 {
    description
      "Add GM sync-e interface configuration";
  }

  revision 2023-03-24 {
    description
      "Add sync-e configuration";
  }

  grouping sync-e-state {
    leaf sync-e-clock-state {
      config false;
      type enumeration {
        enum free-run {
          value 0;
          description "Clock is in free-run state";
        }
        enum holdover {
          value 1;
          tailf:code-name "synce-holdover";
          description "Clock is in holdover state";
        }
        enum locked {
          value 2;
          description "Clock is in locked state";
        }
      }
      description
        "SyncE clock state";
    }
    leaf synce-state-duration {
      config false;
      type string;
      description 
        "Duration of current SyncE Clock state.";
    }
    leaf dpll-clock-state {
      config false;
      type enumeration {
        enum free-run {
          value 0;
          description "DPLL Clock is in free-run state";
        }
        enum holdover {
          value 1;
          tailf:code-name "dpll-holdover";
          description "DPLL Clock is in holdover state";
        }
        enum fastlock {
          value 2;
          description "DPLL Clock is in fastlock state";
        }
        enum acquiring {
          value 3;
          description "DPLL Clock is in aquiring state";
        }
        enum locked {
          value 4;
          tailf:code-name "dpll-locked";
          description "DPLL Clock is in locked state";
        }
      }
      description
        "DPLL (Digital Phase Locked Loop) clock state.";
    }
  }

  grouping sync-e-stats-top {
    list interface-stats {
      config false;
      key "interface";
      leaf interface {
        type oc-if:base-interface-ref;
        description
          "Reference to the configured sync-e interface.";
      }
      leaf status {
        type enumeration {
          enum IDLE {
            value 0;
            description
              "Interface is configured as sync-e output source only.";
          }
          enum FAILED {
            value 1;
            description
              "Interface is not configured for sync-e";
          }
          enum OK {
            value 2;
            description
              "Interface is configured as sync-e input source.";
          }
        }
        description
          "Status of ESMC Interface";
      }
      leaf esmc-sent {
        type yang:zero-based-counter32;
        description
          "ESMC packets sent on interface.";

      }
      leaf esmc-received {
        type yang:zero-based-counter32;
        description
          "ESMC packets received on interface.";
      }
      action counters {
          output {
          leaf result {
            type string;
            description
              "Result of operation.";
          }
        }
      }
    }
  }

  typedef link-state-enumeration {
      type enumeration {
          enum down {
              value 0;
              description
                  "Link State is down";
          }
          enum up {
              value 1;
              description
                  "Link State is up";
          }
      }
  }
  grouping input-source-common {
      description
          "SyncE input source information";
          leaf esmc-status {
              type enumeration{
                  enum idle {
                      value 0;
                  }
                  enum failed {
                      value 1;
                  }
                  enum ok {
                      value 2;
                  }
                  enum N/A {
                      value 3;
                  }
              }
              description
                  "ESMC(Ethernet Synchronization messaging Channel) Interface status";
          }
          leaf is-selected-source {
              type boolean;
              description
                  "ESMC(Ethernet Synchronization messaging Channel) Interface is selected as input source or not";
          }
          leaf ql-configured {
              type string;
              description
                  "QL configured on the SyncE Interface.";
          }
          leaf ql-operational {
              type string;
              description
                  "Operation QL on the SyncE Interface.";
          }
          leaf ql-received {
              type string;
              description
                  "Quality-level received on interface.";
          }
          leaf link-state {
              type link-state-enumeration;
              description
                  "Link state of the SyncE Interface";
          }
          leaf signal-fail {
              type boolean;
              description
                  "Signal Fail status of the SyncE interface";
          }
  }

  grouping synce-source {
      description
          "SyncE input and output source information";
      list output-source {
          config false;
          key "interface";
          description
              "List of all output-source interface";
          leaf interface {
              type if:interface-ref;
              description 
                  "Output-source interface name.";
          }
          leaf link-state {
              type link-state-enumeration;
              description
                  "Link state of the SyncE Interface";
          }
          leaf ql-configured {
              type string;
              description
                  "QL configured on the SyncE Interface.";
          }
          leaf ql-operational {
              type string;
              description
                  "Operation QL on the SyncE Interface.";
          }
      }
      list input-source {
          config false;
          key "interface";
          description
              "List of all input-source interface";
          leaf interface {
              type if:interface-ref;
              description 
                  "Input-source interface name.";
          }
          uses input-source-common;
      }
      list gm-input-source {
          config false;
          key "interface-name";
          description
              "List of all input-source gm interface";
          leaf interface-name {
              type enumeration {
                  enum gps {
                      value 1;
                  }
                  enum ptp {
                      value 2;
                  }
                  enum 10mhz-in{
                      value 3;
                  }
                  enum bits-e1 {
                      value 4;
                  }
                  enum bits-t1 {
                      value 5;
                  }
              }
              description
                  "SyncE interface name";
          }
          uses input-source-common;
      }
  }


  container sync-e {
    leaf enabled {
      type boolean;
      default false;
      description 
        "Enable / Disable SyncE.";
    }
    leaf holdover {
      type uint32 {
        range 0..1440;
      }
      default 10;
      units "minutes";
      description
        "Set synchronous holdover time in minutes.";
    }
    leaf quality-level-enabled {
      type boolean;
      default true;
      description 
        "Enable / Disable quality level parameters.";
    }
    leaf revertive-enabled {
      type boolean;
      default true;
      description 
        "Configure revertive mode.";
    }
    leaf synchronization-network-option {
      type enumeration {
        enum option-1 {
          value 1;
        }
        enum option-2 {
          value 2;
        }
      }
      default option-1;
      description
        "The Network synchronization networking options.
        Values for this enumeration are specified
        in G.781.";
      reference
        "ITU-T G.781-2017: 5.3.1";
    }
    leaf interface-name {
        config false;
        type if:interface-ref;
        description
            "SyncE interface which got selected as source,
            if not then interface which was configured as input sources will be displayed.";
    }
    leaf esmc-status {
        config false;
        type string;
        description
          "ESMC(Ethernet Synchronization messaging Channel) Interface status";
    }
    leaf is-selected-source {
        config false;
        type boolean;
        default true;
        description
          "ESMC(Ethernet Synchronization messaging Channel) Interface is selected as input source or not";
    }
    leaf ql-operational {
        config false;
        type string;
        description
            "Operational Quality-level on interface.";
    }
    uses sync-e-state;
    uses sync-e-stats-top;
    uses synce-source;
    uses synce-interface-list;
  }

  grouping synce-interface-list {
      list interface {
          key "interface-name";
          description
              "List of SyncE interface ";
          leaf interface-name {
              type enumeration {
                  enum gps {
                      value 1;
                  }
                  enum ptp {
                      value 2;
                  }
                  enum 10mhz-in{
                      value 3;
                  }
                  enum bits-e1 {
                      value 4;
                  }
                  enum bits-t1 {
                      value 5;
                  }
              }
              description
                  "SyncE interface name";
          }
          uses synce-interface-common;
      }
  }

  grouping synce-interface-common {
      leaf enabled {
        type boolean;
        default false;
        description
          "Enable / Disable synchronous mode on interface.";
      }
      leaf input-source-priority {
        type int32 {
          range -1..max;
        }
        default -1;
        description 
          "Configure input sources.
           Highest priority is 1, lowest is 255, and 0 will
           exclude the interface from the clock selection.
           Use -1 to disable the input source on the specific interface.";
      }
      leaf mode-lockout {
        type boolean;
        default false;
        description 
          "Enable / Disable the external command lockout.";
      }
      leaf holdoff {
        type uint16 {
          range 300..1800;
        }
        default 300;
        units "milliseconds";
        description 
          "Enter hold-off timer value in milliseconds";
      }
      leaf mode-synchronous {
        type boolean;
        default false;
        description 
          "Enable / Disable Synchronous Mode.";
      }
      leaf wait-to-restore {
        type uint8 {
          range 0..12;
        }
        default 5;
        units "minutes";
        description 
          "Configure wait to restore timer in minutes";
      }
      leaf quality-level {
        type enumeration {
          enum QL_PRC {
            value 2;
          }
          enum QL_SSU_A {
            value 4;
          }
          enum QL_SSU_B {
            value 8;
          }
          enum QL_SEC {
            value 11;
          }
          enum QL_DNU {
            value 15;
          }
        }
        description
          "Configure clock source QL (quality level) as defined in ITU-T G.781.";
        reference
          "ITU-T standard G.781 section 5.4";
      }
  }

  grouping ptp-interface-sync-e-top {
    container sync-e {
      leaf clock-source-id {
        type uint8 {
          range 1..max;
        }
        description 
          "Specify Clock-Source ID";
      }
      leaf set-output-source {
        type boolean;
        default false;
        description 
          "Set ethernet interface as a timing output source.";
      }
      uses synce-interface-common;
    }
  }

  augment "/oc-if:interfaces/oc-if:interface" {
    uses ptp-interface-sync-e-top {
      when "(/arc-features:features/arc-features:feature[arc-features:name=" +
           "'arc-features:ARCOS_PTP_BOUNDARY_CLOCK']/arc-features:supported = 'true') or " +
           "(/oc-sys:system/arc-oc-sys-aug:cli/arc-oc-sys-aug:config/arc-oc-sys-aug:unhide-unsupported-cli = 'true')";
    }
  }
}
