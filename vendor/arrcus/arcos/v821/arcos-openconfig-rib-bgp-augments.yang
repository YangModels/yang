module arcos-openconfig-rib-bgp-augments {
  yang-version 1.1;
  namespace "http://yang.arrcus.com/arcos/openconfig/rib/bgp/augments";
  prefix arc-oc-rib-bgp-aug;

  import openconfig-types {
    prefix oc-types;
  }

  import openconfig-bgp-types {
    prefix oc-bgp-types;
  }

  import ietf-inet-types {
    prefix inet;
  }

  import openconfig-rib-bgp {
    prefix oc-rib-bgp;
  }

  import arcos-openconfig-bgp-types {
    prefix arc-oc-bgp-types;
  }

  import openconfig-network-instance {
    prefix oc-ni;
  }

  import openconfig-network-instance-types {
    prefix oc-ni-types;
  }

  import openconfig-mpls-types {
    prefix "oc-mpls-t";
  }

  import arcos-bgp-types {
    prefix arc-bgp-types;
  }

  import openconfig-rib-bgp-types {
    prefix oc-ribbgp-types;
  }

  import arcos-srv6-types {
    prefix arc-srv6-types;
  }

  import arcos-openconfig-rib-bgp-types {
    prefix arc-oc-ribbgp-types;
  }

  import arcos-evpn {
    prefix arc-evpn;
  }

  organization
    "Arrcus, Inc.";

  contact
    "Arrcus, Inc.
     2077 Gateway Place
     Suite 400
     San Jose, CA 95110
     E-mail: yang-support@arrcus.com";

  description
    "This module defines augmentation for Arrcus
     implementation of the openconfig BGP RIB module.
     
     Copyright (c) 2016-2023 by Arrcus, Inc.
     All rights reserved.";

  revision 2024-04-14 {
    description
      "Adding exported rib for L3VPN IPVX Flowspec";
  }

  revision 2024-02-15 {
    description
      "Add FLOW_LABEL_MISMATCH identity to indicate invalid route reason";
  }

  revision 2024-01-16 {
    description
      "Add new identity VPWS_LOCAL_SWITCHING to PATH_TYPE";
  }

  revision 2023-12-20 {
    description
      "Support multiple SRV6 L3 service SIDs in the prefix SID attribute.";
  }

  revision 2023-12-07 {
    description
      "Change BGP path-id PFCP to LOCAL_MUP";
  }

  revision 2023-11-28 {
    description
      "Add new path type to identify reoriginated MUP ST1 paths.";
  }

  revision 2023-11-19 {
    description
      "Add source address for MUP (ST1) path";
  }

  revision 2023-09-29 {
    description
      "Add pfcp session identifer attributes to state container of MUP path";
  }

  revision 2023-09-26 {
    description
      "*ENUM values for different local path types";
  }

  revision 2023-09-04 {
    description
      "* Rename adj-rib-common groupings to adj-rib-in-pre
       * Use redist-info grouping in loc-rib and adj-rib-out subtrees";
  }

  revision 2023-08-02 {
    description "Added oper state for allocated per-nexthop label or SID in paths";
  }

  revision 2023-06-02 {
    description "Added next-hop-id for routes";
  }

  revision 2023-06-01 {
      description "Added L3RIB redistribution info to loc-rib groupings";
  }

  revision 2023-05-19 {
      description
        "Added CONTROL_WORD_MISMATCH identity to indicate invalid route reason";
  }

  revision 2023-02-22 {
      description "Added network-instance filter for EVPN routes";
  }

  revision 2022-10-26 {
      description "Added network-instance filter for MUP routes";
  }

  revision 2022-08-10 {
      description "Added MUP SAFI support";
  }

  revision 2022-04-19 {
      description
        "* Added auto-inbound-soft-reconfiguation to route oper state.
         * Extended path-flags to 64-bits.";
  }

  revision 2022-03-15 {
      description "Added SID Next Hop for routes";
  }

  revision 2019-06-24 {
      description "ArcOS release 3.3.1";
  }

  revision 2018-08-14 {
      description "ArcOS release 2.2.1";
  }

  revision 2017-09-12 {
    description
      "Initial Revision
       * Add BGP-LU Support.
       * Add embedded attribute state to route.
       * Add route/state/{versions|path-types|path-lists|rib-outs}.
       * Add attr-set/state/{community-index|ext-community-index/refcount}.
       * Add weigth/as-path-string to route/attributes/state and
         attr-set/state.
      ";

    reference
      "RFC 6020: YANG - A Data Modeling Language for the
       Network Configuration Protocol (NETCONF)";
  }

  grouping bgp-rib-ag-adj-rib-common-attr-refs {
    description
      "Definitions of common references to attribute sets for
      multiple AFI-SAFIs for Adj-RIB tables";

    leaf attr-index {
      type leafref {
        path "../../../../../../../../../../oc-ni:attr-sets/oc-ni:attr-set/" +
          "oc-ni:state/oc-ni:index";
      }
      description
        "Reference to the common attribute group for the
        route";
    }

    leaf community-index {
      type leafref {
        path "../../../../../../../../../../oc-ni:communities/oc-ni:community/" +
          "oc-ni:state/oc-ni:index";
      }
      description
        "Reference to the community attribute for the route";
    }

    leaf ext-community-index {
      type leafref {
        path "../../../../../../../../../../oc-ni:ext-communities/" +
          "oc-ni:ext-community/oc-ni:state/oc-ni:index";
      }
      description
        "Reference to the extended community attribute for the
        route";
    }
  }

  grouping bgp-rib-ag-exported-adj-rib-out-attr-refs {
    description
      "Definitions of common references to attribute sets for
      multiple AFI-SAFIs for Adj-RIB tables";

    leaf attr-index {
      type leafref {
        path "../../../../../../../../../../../../oc-ni:attr-sets/oc-ni:attr-set/" +
          "oc-ni:state/oc-ni:index";
      }
      description
        "Reference to the common attribute group for the
        route";
    }

    leaf community-index {
      type leafref {
        path "../../../../../../../../../../../../oc-ni:communities/oc-ni:community/" +
          "oc-ni:state/oc-ni:index";
      }
      description
        "Reference to the community attribute for the route";
    }

    leaf ext-community-index {
      type leafref {
        path "../../../../../../../../../../../../oc-ni:ext-communities/" +
          "oc-ni:ext-community/oc-ni:state/oc-ni:index";
      }
      description
        "Reference to the extended community attribute for the
        route";
    }
  }

  grouping bgp-rib-ag-loc-rib-common-attr-refs {
    description
      "Definitions of common references to attribute sets for
      multiple AFI-SAFIs for LOC-RIB tables";

    leaf attr-index {
      type leafref {
        path "../../../../../../../../oc-ni:attr-sets/oc-ni:attr-set/" +
          "oc-ni:state/oc-ni:index";
      }
      description
        "Reference to the common attribute group for the
        route";
    }

    leaf community-index {
      type leafref {
        path "../../../../../../../../oc-ni:communities/oc-ni:community/" +
          "oc-ni:state/oc-ni:index";
      }
      description
        "Reference to the community attribute for the route";
    }

    leaf ext-community-index {
      type leafref {
        path "../../../../../../../../oc-ni:ext-communities/" +
          "oc-ni:ext-community/oc-ni:state/oc-ni:index";
      }
      description
        "Reference to the extended community attribute for the
        route";
    }
  }

  grouping bgp-large-community-attr-state {
    description
      "Common definition of BGP large community attribute";

    leaf-list large-community {
      type arc-oc-bgp-types:bgp-large-community-type;
      description
        "List of BGP large community attributes.  The received
        large community may be an explicitly modeled
        by an 12 octet value according to RFC 8092.";
      reference
        "RFC 8092 - BGP Large Communities Attribute";
    }

  }

  grouping large-community-sets-top {
    description
      "Top level grouping for list of large community attribute
      sets";

    container large-communities {
      description
        "Enclosing container for the list of large community
        attribute sets";

      list large-community {
        key "index";

        description
          "List of path attributes that may be in use by multiple
          routes in the table";

        leaf index {
          type leafref {
            path "../state/index";
          }
          description
            "Reference to the list key";
        }

        container state {
          config false;
          description
            "Operational state for shared BGP large community
            attribute";

          leaf index {
            type uint64;
            description
              "System generated index for each attribute set.  The
              index is used to reference an attribute set from a
              specific path.  Multiple paths may reference the same
              attribute set.";
          }

          leaf refcount {
            type uint32;
            description
              "Refcount of the large community attribute";
          }

          uses bgp-large-community-attr-state;
        }
      }
    }
  }

  grouping attr-route-shared-top {
    leaf weight {
      type uint16;
      description
        "Weight of the route";
    }

    leaf aigp-metric {
      type uint64;
      description
        "AIGP metric of the route";
    }

    leaf as-path-string {
      type string;
      description
        "String representation of the AS path.";
    }

    leaf esi {
      type string;
      description
        "Ethernet Segment ID (ESI)";
    }

    leaf gateway {
      type inet:ip-address;
      description
        "EVPN route type-5 gateway";
    }
  }

  grouping attr-top {
    leaf community-index {
      type leafref {
        path "../../../../oc-ni:communities" +
             "/oc-ni:community/oc-ni:state/oc-ni:index";
      }
      description
        "Reference to the community attribute for the route";
    }

    leaf ext-community-index {
      type leafref {
        path "../../../../oc-ni:ext-communities" +
             "/oc-ni:ext-community/oc-ni:state/oc-ni:index";
      }
      description
        "Reference to the extended community attribute for the
        route";
    }

    leaf large-community-index {
      type leafref {
        path "../../../../arc-oc-rib-bgp-aug:large-communities" +
             "/arc-oc-rib-bgp-aug:large-community/arc-oc-rib-bgp-aug:state/arc-oc-rib-bgp-aug:index";
      }
      description
        "Reference to the large community attribute for the
        route";
    }

    uses attr-route-shared-top;

    leaf refcount {
      type uint32;
      description
        "Refcount of the attr-set";
    }
  }

  grouping comm-top {
    leaf refcount {
      type uint32;
      description
        "Refcount of the community attribute";
    }
  }

  grouping extcomm-top {
    leaf refcount {
      type uint32;
      description
        "Refcount of the extended community attribute";
    }
  }

  grouping bgp-loc-rib-remote-label {
    leaf out-tag {
      type uint32;
      default 0;
      description
        "MPLS Out tag";
    }

    leaf-list remote-labels {
      type uint32;
      description
        "Per-path remote labels";
    }
  }

  grouping bgp-loc-rib-pfcp-session-info {
    container pfcp {
      container state {
        leaf session-id {
          type uint64;
          description
            "PFCP Session ID for this path";
        }
        leaf upf-address {
          type inet:ip-address;
          description
            "UPF address from the PFCP session";
        }
        leaf smf-address {
          type inet:ip-address;
          description
            "SMF address from the PFCP session";
        }
      }
    }
  }

  grouping bgp-loc-rib-local-label {
    leaf local-label {
      type uint32;
      description
        "Per-NLRI local label";
    }
  }

  grouping bgp-loc-rib-redist-info {
    leaf l3rib-nhid {
      type uint32;
      description
        "Next-hop ID (NHID) for this route learnt from L3RIB";
    }
  }

  grouping bgp-l2vpn-evpn-route-filters-top {
    description
      "Filters for EVPN route types.";
    leaf route-type {
      type uint8;
      description
        "EVPN route type.";
    }

    leaf route-distinguisher {
      type oc-ni-types:route-distinguisher;
      description
        "The route distinguisher of the EVPN route.";
    }

    leaf network-instance {
      type leafref {
        path "/oc-ni:network-instances" +
             "/oc-ni:network-instance/oc-ni:name";
      }
      description
        "The network-instance of the the EVPN route";
    }

    leaf domain {
      type leafref {
        path "/arc-evpn:evpn/arc-evpn:domains/arc-evpn:domain/arc-evpn:name";
      }
      description
        "The Domain of the the EVPN route";
    }
  }

  grouping bgp-l2vpn-evpn-route-top {

    leaf second-out-tag {
      type uint32;
      description
        "Second label";
    }
  }

  grouping bgp-lu-adj-rib-key-refs-v4 {
    description
      "Key references to support operational state structure for
      the BGP ADJ-RIB table";

    leaf prefix {
      type leafref {
        path "../state/prefix";
      }
      description
        "Reference to the prefix list key";
    }

    leaf path-id {
      type leafref {
        path "../state/path-id";
      }
      description
        "Reference to the path-id list key";
    }
  }

  grouping bgp-lu-loc-rib-key-refs-v4 {
    description
      "Key references to support operational state structure for
      the BGP LOC-RIB table";

    leaf prefix {
      type leafref {
        path "../state/prefix";
      }
      description
        "Reference to the prefix list key";
    }

    leaf origin {
      type leafref {
        path "../state/origin";
      }
      description
        "Reference to the origin list key";
    }

    leaf path-id {
      type leafref {
        path "../state/path-id";
      }
      description
        "Reference to the path-id list key";
    }
  }

  grouping bgp-lu-adj-rib-key-refs-v6 {
    description
      "Key references to support operational state structure for
      the BGP ADJ-RIB table";

    leaf prefix {
      type leafref {
        path "../state/prefix";
      }
      description
        "Reference to the prefix list key";
    }

    leaf path-id {
      type leafref {
        path "../state/path-id";
      }
      description
        "Reference to the path-id list key";
    }
  }

  grouping bgp-lu-loc-rib-key-refs-v6 {
    description
      "Key references to support operational state structure for
      the BGP LOC-RIB table";

    leaf prefix {
      type leafref {
        path "../state/prefix";
      }
      description
        "Reference to the prefix list key";
    }

    leaf origin {
      type leafref {
        path "../state/origin";
      }
      description
        "Reference to the origin list key";
    }

    leaf path-id {
      type leafref {
        path "../state/path-id";
      }
      description
        "Reference to the path-id list key";
    }
  }

  grouping ipv4-lu-loc-rib-top {
    description
      "Top-level grouping for IPv4 routing tables";

    container loc-rib {
      config false;
      description
        "Container for the IPv4 BGP LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-lu-loc-rib-key-refs-v4;

          container state {
            description
              "Operational state data for route entries in the
              BGP LOC-RIB";

            leaf prefix {
              type inet:ipv4-prefix;
              description
                "The IPv4 prefix corresponding to the route";
            }

            uses arc-bgp-types:bgp-loc-rib-common-keys;
            uses bgp-loc-rib-local-label;
            uses bgp-loc-rib-remote-label;
            uses bgp-rib-ag-loc-rib-common-attr-refs;
            uses oc-rib-bgp:bgp-loc-rib-attr-state;
            uses oc-rib-bgp:bgp-common-route-annotations-state;
            uses oc-rib-bgp:bgp-loc-rib-route-annotations-state;
            uses bgp-prefix-sid-attr-top;
            uses bgp-loc-rib-redist-info;
           }

           uses oc-rib-bgp:bgp-unknown-attr-top;
        }
      }
    }
  }

  grouping ipv4-lu-adj-rib-out {
    description
      "Structural grouping for each IPv4 label-unicast adj-RIB-out table";

    uses oc-rib-bgp:bgp-common-table-attrs-top;

    container routes {
      config false;
      description
        "Enclosing container for list of routes in the routing
        table.";

      list route {
        key "prefix origin path-id";

        description
          "List of routes in the table, keyed by a combination of
          the route prefix, origin and path-id to distinguish multiple
          routes received from a neighbor for the same prefix,
          e.g., when BGP add-paths is enabled.";

        uses bgp-lu-loc-rib-key-refs-v4;

        container state {
          description
            "Operational state data for BGP Adj-RIB entries";

          leaf prefix {
            type inet:ipv4-prefix;
            description
              "Prefix for the route";
          }

          leaf origin {
            type arc-bgp-types:bgp-rib-origin-type;
            description
              "The origin of the route";
          }

          uses bgp-loc-rib-local-label;
          uses bgp-loc-rib-remote-label;
          uses arc-bgp-types:bgp-adj-rib-attr-state;
          uses bgp-rib-ag-adj-rib-common-attr-refs;
          uses oc-rib-bgp:bgp-common-route-annotations-state;
          uses bgp-prefix-sid-attr-top;
          uses bgp-loc-rib-redist-info;
        }

        uses oc-rib-bgp:bgp-unknown-attr-top;
      }
    }
  }

  grouping ipv4-lu-adj-rib-in-pre {
    description
      "Structural grouping for each IPv4 label-unicast adj-RIB-in-pre table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-lu-adj-rib-key-refs-v4;

        container state {
          description
            "Operational state data for BGP Adj-RIB entries";

          leaf prefix {
            type inet:ipv4-prefix;
            description
              "Prefix for the route";
          }
          uses bgp-loc-rib-local-label;
          uses bgp-loc-rib-remote-label;
          uses arc-bgp-types:bgp-adj-rib-attr-state;
          uses bgp-rib-ag-adj-rib-common-attr-refs;
          uses oc-rib-bgp:bgp-common-route-annotations-state;
          uses bgp-prefix-sid-attr-top;
        }

        uses oc-rib-bgp:bgp-unknown-attr-top;
      }
    }
  }

  grouping ipv4-lu-adj-rib-in-post {
    description
      "Common structural grouping for the IPv4 label-unicast adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-lu-adj-rib-key-refs-v4;

        container state {
          description
            "Operational state data for BGP Adj-RIB entries";

          leaf prefix {
            type inet:ipv4-prefix;
            description
              "Prefix for the route";
          }

          uses bgp-loc-rib-local-label;
          uses bgp-loc-rib-remote-label;
          uses arc-bgp-types:bgp-adj-rib-attr-state;
          uses bgp-rib-ag-adj-rib-common-attr-refs;
          uses oc-rib-bgp:bgp-common-route-annotations-state;
          uses oc-rib-bgp:bgp-adj-rib-in-post-route-annotations-state;
          uses bgp-prefix-sid-attr-top;
        }

        uses oc-rib-bgp:bgp-unknown-attr-top;
      }
    }
  }

  grouping ipv4-lu-adj-rib-top {
    description
      "Top-level grouping for ipv4-label-unicast Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }

        container adj-rib-in-pre {
          description
            "Per-neighbor table containing the NLRI updates
            received from the neighbor before any local input
            policy rules or filters have been applied.  This can
            be considered the 'raw' updates from the neighbor.";

          uses ipv4-lu-adj-rib-in-pre;
        }

        container adj-rib-in-post {
          description
            "Per-neighbor table containing the paths received from
            the neighbor that are eligible for best-path selection
            after local input policy rules have been applied.";

          uses ipv4-lu-adj-rib-in-post;
        }

        container adj-rib-out {
          description
            "Per-neighbor table containing prefixes that have been
            advertised to the neighbor without applying output policy
            rules for attributes and/or next-hop change";

          uses ipv4-lu-adj-rib-out;
        }
      }
    }
  }

  grouping ipv6-lu-loc-rib-top {
    description
      "Top-level grouping for IPv6 routing tables";

    container loc-rib {
      config false;
      description
        "Container for the IPv6 BGP LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-lu-loc-rib-key-refs-v6;

          container state {
            description
              "Operational state data for route entries in the
              BGP LOC-RIB";

            leaf prefix {
              type inet:ipv6-prefix;
              description
                "The IPv6 prefix corresponding to the route";
            }

            uses arc-bgp-types:bgp-loc-rib-common-keys;
            uses bgp-loc-rib-local-label;
            uses bgp-loc-rib-remote-label;
            uses bgp-rib-ag-loc-rib-common-attr-refs;
            uses oc-rib-bgp:bgp-loc-rib-attr-state;
            uses oc-rib-bgp:bgp-common-route-annotations-state;
            uses oc-rib-bgp:bgp-loc-rib-route-annotations-state;
            uses bgp-prefix-sid-attr-top;
            uses bgp-loc-rib-redist-info;
          }

          uses oc-rib-bgp:bgp-unknown-attr-top;
        }
      }
    }
  }

  grouping ipv6-lu-adj-rib-out {
    description
      "Structural grouping for each IPv6 label-unicast adj-RIB-out table";

    uses oc-rib-bgp:bgp-common-table-attrs-top;

    container routes {
      config false;
      description
        "Enclosing container for list of routes in the routing
        table.";

      list route {
        key "prefix origin path-id";

        description
          "List of routes in the table, keyed by a combination of
          the route prefix, origin and path-id to distinguish multiple
          routes received from a neighbor for the same prefix,
          e.g., when BGP add-paths is enabled.";

        uses bgp-lu-loc-rib-key-refs-v6;

        container state {
          description
            "Operational state data for BGP Adj-RIB entries";

          leaf prefix {
            type inet:ipv6-prefix;
            description
              "Prefix for the route";
          }

          leaf origin {
            type arc-bgp-types:bgp-rib-origin-type;
            description
              "The origin of the route";
          }

          uses bgp-loc-rib-local-label;
          uses bgp-loc-rib-remote-label;
          uses arc-bgp-types:bgp-adj-rib-attr-state;
          uses bgp-rib-ag-adj-rib-common-attr-refs;
          uses oc-rib-bgp:bgp-common-route-annotations-state;
          uses bgp-loc-rib-redist-info;
        }

        uses oc-rib-bgp:bgp-unknown-attr-top;
      }
    }
  }

  grouping ipv6-lu-adj-rib-in-pre {
    description
      "Structural grouping for each IPv4 label-unicast adj-RIB-in-pre table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-lu-adj-rib-key-refs-v6;

        container state {
          description
            "Operational state data for BGP Adj-RIB entries";

          leaf prefix {
            type inet:ipv6-prefix;
            description
              "Prefix for the route";
          }
          uses bgp-loc-rib-local-label;
          uses bgp-loc-rib-remote-label;
          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping ipv6-lu-adj-rib-in-post {
    description
      "Common structural grouping for the IPv4 label-unicast adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-lu-adj-rib-key-refs-v6;

        container state {
          description
            "Operational state data for BGP Adj-RIB entries";

          leaf prefix {
            type inet:ipv6-prefix;
            description
              "Prefix for the route";
          }

          uses bgp-loc-rib-local-label;
          uses bgp-loc-rib-remote-label;
          uses arc-bgp-types:bgp-adj-rib-attr-state;
          uses bgp-rib-ag-adj-rib-common-attr-refs;
          uses oc-rib-bgp:bgp-common-route-annotations-state;
          uses oc-rib-bgp:bgp-adj-rib-in-post-route-annotations-state;
          uses bgp-prefix-sid-attr-top;
        }

        uses oc-rib-bgp:bgp-unknown-attr-top;
      }
    }
  }

  grouping ipv6-lu-adj-rib-top {
    description
      "Top-level grouping for ipv4-label-unicast Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }

        container adj-rib-in-pre {
          description
            "Per-neighbor table containing the NLRI updates
            received from the neighbor before any local input
            policy rules or filters have been applied.  This can
            be considered the 'raw' updates from the neighbor.";

          uses ipv6-lu-adj-rib-in-pre;
        }

        container adj-rib-in-post {
          description
            "Per-neighbor table containing the paths received from
            the neighbor that are eligible for best-path selection
            after local input policy rules have been applied.";

          uses ipv6-lu-adj-rib-in-post;
        }

        container adj-rib-out {
          description
            "Per-neighbor table containing prefixes that have been
            advertised to the neighbor without applying output policy
            rules for attributes and/or next-hop change";

          uses ipv6-lu-adj-rib-out;
        }
      }
    }
  }


  grouping bgp-vpn-loc-rib-key-refs {
    description
      "Key references to support operational state structure for
      the BGP VPNv4 and VPNv6 LOC-RIB tables";

    leaf prefix {
      type leafref {
        path "../state/prefix";
      }
      description
        "Reference to the prefix list key";
    }

    leaf origin {
      type leafref {
        path "../state/origin";
      }
      description
        "Reference to the origin list key";
    }

    leaf path-id {
      type leafref {
        path "../state/path-id";
      }
      description
        "Reference to the path-id list key";
    }
  }

  grouping bgp-vpn-adj-rib-in-key-refs {
    description
      "Key references to support operational state structure for
      the BGP VPNv4 and VPNv6 adj-RIB-in tables";

    leaf prefix {
      type leafref {
        path "../state/prefix";
      }
      description
        "Reference to the prefix list key";
    }

    leaf path-id {
      type leafref {
        path "../state/path-id";
      }
      description
        "Reference to the path-id list key";
    }
  }

  grouping l3vpn-ipv4-loc-rib-top {
    description
      "Top-level grouping for VPNv4 routing tables";

    container loc-rib {
      config false;
      description
        "Container for the VPNv4 BGP LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-vpn-loc-rib-key-refs;

          container state {
            description
              "Operational state data for route entries in the
              BGP LOC-RIB";

            leaf prefix {
              type string;
              description
                "The VPNv4 or VPNv6 prefix corresponding to the route";
            }

            uses arc-bgp-types:bgp-loc-rib-common-keys;

            uses bgp-loc-rib-local-label;

            uses bgp-rib-ag-loc-rib-common-attr-refs;

            uses oc-rib-bgp:bgp-loc-rib-attr-state;

            uses oc-rib-bgp:bgp-common-route-annotations-state;

            uses oc-rib-bgp:bgp-loc-rib-route-annotations-state;

            uses bgp-loc-rib-remote-label;

            uses bgp-loc-rib-redist-info;
          }

          uses oc-rib-bgp:bgp-unknown-attr-top;
        }
      }
    }
  }

  grouping l3vpn-ipv4-exported-adj-rib-out {
    description
      "Structural grouping for VPNv4 exported adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

        uses bgp-vpn-loc-rib-key-refs;

        container state {
          description
            "Operational state data for BGP Adj-RIB entries";

          leaf prefix {
            type string;
            description
              "The VPNv4 prefix corresponding to the route";
          }

          leaf origin {
            type arc-bgp-types:bgp-rib-origin-type;
            description
              "The origin of the route";
          }

          uses bgp-loc-rib-local-label;

          uses arc-bgp-types:bgp-adj-rib-attr-state;

          uses bgp-rib-ag-exported-adj-rib-out-attr-refs;

          uses oc-rib-bgp:bgp-common-route-annotations-state;

          uses bgp-loc-rib-redist-info;
        }

        uses oc-rib-bgp:bgp-unknown-attr-top;
      }
    }
  }

  grouping l3vpn-ipv6-exported-adj-rib-out {
    description
      "Structural grouping for VPNv6 exported adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

        uses bgp-vpn-loc-rib-key-refs;

        container state {
          description
            "Operational state data for BGP Adj-RIB entries";

          leaf prefix {
            type string;
            description
              "The VPNv6 prefix corresponding to the route";
          }

          leaf origin {
            type arc-bgp-types:bgp-rib-origin-type;
            description
              "The origin of the route";
          }

          uses bgp-loc-rib-local-label;

          uses arc-bgp-types:bgp-adj-rib-attr-state;

          uses bgp-rib-ag-exported-adj-rib-out-attr-refs;

          uses oc-rib-bgp:bgp-common-route-annotations-state;

          uses bgp-loc-rib-redist-info;
        }

        uses oc-rib-bgp:bgp-unknown-attr-top;
      }
    }
  }

  grouping l3vpn-ipv4-adj-rib-out {
    description
      "Structural grouping for VPNv4 adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

        uses bgp-vpn-loc-rib-key-refs;

        container state {
          description
            "Operational state data for BGP Adj-RIB entries";

          leaf prefix {
            type string;
            description
              "The VPNv4 prefix corresponding to the route";
          }

          leaf origin {
            type arc-bgp-types:bgp-rib-origin-type;
            description
              "The origin of the route";
          }

          uses bgp-loc-rib-local-label;

          uses arc-bgp-types:bgp-adj-rib-attr-state;

          uses bgp-rib-ag-adj-rib-common-attr-refs;

          uses oc-rib-bgp:bgp-common-route-annotations-state;

          uses bgp-loc-rib-remote-label;

          uses bgp-loc-rib-redist-info;
        }

        uses oc-rib-bgp:bgp-unknown-attr-top;
      }
    }
  }

  grouping l3vpn-ipv4-exported-rib {
    description
      "Structural grouping for VPNv4 table from exported routes";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

        uses bgp-vpn-loc-rib-key-refs;

        container state {
          description
            "Operational state data for BGP exported RIB entries";

          leaf prefix {
            type string;
            description
              "The VPNv4 prefix corresponding to the route";
          }

          leaf origin {
            type arc-bgp-types:bgp-rib-origin-type;
            description
              "The origin of the route";
          }

          uses bgp-loc-rib-local-label;

          uses arc-bgp-types:bgp-adj-rib-attr-state;

          uses bgp-rib-ag-adj-rib-common-attr-refs;

          uses oc-rib-bgp:bgp-common-route-annotations-state;

          uses bgp-loc-rib-remote-label;

          uses bgp-loc-rib-redist-info;
        }

        uses oc-rib-bgp:bgp-unknown-attr-top;
      }
    }
  }

  grouping l3vpn-ipv6-exported-rib {
    description
      "Structural grouping for VPNv6 table from exported routes";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

        uses bgp-vpn-loc-rib-key-refs;

        container state {
          description
            "Operational state data for BGP exported RIB entries";

          leaf prefix {
            type string;
            description
              "The VPNv6 prefix corresponding to the route";
          }

          leaf origin {
            type arc-bgp-types:bgp-rib-origin-type;
            description
              "The origin of the route";
          }

          uses bgp-loc-rib-local-label;

          uses arc-bgp-types:bgp-adj-rib-attr-state;

          uses bgp-rib-ag-adj-rib-common-attr-refs;

          uses oc-rib-bgp:bgp-common-route-annotations-state;

          uses bgp-loc-rib-remote-label;

          uses bgp-loc-rib-redist-info;
        }

        uses oc-rib-bgp:bgp-unknown-attr-top;
      }
    }
  }

  grouping l3vpn-ipv4-adj-rib-in-pre {
    description
      "Structural grouping for each VPNv4 adj-RIB-in-pre table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-vpn-adj-rib-in-key-refs;

        container state {
          description
            "Operational state data for BGP Adj-RIB entries";

          leaf prefix {
            type string;
            description
              "The VPNv4 or VPNv6 prefix corresponding to the route";
          }

          uses bgp-loc-rib-local-label;

          uses arc-bgp-types:bgp-adj-rib-attr-state;

          uses bgp-rib-ag-adj-rib-common-attr-refs;

          uses oc-rib-bgp:bgp-common-route-annotations-state;

          uses bgp-loc-rib-remote-label;
        }

        uses oc-rib-bgp:bgp-unknown-attr-top;
      }
    }
  }

  grouping l3vpn-ipv4-adj-rib-in-post {
    description
      "Common structural grouping for the VPNv4 adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-vpn-adj-rib-in-key-refs;

        container state {
          description
            "Operational state data for BGP Adj-RIB entries";

          leaf prefix {
            type string;
            description
              "The VPNv4 or VPNv6 prefix corresponding to the route";
          }

          uses bgp-loc-rib-local-label;

          uses arc-bgp-types:bgp-adj-rib-attr-state;

          uses bgp-rib-ag-adj-rib-common-attr-refs;

          uses oc-rib-bgp:bgp-common-route-annotations-state;

          uses bgp-loc-rib-remote-label;
        }

        uses oc-rib-bgp:bgp-unknown-attr-top;
      }
    }
  }

  grouping l3vpn-ipv4-ni-exported-adj-rib-out-top {
    description
      "Top-level grouping for exported adj-rib-out to a neighbor";

    container network-instances {
      config false;
      description
        "Enclosing container for network-instance list";

      list network-instance {
        key "network-instance-name";
        description
          "List of network-instances the routes are exported from";

        leaf network-instance-name {
          type leafref {
            path "../state/network-instance-name";
          }
          description
            "Reference to the list key";
        }

        container state {
          description
            "Operational state for each network-instance exported RIB";

          leaf network-instance-name {
            type leafref {
              path "/oc-ni:network-instances/oc-ni:network-instance/oc-ni:config/oc-ni:name";
            }
            description
              "Reference to the network-instance list key";
          }
        }

        container adj-rib-out {
          description
            "Per-neighbor table containing prefixes that have been
            advertised to the neighbor without applying output policy
            rules for attributes and/or next-hop change";

          uses l3vpn-ipv4-exported-adj-rib-out;
        }
      }
    }
  }

  grouping l3vpn-ipv6-ni-exported-adj-rib-out-top {
    description
      "Top-level grouping for exported adj-rib-out to a neighbor";

    container network-instances {
      config false;
      description
        "Enclosing container for network-instance list";

      list network-instance {
        key "network-instance-name";
        description
          "List of network-instances the routes are exported from";

        leaf network-instance-name {
          type leafref {
            path "../state/network-instance-name";
          }
          description
            "Reference to the list key";
        }

        container state {
          description
            "Operational state for each network-instance exported RIB";

          leaf network-instance-name {
            type leafref {
              path "/oc-ni:network-instances/oc-ni:network-instance/oc-ni:config/oc-ni:name";
            }
            description
              "Reference to the network-instance list key";
          }
        }

        container adj-rib-out {
          description
            "Per-neighbor table containing prefixes that have been
            advertised to the neighbor without applying output policy
            rules for attributes and/or next-hop change";

          uses l3vpn-ipv6-exported-adj-rib-out;
        }
      }
    }
  }

  grouping l3vpn-ipv4-ni-exported-rib-top {
    description
      "Top-level grouping for exported routes from network-instances";

    container network-instances {
      config false;
      description
        "Enclosing container for network-instance list";

      list network-instance {
        key "network-instance-name";
        description
          "List of network-instances the routes are exported from";

        leaf network-instance-name {
          type leafref {
            path "../state/network-instance-name";
          }
          description
            "Reference to the list key";
        }

        container state {
          description
            "Operational state for each network-instance exported RIB";

          leaf network-instance-name {
            type leafref {
              path "/oc-ni:network-instances/oc-ni:network-instance/oc-ni:config/oc-ni:name";
            }
            description
              "Reference to the network-instance list key";
          }
        }

        container exported-rib {
          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses l3vpn-ipv4-exported-rib;
        }
      }
    }
  }

  grouping l3vpn-ipv6-ni-exported-rib-top {
    description
      "Top-level grouping for exported routes from network-instances";

    container network-instances {
      config false;
      description
        "Enclosing container for network-instance list";

      list network-instance {
        key "network-instance-name";
        description
          "List of network-instances the routes are exported from";

        leaf network-instance-name {
          type leafref {
            path "../state/network-instance-name";
          }
          description
            "Reference to the list key";
        }

        container state {
          description
            "Operational state for each network-instance exported RIB";

          leaf network-instance-name {
            type leafref {
              path "/oc-ni:network-instances/oc-ni:network-instance/oc-ni:config/oc-ni:name";
            }
            description
              "Reference to the network-instance list key";
          }
        }

        container exported-rib {
          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses l3vpn-ipv6-exported-rib;
        }
      }
    }
  }

  grouping l3vpn-ipv4-adj-rib-top {
    description
      "Top-level grouping for Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }

        container adj-rib-in-pre {
          description
            "Per-neighbor table containing the NLRI updates
            received from the neighbor before any local input
            policy rules or filters have been applied.  This can
            be considered the 'raw' updates from the neighbor.";

          uses l3vpn-ipv4-adj-rib-in-pre;
        }

        container adj-rib-in-post {
          description
            "Per-neighbor table containing the paths received from
            the neighbor that are eligible for best-path selection
            after local input policy rules have been applied.";

          uses l3vpn-ipv4-adj-rib-in-post;
        }

        container adj-rib-out {
          description
            "Per-neighbor table containing prefixes that have been
            advertised to the neighbor without applying output policy
            rules for attributes and/or next-hop change";

          uses l3vpn-ipv4-adj-rib-out;
        }

        uses l3vpn-ipv4-ni-exported-adj-rib-out-top;
      }
    }
  }

  grouping bgp-flowspec-loc-rib-key-refs-v4 {
    description
      "Key references to support operational state structure for
      the BGP Flowspec IPv4 LOC-RIB tables";

    leaf prefix {
      type leafref {
        path "../state/prefix";
      }
      description
        "Reference to the prefix list key";
    }

    leaf origin {
      type leafref {
        path "../state/origin";
      }
      description
        "Reference to the origin list key";
    }

    leaf path-id {
      type leafref {
        path "../state/path-id";
      }
      description
        "Reference to the path-id list key";
    }
  }

  grouping bgp-flowspec-adj-rib-in-key-refs-v4 {
    description
      "Key references to support operational state structure for
      the BGP Flowspec IPv4 adj-RIB-in tables";

    leaf prefix {
      type leafref {
        path "../state/prefix";
      }
      description
        "Reference to the prefix list key";
    }

    leaf path-id {
      type leafref {
        path "../state/path-id";
      }
      description
        "Reference to the path-id list key";
    }
  }

  grouping ipv4-flowspec-loc-rib-top {
    description
      "Top-level grouping for Flowspec IPv4 routing tables";

    container loc-rib {
      config false;
      description
        "Container for the Flowspec IPv4 BGP LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-flowspec-loc-rib-key-refs-v4;

          container state {
            description
              "Operational state data for route entries in the
              BGP LOC-RIB";

            leaf prefix {
              type string;
              description
                "The Flowspec IPv4 prefix corresponding to the route";
            }

            uses arc-bgp-types:bgp-loc-rib-common-keys;
            uses bgp-rib-ag-loc-rib-common-attr-refs;
            uses oc-rib-bgp:bgp-loc-rib-attr-state;
            uses oc-rib-bgp:bgp-common-route-annotations-state;
            uses oc-rib-bgp:bgp-loc-rib-route-annotations-state;
          }

          uses oc-rib-bgp:bgp-unknown-attr-top;
        }
      }
    }
  }

  grouping ipv4-flowspec-adj-rib-out {
    description
      "Structural grouping for Flowspec IPv4 adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

          uses bgp-flowspec-loc-rib-key-refs-v4;

        container state {
          description
            "Operational state data for BGP Adj-RIB entries";

          leaf prefix {
            type string;
            description
              "The Flowspec IPv4 prefix corresponding to the route";
          }

          leaf origin {
            type arc-bgp-types:bgp-rib-origin-type;
            description
              "The origin of the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping ipv4-flowspec-adj-rib-in-pre {
    description
      "Structural grouping for each Flowspec IPv4 adj-RIB-in-pre table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-flowspec-adj-rib-in-key-refs-v4;

        container state {
          description
            "Operational state data for BGP Adj-RIB entries";

          leaf prefix {
            type string;
            description
              "The Flowspec IPv4 prefix corresponding to the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping ipv4-flowspec-adj-rib-in-post {
    description
      "Common structural grouping for the Flowspec IPv4 adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-flowspec-adj-rib-in-key-refs-v4;

        container state {
          description
            "Operational state data for BGP Adj-RIB entries";

          leaf prefix {
            type string;
            description
              "The Flowspec IPv4 prefix corresponding to the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping ipv4-flowspec-adj-rib-top {
    description
      "Top-level grouping for Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }

        container adj-rib-in-pre {
          description
            "Per-neighbor table containing the NLRI updates
            received from the neighbor before any local input
            policy rules or filters have been applied.  This can
            be considered the 'raw' updates from the neighbor.";

          uses ipv4-flowspec-adj-rib-in-pre;
        }

        container adj-rib-in-post {
          description
            "Per-neighbor table containing the paths received from
            the neighbor that are eligible for best-path selection
            after local input policy rules have been applied.";

          uses ipv4-flowspec-adj-rib-in-post;
        }

        container adj-rib-out {
          description
            "Per-neighbor table containing prefixes that have been
            advertised to the neighbor without applying output policy
            rules for attributes and/or next-hop change";

          uses ipv4-flowspec-adj-rib-out;
        }
      }
    }
  }

  grouping l3vpn-ipv4-flowspec-loc-rib-top {
    description
      "Top-level grouping for Flowspec VPNv4 routing tables";

    container loc-rib {
      config false;
      description
        "Container for the Flowspec VPNv4 BGP LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-flowspec-loc-rib-key-refs-v4;

          container state {
            description
              "Operational state data for route entries in the
              BGP LOC-RIB";

            leaf prefix {
              type string;
              description
                "The Flowspec VPNv4 prefix corresponding to the route";
            }

            uses arc-bgp-types:bgp-loc-rib-common-keys;
            uses bgp-rib-ag-loc-rib-common-attr-refs;
            uses oc-rib-bgp:bgp-loc-rib-attr-state;
            uses oc-rib-bgp:bgp-common-route-annotations-state;
            uses oc-rib-bgp:bgp-loc-rib-route-annotations-state;
          }

          uses oc-rib-bgp:bgp-unknown-attr-top;
        }
      }
    }
  }

  grouping l3vpn-ipv4-flowspec-adj-rib-out {
    description
      "Structural grouping for Flowspec IPv4 adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

          uses bgp-flowspec-loc-rib-key-refs-v4;

        container state {
          description
            "Operational state data for BGP Adj-RIB entries";

          leaf prefix {
            type string;
            description
              "The Flowspec VPNv4 prefix corresponding to the route";
          }

          leaf origin {
            type arc-bgp-types:bgp-rib-origin-type;
            description
              "The origin of the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping l3vpn-ipv4-flowspec-adj-rib-in-pre {
    description
      "Common structural grouping for each Flowspec VPNv4 adj-RIB table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-flowspec-adj-rib-in-key-refs-v4;

        container state {
          description
            "Operational state data for BGP Adj-RIB entries";

          leaf prefix {
            type string;
            description
              "The Flowspec VPNv4 prefix corresponding to the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping l3vpn-ipv4-flowspec-adj-rib-in-post {
    description
      "Common structural grouping for the Flowspec VPNv4 adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-flowspec-adj-rib-in-key-refs-v4;

        container state {
          description
            "Operational state data for BGP Adj-RIB entries";

          leaf prefix {
            type string;
            description
              "The Flowspec VPNv4 prefix corresponding to the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping l3vpn-ipv4-flowspec-adj-rib-top {
    description
      "Top-level grouping for Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }

        container adj-rib-in-pre {
          description
            "Per-neighbor table containing the NLRI updates
            received from the neighbor before any local input
            policy rules or filters have been applied.  This can
            be considered the 'raw' updates from the neighbor.";

          uses l3vpn-ipv4-flowspec-adj-rib-in-pre;
        }

        container adj-rib-in-post {
          description
            "Per-neighbor table containing the paths received from
            the neighbor that are eligible for best-path selection
            after local input policy rules have been applied.";

          uses l3vpn-ipv4-flowspec-adj-rib-in-post;
        }

        container adj-rib-out {
          description
            "Per-neighbor table containing prefixes that have been
            advertised to the neighbor without applying output policy
            rules for attributes and/or next-hop change";

          uses l3vpn-ipv4-flowspec-adj-rib-out;
        }
      }
    }
  }

  /*
   * L2VPN EVPN loc-rib and adj-rib.
   */
  grouping bgp-l2vpn-evpn-loc-rib-key-refs {
    description
      "Key references to support operational state structure for
      the L2VPN EVPN LOC-RIB tables";

    leaf prefix {
      type leafref {
        path "../state/prefix";
      }
      description
        "Reference to the prefix list key";
    }

    leaf origin {
      type leafref {
        path "../state/origin";
      }
      description
        "Reference to the origin list key";
    }

    leaf path-id {
      type leafref {
        path "../state/path-id";
      }
      description
        "Reference to the path-id list key";
    }
  }

  grouping bgp-l2vpn-evpn-adj-rib-in-key-refs {
    description
      "Key references to support operational state structure for
      the BGP L2VPN EVPN adj-RIB-in tables";

    leaf prefix {
      type leafref {
        path "../state/prefix";
      }
      description
        "Reference to the prefix list key";
    }

    leaf path-id {
      type leafref {
        path "../state/path-id";
      }
      description
        "Reference to the path-id list key";
    }
  }

  grouping l2vpn-evpn-loc-rib-top {
    description
      "Top-level grouping for L2VPN EVPN routing tables";

    container loc-rib {
      config false;
      description
        "Container for the L2VPN EVPN BGP LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-l2vpn-evpn-loc-rib-key-refs;

          container state {
            description
              "Operational state data for route entries in the
              BGP LOC-RIB";

            leaf prefix {
              type string;
              description
                "The EVPN prefix corresponding to the route";
            }

            uses arc-bgp-types:bgp-loc-rib-common-keys;

            uses bgp-loc-rib-local-label;

            uses bgp-rib-ag-loc-rib-common-attr-refs;

            uses oc-rib-bgp:bgp-loc-rib-attr-state;

            uses oc-rib-bgp:bgp-common-route-annotations-state;

            uses oc-rib-bgp:bgp-loc-rib-route-annotations-state;

            uses bgp-loc-rib-remote-label;

            uses bgp-l2vpn-evpn-route-top;
          }

          uses bgp-l2vpn-evpn-route-filters-top;
          uses oc-rib-bgp:bgp-unknown-attr-top;
        }
      }
    }
  }

  grouping l2vpn-evpn-adj-rib-out {
    description
      "Structural grouping for L2VPN EVPN adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

        uses bgp-l2vpn-evpn-loc-rib-key-refs;

        container state {
          description
            "Operational state data for BGP Adj-RIB entries";

          leaf prefix {
            type string;
            description
              "The L2VPN EVPN prefix corresponding to the route";
          }

          leaf origin {
            type arc-bgp-types:bgp-rib-origin-type;
            description
              "The origin of the route";
          }

          uses bgp-loc-rib-local-label;

          uses arc-bgp-types:bgp-adj-rib-attr-state;

          uses bgp-rib-ag-adj-rib-common-attr-refs;

          uses oc-rib-bgp:bgp-common-route-annotations-state;

          uses bgp-loc-rib-remote-label;

          uses bgp-l2vpn-evpn-route-top;
        }

        uses bgp-l2vpn-evpn-route-filters-top;
        uses oc-rib-bgp:bgp-unknown-attr-top;
      }
    }
  }

  grouping l2vpn-evpn-adj-rib-in-pre {
    description
      "Structural grouping for each L2VPN EVPN adj-RIB-in-pre table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-l2vpn-evpn-adj-rib-in-key-refs;

        container state {
          description
            "Operational state data for BGP Adj-RIB entries";

          leaf prefix {
            type string;
            description
              "The L2VPN EVPN prefix corresponding to the route";
          }

          uses bgp-loc-rib-local-label;

          uses arc-bgp-types:bgp-adj-rib-attr-state;

          uses bgp-rib-ag-adj-rib-common-attr-refs;

          uses oc-rib-bgp:bgp-common-route-annotations-state;

          uses bgp-loc-rib-remote-label;

          uses bgp-l2vpn-evpn-route-top;
        }

        uses bgp-l2vpn-evpn-route-filters-top;
        uses oc-rib-bgp:bgp-unknown-attr-top;
      }
    }
  }

  grouping l2vpn-evpn-adj-rib-in-post {
    description
      "Common structural grouping for the L2VPN EVPN adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-l2vpn-evpn-adj-rib-in-key-refs;

        container state {
          description
            "Operational state data for BGP Adj-RIB entries";

          leaf prefix {
            type string;
            description
              "The VPNv4 or VPNv6 prefix corresponding to the route";
          }

          uses bgp-loc-rib-local-label;

          uses arc-bgp-types:bgp-adj-rib-attr-state;

          uses bgp-rib-ag-adj-rib-common-attr-refs;

          uses oc-rib-bgp:bgp-common-route-annotations-state;

          uses bgp-loc-rib-remote-label;

          uses bgp-l2vpn-evpn-route-top;
        }

        uses bgp-l2vpn-evpn-route-filters-top;
        uses oc-rib-bgp:bgp-unknown-attr-top;
      }
    }
  }

  grouping l2vpn-evpn-adj-rib-top {
    description
      "Top-level grouping for Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }

        container adj-rib-in-pre {
          description
            "Per-neighbor table containing the NLRI updates
            received from the neighbor before any local input
            policy rules or filters have been applied.  This can
            be considered the 'raw' updates from the neighbor.";

          uses l2vpn-evpn-adj-rib-in-pre;

        }

        container adj-rib-in-post {
          description
            "Per-neighbor table containing the paths received from
            the neighbor that are eligible for best-path selection
            after local input policy rules have been applied.";

          uses l2vpn-evpn-adj-rib-in-post;
        }

        container adj-rib-out {
          description
            "Per-neighbor table containing prefixes that have been
            advertised to the neighbor without applying output policy
            rules for attributes and/or next-hop change";

          uses l2vpn-evpn-adj-rib-out;
        }
      }
    }
  }

  /*
   * MUP loc-rib and adj-rib.
   */
  grouping bgp-mup-route-filters-top {
    description
      "Filters for MUP route types.";
    leaf route-type {
      type arc-bgp-types:bgp-mup-route-type;
      description
        "MUP route type.";
    }

    leaf route-distinguisher {
      type oc-ni-types:route-distinguisher;
      description
        "The route distinguisher of the MUP route.";
    }

    leaf network-instance {
      type leafref {
        path "/oc-ni:network-instances" +
             "/oc-ni:network-instance/oc-ni:name";
      }
      description
        "The network-instance of the the MUP route";
    }
  }

  grouping bgp-mup-route-top {
    container mup {
      container state {
        leaf teid {
          type inet:ipv4-address;
          description
            "The TEID carried in the Type-1 ST NLRI.";
          reference "draft-mpmz-bess-mup-safi-01.txt";
        }
        leaf qfi {
          type uint8;
          description
            "The QFI carried in the Type-1 ST NLRI.";
          reference "draft-mpmz-bess-mup-safi-01.txt";
        }
        leaf endpoint {
          type inet:ip-address;
          description
            "The endpoint address carried in the Type-1 ST NLRI.";
          reference "draft-mpmz-bess-mup-safi-01.txt";
        }
        leaf source {
          type inet:ip-address;
          description
            "The source address carried in the Type-1 ST NLRI.";
             reference "draft-mpmz-bess-mup-safi-03.txt";
        }
      }
    }
  }

  grouping bgp-mup-loc-rib-key-refs {
    description
      "Key references to support operational state structure for
      the MUP LOC-RIB tables";

    leaf prefix {
      type leafref {
        path "../state/prefix";
      }
      description
        "Reference to the prefix list key";
    }

    leaf origin {
      type leafref {
        path "../state/origin";
      }
      description
        "Reference to the origin list key";
    }

    leaf path-id {
      type leafref {
        path "../state/path-id";
      }
      description
        "Reference to the path-id list key";
    }
  }

  grouping bgp-mup-adj-rib-in-key-refs {
    description
      "Key references to support operational state structure for
      the BGP MUP adj-RIB-in tables";

    leaf prefix {
      type leafref {
        path "../state/prefix";
      }
      description
        "Reference to the prefix list key";
    }

    leaf path-id {
      type leafref {
        path "../state/path-id";
      }
      description
        "Reference to the path-id list key";
    }
  }

  grouping mup-loc-rib-top {
    description
      "Top-level grouping for MUP routing tables";

    container loc-rib {
      config false;
      description
        "Container for the MUP BGP LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-mup-loc-rib-key-refs;

          container state {
            description
              "Operational state data for route entries in the
              BGP LOC-RIB";

            leaf prefix {
              type string;
              description
                "The MUP prefix corresponding to the route";
            }

            uses arc-bgp-types:bgp-loc-rib-common-keys;

            uses bgp-rib-ag-loc-rib-common-attr-refs;

            uses oc-rib-bgp:bgp-loc-rib-attr-state;

            uses oc-rib-bgp:bgp-common-route-annotations-state;

            uses oc-rib-bgp:bgp-loc-rib-route-annotations-state;

          }

          uses bgp-mup-route-top;
          uses bgp-loc-rib-pfcp-session-info;
          uses bgp-mup-route-filters-top;
          uses oc-rib-bgp:bgp-unknown-attr-top;
        }
      }
    }
  }

  grouping mup-adj-rib-out {
    description
      "Structural grouping for MUP adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

        uses bgp-mup-loc-rib-key-refs;

        container state {
          description
            "Operational state data for BGP Adj-RIB entries";

          leaf prefix {
            type string;
            description
              "The MUP prefix corresponding to the route";
          }

          leaf origin {
            type arc-bgp-types:bgp-rib-origin-type;
            description
              "The origin of the route";
          }

          uses arc-bgp-types:bgp-adj-rib-attr-state;

          uses bgp-rib-ag-adj-rib-common-attr-refs;

          uses oc-rib-bgp:bgp-common-route-annotations-state;


        }

        uses bgp-mup-route-top;
        uses bgp-loc-rib-pfcp-session-info;
        uses bgp-mup-route-filters-top;
        uses oc-rib-bgp:bgp-unknown-attr-top;
      }
    }
  }

  grouping mup-adj-rib-in-pre {
    description
      "Structural grouping for each MUP adj-RIB-in-pre table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-mup-adj-rib-in-key-refs;

        container state {
          description
            "Operational state data for BGP Adj-RIB entries";

          leaf prefix {
            type string;
            description
              "The MUP prefix corresponding to the route";
          }

          uses arc-bgp-types:bgp-adj-rib-attr-state;

          uses bgp-rib-ag-adj-rib-common-attr-refs;

          uses oc-rib-bgp:bgp-common-route-annotations-state;

        }

        uses bgp-mup-route-top;
        uses bgp-mup-route-filters-top;
        uses oc-rib-bgp:bgp-unknown-attr-top;
      }
    }
  }

  grouping mup-adj-rib-in-post {
    description
      "Common structural grouping for the MUP adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-mup-adj-rib-in-key-refs;

        container state {
          description
            "Operational state data for BGP Adj-RIB entries";

          leaf prefix {
            type string;
            description
              "The MUP prefix corresponding to the route";
          }

          uses arc-bgp-types:bgp-adj-rib-attr-state;

          uses bgp-rib-ag-adj-rib-common-attr-refs;

          uses oc-rib-bgp:bgp-common-route-annotations-state;

        }

        uses bgp-mup-route-top;
        uses bgp-mup-route-filters-top;
        uses oc-rib-bgp:bgp-unknown-attr-top;
      }
    }
  }

  grouping mup-adj-rib-top {
    description
      "Top-level grouping for Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }

        container adj-rib-in-pre {
          description
            "Per-neighbor table containing the NLRI updates
            received from the neighbor before any local input
            policy rules or filters have been applied.  This can
            be considered the 'raw' updates from the neighbor.";

          uses mup-adj-rib-in-pre;

        }

        container adj-rib-in-post {
          description
            "Per-neighbor table containing the paths received from
            the neighbor that are eligible for best-path selection
            after local input policy rules have been applied.";

          uses mup-adj-rib-in-post;
        }

        container adj-rib-out {
          description
            "Per-neighbor table containing prefixes that have been
            advertised to the neighbor without applying output policy
            rules for attributes and/or next-hop change";

          uses mup-adj-rib-out;
        }
      }
    }
  }

  //VPNv6 loc-rib and adj-rib
  grouping bgp-vpn-loc-rib-key-refs-v6 {
    description
      "Key references to support operational state structure for
      the BGP VPNv6 LOC-RIB tables";

    leaf prefix {
      type leafref {
        path "../state/prefix";
      }
      description
        "Reference to the prefix list key";
    }

    leaf origin {
      type leafref {
        path "../state/origin";
      }
      description
        "Reference to the origin list key";
    }

    leaf path-id {
      type leafref {
        path "../state/path-id";
      }
      description
        "Reference to the path-id list key";
    }
  }

  grouping bgp-vpn-adj-rib-in-key-refs-v6 {
    description
      "Key references to support operational state structure for
      the BGP VPNv6 adj-RIB-in tables";

    leaf prefix {
      type leafref {
        path "../state/prefix";
      }
      description
        "Reference to the prefix list key";
    }

    leaf path-id {
      type leafref {
        path "../state/path-id";
      }
      description
        "Reference to the path-id list key";
    }
  }

  grouping l3vpn-ipv6-loc-rib-top {
    description
      "Top-level grouping for VPNv6 routing tables";

    container loc-rib {
      config false;
      description
        "Container for the VPNv6 BGP LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-vpn-loc-rib-key-refs-v6;

          container state {
            description
              "Operational state data for route entries in the
              BGP LOC-RIB";

            leaf prefix {
              type string;
              description
                "The VPNv6 prefix corresponding to the route";
            }

            uses arc-bgp-types:bgp-loc-rib-common-keys;

            uses bgp-loc-rib-local-label;

            uses bgp-rib-ag-loc-rib-common-attr-refs;

            uses oc-rib-bgp:bgp-loc-rib-attr-state;

            uses oc-rib-bgp:bgp-common-route-annotations-state;

            uses oc-rib-bgp:bgp-loc-rib-route-annotations-state;

            uses bgp-loc-rib-remote-label;

            uses bgp-loc-rib-redist-info;
          }

          uses oc-rib-bgp:bgp-unknown-attr-top;
        }
      }
    }
  }

  grouping l3vpn-ipv6-adj-rib-out {
    description
      "Structural grouping for VPNv6 adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

        uses bgp-vpn-loc-rib-key-refs-v6;

        container state {
          description
            "Operational state data for BGP Adj-RIB entries";

          leaf prefix {
            type string;
            description
              "The VPNv6 refix corresponding to the route";
          }

          leaf origin {
            type arc-bgp-types:bgp-rib-origin-type;
            description
              "The origin of the route";
          }

          uses bgp-loc-rib-local-label;

          uses arc-bgp-types:bgp-adj-rib-attr-state;

          uses bgp-rib-ag-adj-rib-common-attr-refs;

          uses oc-rib-bgp:bgp-common-route-annotations-state;

          uses bgp-loc-rib-remote-label;

          uses bgp-loc-rib-redist-info;
        }

        uses oc-rib-bgp:bgp-unknown-attr-top;
      }
    }
  }

  grouping l3vpn-ipv6-adj-rib-in-pre {
    description
      "Structural grouping for each VPNv6 adj-RIB-in-pre table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-vpn-adj-rib-in-key-refs-v6;

        container state {
          description
            "Operational state data for BGP Adj-RIB entries";

          leaf prefix {
            type string;
            description
              "The VPNv6 prefix corresponding to the route";
          }

          uses bgp-loc-rib-local-label;

          uses arc-bgp-types:bgp-adj-rib-attr-state;

          uses bgp-rib-ag-adj-rib-common-attr-refs;

          uses oc-rib-bgp:bgp-common-route-annotations-state;

          uses bgp-loc-rib-remote-label;
        }

        uses oc-rib-bgp:bgp-unknown-attr-top;
      }
    }
  }

  grouping l3vpn-ipv6-adj-rib-in-post {
    description
      "Common structural grouping for the VPNv6 adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-vpn-adj-rib-in-key-refs-v6;

        container state {
          description
            "Operational state data for BGP Adj-RIB entries";

          leaf prefix {
            type string;
            description
              "The VPNv6 prefix corresponding to the route";
          }

          uses bgp-loc-rib-local-label;

          uses arc-bgp-types:bgp-adj-rib-attr-state;

          uses bgp-rib-ag-adj-rib-common-attr-refs;

          uses oc-rib-bgp:bgp-common-route-annotations-state;

          uses bgp-loc-rib-remote-label;
        }

        uses oc-rib-bgp:bgp-unknown-attr-top;
      }
    }
  }

  grouping l3vpn-ipv6-adj-rib-top {
    description
      "Top-level grouping for Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }

        container adj-rib-in-pre {
          description
            "Per-neighbor table containing the NLRI updates
            received from the neighbor before any local input
            policy rules or filters have been applied.  This can
            be considered the 'raw' updates from the neighbor.";

          uses l3vpn-ipv6-adj-rib-in-pre;
        }

        container adj-rib-in-post {
          description
            "Per-neighbor table containing the paths received from
            the neighbor that are eligible for best-path selection
            after local input policy rules have been applied.";

          uses l3vpn-ipv6-adj-rib-in-post;
        }

        container adj-rib-out {
          description
            "Per-neighbor table containing prefixes that have been
            advertised to the neighbor without applying output policy
            rules for attributes and/or next-hop change";

          uses l3vpn-ipv6-adj-rib-out;
        }

        uses l3vpn-ipv6-ni-exported-adj-rib-out-top;
      }
    }
  }
  
  grouping bgp-flowspec-loc-rib-key-refs-v6 {
    description
      "Key references to support operational state structure for
      the BGP Flowspec IPv6 LOC-RIB tables";

    leaf prefix {
      type leafref {
        path "../state/prefix";
      }
      description
        "Reference to the prefix list key";
    }

    leaf origin {
      type leafref {
        path "../state/origin";
      }
      description
        "Reference to the origin list key";
    }

    leaf path-id {
      type leafref {
        path "../state/path-id";
      }
      description
        "Reference to the path-id list key";
    }
  }

  grouping bgp-flowspec-adj-rib-in-key-refs-v6 {
    description
      "Key references to support operational state structure for
      the BGP Flowspec IPv6 adj-RIB-in tables";

    leaf prefix {
      type leafref {
        path "../state/prefix";
      }
      description
        "Reference to the prefix list key";
    }

    leaf path-id {
      type leafref {
        path "../state/path-id";
      }
      description
        "Reference to the path-id list key";
    }
  }

  grouping ipv6-flowspec-loc-rib-top {
    description
      "Top-level grouping for Flowspec IPv6 routing tables";

    container loc-rib {
      config false;
      description
        "Container for the Flowspec IPv6 BGP LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-flowspec-loc-rib-key-refs-v6;

          container state {
            description
              "Operational state data for route entries in the
              BGP LOC-RIB";

            leaf prefix {
              type string;
              description
                "The Flowspec IPv6 prefix corresponding to the route";
            }

            uses arc-bgp-types:bgp-loc-rib-common-keys;
            uses bgp-rib-ag-loc-rib-common-attr-refs;
            uses oc-rib-bgp:bgp-loc-rib-attr-state;
            uses oc-rib-bgp:bgp-common-route-annotations-state;
            uses oc-rib-bgp:bgp-loc-rib-route-annotations-state;
          }

          uses oc-rib-bgp:bgp-unknown-attr-top;
        }
      }
    }
  }

  grouping ipv6-flowspec-adj-rib-out {
    description
      "Structural grouping for Flowspec IPv6 adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

          uses bgp-flowspec-loc-rib-key-refs-v6;

        container state {
          description
            "Operational state data for BGP Adj-RIB entries";

          leaf prefix {
            type string;
            description
              "The Flowspec IPv6 refix corresponding to the route";
          }

          leaf origin {
            type arc-bgp-types:bgp-rib-origin-type;
            description
              "The origin of the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping ipv6-flowspec-adj-rib-in-pre {
    description
      "Structural grouping for each Flowspec IPv6 adj-RIB-in-pre table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-flowspec-adj-rib-in-key-refs-v6;

        container state {
          description
            "Operational state data for BGP Adj-RIB entries";

          leaf prefix {
            type string;
            description
              "The Flowspec IPv6 prefix corresponding to the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping ipv6-flowspec-adj-rib-in-post {
    description
      "Common structural grouping for the Flowspec IPv6 adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-flowspec-adj-rib-in-key-refs-v6;

        container state {
          description
            "Operational state data for BGP Adj-RIB entries";

          leaf prefix {
            type string;
            description
              "The Flowspec IPv6 prefix corresponding to the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping ipv6-flowspec-adj-rib-top {
    description
      "Top-level grouping for Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }
        
        container adj-rib-in-pre {
          description
            "Per-neighbor table containing the NLRI updates
            received from the neighbor before any local input
            policy rules or filters have been applied.  This can
            be considered the 'raw' updates from the neighbor.";

          uses ipv6-flowspec-adj-rib-in-pre;

        }

        container adj-rib-in-post {
          description
            "Per-neighbor table containing the paths received from
            the neighbor that are eligible for best-path selection
            after local input policy rules have been applied.";

          uses ipv6-flowspec-adj-rib-in-post;
        }

        container adj-rib-out {
          description
            "Per-neighbor table containing prefixes that have been
            advertised to the neighbor without applying output policy
            rules for attributes and/or next-hop change";

          uses ipv6-flowspec-adj-rib-out;
        }
      }
    }
  }

  grouping l3vpn-ipv6-flowspec-loc-rib-top {
    description
      "Top-level grouping for Flowspec VPNv6 routing tables";

    container loc-rib {
      config false;
      description
        "Container for the Flowspec VPNv6 BGP LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-flowspec-loc-rib-key-refs-v6;

          container state {
            description
              "Operational state data for route entries in the
              BGP LOC-RIB";

            leaf prefix {
              type string;
              description
                "The Flowspec IPv6 prefix corresponding to the route";
            }

            uses arc-bgp-types:bgp-loc-rib-common-keys;
            uses bgp-rib-ag-loc-rib-common-attr-refs;
            uses oc-rib-bgp:bgp-loc-rib-attr-state;
            uses oc-rib-bgp:bgp-common-route-annotations-state;
            uses oc-rib-bgp:bgp-loc-rib-route-annotations-state;
          }

          uses oc-rib-bgp:bgp-unknown-attr-top;
        }
      }
    }
  }

  grouping l3vpn-ipv6-flowspec-adj-rib-out {
    description
      "Structural grouping for Flowspec VPNv6 adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

          uses bgp-flowspec-loc-rib-key-refs-v6;

        container state {
          description
            "Operational state data for BGP Adj-RIB entries";

          leaf prefix {
            type string;
            description
              "The Flowspec IPv6 refix corresponding to the route";
          }

          leaf origin {
            type arc-bgp-types:bgp-rib-origin-type;
            description
              "The origin of the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping l3vpn-ipv6-flowspec-adj-rib-in-pre {
    description
      "Structural grouping for each Flowspec VPNv6 adj-RIB-in-pre table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-flowspec-adj-rib-in-key-refs-v6;

        container state {
          description
            "Operational state data for BGP Adj-RIB entries";

          leaf prefix {
            type string;
            description
              "The Flowspec IPv6 prefix corresponding to the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping l3vpn-ipv6-flowspec-adj-rib-in-post {
    description
      "Common structural grouping for the Flowspec VPNv6 adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-flowspec-adj-rib-in-key-refs-v6;

        container state {
          description
            "Operational state data for BGP Adj-RIB entries";

          leaf prefix {
            type string;
            description
              "The Flowspec IPv6 prefix corresponding to the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping l3vpn-ipv6-flowspec-adj-rib-top {
    description
      "Top-level grouping for Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }
        
        container adj-rib-in-pre {
          description
            "Per-neighbor table containing the NLRI updates
            received from the neighbor before any local input
            policy rules or filters have been applied.  This can
            be considered the 'raw' updates from the neighbor.";

          uses l3vpn-ipv6-flowspec-adj-rib-in-pre;

        }

        container adj-rib-in-post {
          description
            "Per-neighbor table containing the paths received from
            the neighbor that are eligible for best-path selection
            after local input policy rules have been applied.";

          uses l3vpn-ipv6-flowspec-adj-rib-in-post;
        }

        container adj-rib-out {
          description
            "Per-neighbor table containing prefixes that have been
            advertised to the neighbor without applying output policy
            rules for attributes and/or next-hop change";

          uses l3vpn-ipv6-flowspec-adj-rib-out;
        }
      }
    }
  }

  /* SRTE Policy IPv4 loc-rib and adj-rib */
  grouping bgp-srte-loc-rib-key-refs-v4 {
    description
      "Key references to support operational state structure for
      the BGP SRTE Policy IPv4 LOC-RIB tables";

    leaf prefix {
      type leafref {
        path "../state/prefix";
      }
      description
        "Reference to the prefix list key";
    }

    leaf origin {
      type leafref {
        path "../state/origin";
      }
      description
        "Reference to the origin list key";
    }

    leaf path-id {
      type leafref {
        path "../state/path-id";
      }
      description
        "Reference to the path-id list key";
    }
  }

  grouping bgp-srte-adj-rib-in-key-refs-v4 {
    description
      "Key references to support operational state structure for
      the BGP SRTE Policy IPv4 adj-RIB-in tables";

    leaf prefix {
      type leafref {
        path "../state/prefix";
      }
      description
        "Reference to the prefix list key";
    }

    leaf path-id {
      type leafref {
        path "../state/path-id";
      }
      description
        "Reference to the path-id list key";
    }
  }

  grouping srte-policy-ipv4-loc-rib-top {
    description
      "Top-level grouping for SRTE Policy IPv4 routing tables";

    container loc-rib {
      config false;
      description
        "Container for the SRTE Policy IPv4 BGP LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-srte-loc-rib-key-refs-v4;

          container state {
            description
              "Operational state data for route entries in the
              BGP LOC-RIB";

            leaf prefix {
              type string;
              description
                "The SRTE Policy IPv4 prefix corresponding to the route";
            }

            uses arc-bgp-types:bgp-loc-rib-common-keys;
            uses bgp-rib-ag-loc-rib-common-attr-refs;
            uses oc-rib-bgp:bgp-loc-rib-attr-state;
            uses oc-rib-bgp:bgp-common-route-annotations-state;
            uses oc-rib-bgp:bgp-loc-rib-route-annotations-state;
          }

          uses oc-rib-bgp:bgp-unknown-attr-top;
        }
      }
    }
  }

  grouping srte-policy-ipv4-adj-rib-out {
    description
      "Structural grouping for SRTE Policy IPv4 adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

          uses bgp-srte-loc-rib-key-refs-v4;

        container state {
          description
            "Operational state data for BGP Adj-RIB entries";

          leaf prefix {
            type string;
            description
              "The SRTE Policy IPv4 prefix corresponding to the route";
          }

          leaf origin {
            type arc-bgp-types:bgp-rib-origin-type;
            description
              "The origin of the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping srte-policy-ipv4-adj-rib-in-pre {
    description
      "Structural grouping for each SRTE Policy IPv4 adj-RIB-in-pre table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-srte-adj-rib-in-key-refs-v4;

        container state {
          description
            "Operational state data for BGP Adj-RIB entries";

          leaf prefix {
            type string;
            description
              "The SRTE Policy IPv4 prefix corresponding to the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping srte-policy-ipv4-adj-rib-in-post {
    description
      "Common structural grouping for the SRTE Policy IPv4 adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-srte-adj-rib-in-key-refs-v4;

        container state {
          description
            "Operational state data for BGP Adj-RIB entries";

          leaf prefix {
            type string;
            description
              "The SRTE Policy IPv4 prefix corresponding to the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping srte-policy-ipv4-adj-rib-top {
    description
      "Top-level grouping for Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }

        container adj-rib-in-pre {
          description
            "Per-neighbor table containing the NLRI updates
            received from the neighbor before any local input
            policy rules or filters have been applied.  This can
            be considered the 'raw' updates from the neighbor.";

          uses srte-policy-ipv4-adj-rib-in-pre;
        }

        container adj-rib-in-post {
          description
            "Per-neighbor table containing the paths received from
            the neighbor that are eligible for best-path selection
            after local input policy rules have been applied.";

          uses srte-policy-ipv4-adj-rib-in-post;
        }

        container adj-rib-out {
          description
            "Per-neighbor table containing prefixes that have been
            advertised to the neighbor without applying output policy
            rules for attributes and/or next-hop change";

          uses srte-policy-ipv4-adj-rib-out;
        }
      }
    }
  }
  
    /* SRTE Policy IPv6 loc-rib and adj-rib */
  grouping bgp-srte-loc-rib-key-refs-v6 {
    description
      "Key references to support operational state structure for
      the BGP SRTE Policy IPv6 LOC-RIB tables";

    leaf prefix {
      type leafref {
        path "../state/prefix";
      }
      description
        "Reference to the prefix list key";
    }

    leaf origin {
      type leafref {
        path "../state/origin";
      }
      description
        "Reference to the origin list key";
    }

    leaf path-id {
      type leafref {
        path "../state/path-id";
      }
      description
        "Reference to the path-id list key";
    }
  }

  grouping bgp-srte-adj-rib-in-key-refs-v6 {
    description
      "Key references to support operational state structure for
      the BGP SRTE Policy IPv6 adj-RIB-in tables";

    leaf prefix {
      type leafref {
        path "../state/prefix";
      }
      description
        "Reference to the prefix list key";
    }

    leaf path-id {
      type leafref {
        path "../state/path-id";
      }
      description
        "Reference to the path-id list key";
    }
  }
  
  grouping srte-policy-ipv6-loc-rib-top {
    description
      "Top-level grouping for SRTE Policy IPv6 routing tables";

    container loc-rib {
      config false;
      description
        "Container for the SRTE Policy IPv6 BGP LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-srte-loc-rib-key-refs-v6;

          container state {
            description
              "Operational state data for route entries in the
              BGP LOC-RIB";

            leaf prefix {
              type string;
              description
                "The SRTE Policy IPv6 prefix corresponding to the route";
            }

            uses arc-bgp-types:bgp-loc-rib-common-keys;
            uses bgp-rib-ag-loc-rib-common-attr-refs;
            uses oc-rib-bgp:bgp-loc-rib-attr-state;
            uses oc-rib-bgp:bgp-common-route-annotations-state;
            uses oc-rib-bgp:bgp-loc-rib-route-annotations-state;
          }

          uses oc-rib-bgp:bgp-unknown-attr-top;
        }
      }
    }
  }

  grouping srte-policy-ipv6-adj-rib-out {
    description
      "Structural grouping for SRTE Policy IPv6 adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

          uses bgp-srte-loc-rib-key-refs-v6;

        container state {
          description
            "Operational state data for BGP Adj-RIB entries";

          leaf prefix {
            type string;
            description
              "The SRTE Policy IPv6 prefix corresponding to the route";
          }

          leaf origin {
            type inet:ip-address-no-zone;
            description
              "The origin of the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping srte-policy-ipv6-adj-rib-in-pre {
    description
      "Structural grouping for each SRTE Policy IPv6 adj-RIB-in-pre table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-srte-adj-rib-in-key-refs-v6;

        container state {
          description
            "Operational state data for BGP Adj-RIB entries";

          leaf prefix {
            type string;
            description
              "The SRTE Policy IPv6 prefix corresponding to the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping srte-policy-ipv6-adj-rib-in-post {
    description
      "Common structural grouping for the SRTE Policy IPv6 adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-srte-adj-rib-in-key-refs-v6;

        container state {
          description
            "Operational state data for BGP Adj-RIB entries";

          leaf prefix {
            type string;
            description
              "The SRTE Policy IPv6 prefix corresponding to the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping srte-policy-ipv6-adj-rib-top {
    description
      "Top-level grouping for Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }

        container adj-rib-in-pre {
          description
            "Per-neighbor table containing the NLRI updates
            received from the neighbor before any local input
            policy rules or filters have been applied.  This can
            be considered the 'raw' updates from the neighbor.";

          uses srte-policy-ipv6-adj-rib-in-pre;
        }

        container adj-rib-in-post {
          description
            "Per-neighbor table containing the paths received from
            the neighbor that are eligible for best-path selection
            after local input policy rules have been applied.";

          uses srte-policy-ipv6-adj-rib-in-post;
        }

        container adj-rib-out {
          description
            "Per-neighbor table containing prefixes that have been
            advertised to the neighbor without applying output policy
            rules for attributes and/or next-hop change";

          uses srte-policy-ipv6-adj-rib-out;
        }
      }
    }
  }

  /* RTFILTER loc-rib and adj-rib */
  grouping bgp-rtfilter-loc-rib-key-refs {
    description
      "Key references to support operational state structure for
      the BGP RTFILTER LOC-RIB tables";

    leaf prefix {
      type leafref {
        path "../state/prefix";
      }
      description
        "Reference to the prefix list key";
    }

    leaf origin {
      type leafref {
        path "../state/origin";
      }
      description
        "Reference to the origin list key";
    }

    leaf path-id {
      type leafref {
        path "../state/path-id";
      }
      description
        "Reference to the path-id list key";
    }
  }

  grouping bgp-rtfilter-adj-rib-in-key-refs {
    description
      "Key references to support operational state structure for
      the BGP RTFILTER adj-RIB-in tables";

    leaf prefix {
      type leafref {
        path "../state/prefix";
      }
      description
        "Reference to the prefix list key";
    }

    leaf path-id {
      type leafref {
        path "../state/path-id";
      }
      description
        "Reference to the path-id list key";
    }
  }

  grouping bgp-rtfilter-loc-rib-top {
    description
      "Top-level grouping for RTFILTER Loc-RIB";

    container loc-rib {
      config false;
      description
        "Container for the BGP RTFILTER LOC-RIB data";

      uses oc-rib-bgp:bgp-common-table-attrs-top;

      container routes {
        description
          "Enclosing container for list of routes in the routing
          table.";

        list route {
          key "prefix origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          uses bgp-rtfilter-loc-rib-key-refs;

          container state {
            description
              "Operational state data for route entries in the
              BGP LOC-RIB";

            leaf prefix {
              type string;
              description
                "The RTFILTER prefix corresponding to the route";
            }

            uses arc-bgp-types:bgp-loc-rib-common-keys;

            uses bgp-rib-ag-loc-rib-common-attr-refs;

            uses oc-rib-bgp:bgp-loc-rib-attr-state;

            uses oc-rib-bgp:bgp-common-route-annotations-state;

            uses oc-rib-bgp:bgp-loc-rib-route-annotations-state;
          }

          uses oc-rib-bgp:bgp-unknown-attr-top;
        }
      }
    }
  }

  grouping bgp-rtfilter-adj-rib-out {
    description
      "Structural grouping for RTFILTER adj-RIB-out table";

    uses oc-rib-bgp:bgp-common-table-attrs-top;

    container routes {
      config false;
      description
        "Enclosing container for list of routes in the routing
        table.";

      list route {
        key "prefix origin path-id";

        description
          "List of routes in the table, keyed by a combination of
          the route prefix and path-id to distinguish multiple
          routes received from a neighbor for the same prefix,
          e.g., when BGP add-paths is enabled.";

        uses bgp-rtfilter-loc-rib-key-refs;

        container state {
          description
            "Operational state data for BGP Adj-RIB entries";

          leaf prefix {
            type string;
            description
              "The RTFILTER prefix corresponding to the route";
          }

          leaf origin {
            type inet:ip-address-no-zone;
            description
              "The origin of the route";
          }

          uses arc-bgp-types:bgp-adj-rib-attr-state;

          uses bgp-rib-ag-adj-rib-common-attr-refs;

          uses oc-rib-bgp:bgp-common-route-annotations-state;
        }

        uses oc-rib-bgp:bgp-unknown-attr-top;
      }
    }
  }

  grouping bgp-rtfilter-adj-rib-in-pre {
    description
      "Structural grouping for each RTFILTER adj-RIB-in-pre table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-rtfilter-adj-rib-in-key-refs;

        container state {
          description
            "Operational state data for BGP Adj-RIB entries";

          leaf prefix {
            type string;
            description
              "The RTFILTER prefix corresponding to the route";
          }

          uses arc-bgp-types:bgp-adj-rib-attr-state;

          uses bgp-rib-ag-adj-rib-common-attr-refs;

          uses oc-rib-bgp:bgp-common-route-annotations-state;
        }

        uses oc-rib-bgp:bgp-unknown-attr-top;
      }
    }
  }

  grouping bgp-rtfilter-adj-rib-in-post {
    description
      "Common structural grouping for the RTFILTER adj-rib-in
      post-policy table";

    uses oc-rib-bgp:bgp-common-table-attrs-top;

    container routes {
      config false;
      description
        "Enclosing container for list of routes in the routing
        table.";

      list route {
        key "prefix path-id";

        description
          "List of routes in the table, keyed by a combination of
          the route prefix and path-id to distinguish multiple
          routes received from a neighbor for the same prefix,
          e.g., when BGP add-paths is enabled.";

        uses bgp-rtfilter-adj-rib-in-key-refs;

        container state {
          description
            "Operational state data for BGP Adj-RIB entries";

          leaf prefix {
            type string;
            description
              "The RTFILTER prefix corresponding to the route";
          }

          uses arc-bgp-types:bgp-adj-rib-attr-state;

          uses bgp-rib-ag-adj-rib-common-attr-refs;

          uses oc-rib-bgp:bgp-common-route-annotations-state;
        }

        uses oc-rib-bgp:bgp-unknown-attr-top;
      }
    }
  }

  grouping bgp-rtfilter-adj-rib-top {
    description
      "Top-level grouping for Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type leafref {
              path "/oc-ni:network-instances/oc-ni:network-instance" +
                   "/oc-ni:protocols/oc-ni:protocol" +
                   "/oc-ni:bgp" +
                   "/oc-ni:neighbors/oc-ni:neighbor" +
                   "/oc-ni:neighbor-address";
            }
            description
              "IP address of the BGP neighbor or peer";
          }
        }

        container adj-rib-in-post {
          description
            "Per-neighbor table containing the paths received from
            the neighbor that are eligible for best-path selection
            after local input policy rules have been applied.";

          uses bgp-rtfilter-adj-rib-in-post;
        }

        container adj-rib-out {
          description
            "Per-neighbor table containing prefixes that have been
            advertised to the neighbor without applying output policy
            rules for attributes and/or next-hop change";

          uses bgp-rtfilter-adj-rib-out;
        }
      }
    }
  }

  identity PATH_TYPE {
    description "Base identity for BGP path type.";
  }

  identity AGGREGATE_SUPPRESSED_PATH {
    base PATH_TYPE;
    description "Aggregate suppressed path.";
  }
  
  identity BEST_PATH {
    base PATH_TYPE;
    description "Best path.";
  }

  identity SECOND_BEST_PATH {
    base PATH_TYPE;
    description "Second best path.";
  }

  identity BACKUP_PATH {
    base PATH_TYPE;
    description "Backup path.";
  }

  identity BEST_EXTERNAL_PATH {
    base PATH_TYPE;
    description "Best-external path.";
  }

  identity MULTI_PATH {
    base PATH_TYPE;
    description "Multiple path.";
  }

  identity OLD_BEST_PATH {
    base PATH_TYPE;
    description "Old best path.";
  }

  identity OLD_MULTI_PATH {
    base PATH_TYPE;
    description "Old multiple path.";
  }

  identity LOCAL_NETWORK {
     base PATH_TYPE;
     description "Local path added using network command.";
  }

  identity LOCAL_REDISTRIBUTED {
    base PATH_TYPE;
    description "Local redistributed path.";
  }

  identity LOCAL_AGGREGATE {
    base PATH_TYPE;
    description "Local aggregate path.";
  }

  identity LOCAL_MUP {
    base PATH_TYPE;
    description "Local path added by MUP SAFI.";
  }

  identity CONTROLLER_PATH {
    base PATH_TYPE;
    description "Controller path.";
  }

  identity IMPORT_SOURCE_PATH {
    base PATH_TYPE;
    description "Import source path.";
  }

  identity IMPORTED_PATH {
    base PATH_TYPE;
    description "Imported path.";
  }

  identity EXPORT_SOURCE_PATH {
    base PATH_TYPE;
    description "Export source path.";
  }

  identity EXPORTED_PATH {
    base PATH_TYPE;
    description "Exported path.";
  }

  identity REIMPORT_PATH {
    base PATH_TYPE;
    description "Reimported source/target path.";
  }

  identity REORIG_MUP_ST1_PATH {
    base PATH_TYPE;
    description "Reoriginated MUP ST1 path.";
  }

  identity DELETED_PATH {
    base PATH_TYPE;
    description "Deleted path.";
  }

  identity VPWS_LOCAL_SWITCHING {
    base PATH_TYPE;
    description "EVPN VPWS local-switching path.";
  }

  identity PATH_LIST {
    description "Base identity for BGP path list.";
  }

  identity UPDATE_PATH_LIST {
    base PATH_LIST;
    description "Update path list.";
  }

  identity L3VPN_UPDATE_PATH_LIST {
    base PATH_LIST;
    description "Update path list.";
  }

  identity LABEL_PATH_LIST {
    base PATH_LIST;
    description "Label path list.";
  }

  identity BEST_PATH_LIST {
    base PATH_LIST;
    description "Best path list.";
  }

  identity RIB_PATH_LIST {
    base PATH_LIST;
    description "RIB path list.";
  }

  identity NEXT_HOP_PATH_LIST {
    base PATH_LIST;
    description "Next hop path list.";
  }
  
  /*
   * Augment invalid-route-reasons.
   */
  identity BEST_PATH_PENDING {
    base oc-ribbgp-types:INVALID_ROUTE_REASON;
    description
      "Route was invalid due to best path calculation is not run yet";
  }
 
  identity REJECTED_IMPORT_POLICY {
    base oc-ribbgp-types:INVALID_ROUTE_REASON;
    description
      "Route was rejected after apply import policies";
  }

  identity NEXT_HOP_UNREACHABLE {
    base oc-ribbgp-types:INVALID_ROUTE_REASON;
    description
      "Route was invalid due to next-hop unreachable";
  }

  identity IMPORT_ERPL_PENDING {
    base oc-ribbgp-types:INVALID_ROUTE_REASON;
    description
      "Route was invalid due to import eRPL pending";
  }

  identity NO_PER_NEXTHOP_LABEL {
    base oc-ribbgp-types:INVALID_ROUTE_REASON;
    description
      "Route was invalid due to invalid per-nexthop label";
  }

  identity NO_PER_PREFIX_LABEL {
    base oc-ribbgp-types:INVALID_ROUTE_REASON;
    description
      "Route was invalid due to invalid per-prefix label";
  }

  identity NO_REMOTE_SID {
    base oc-ribbgp-types:INVALID_ROUTE_REASON;
    description
      "Route was invalid due to invalid remote service ID";
  }

  identity L2_MTU_MISMATCHED {
    base oc-ribbgp-types:INVALID_ROUTE_REASON;
    description
      "Route was invalid due to L2 MTU mismatched";
  }

  identity LOCAL_AC_DOWN {
    base oc-ribbgp-types:INVALID_ROUTE_REASON;
    description
      "Route was invalid due to local AC in down state";
  }

  identity CONTROL_WORD_MISMATCH {
    base oc-ribbgp-types:INVALID_ROUTE_REASON;
    description
      "Route was invalid due to local and remote control word mismatch";
  }

  identity MARTIAN {
    base oc-ribbgp-types:INVALID_ROUTE_REASON;
    description
      "Route was rejected as martian";
  }

  identity FLOW_LABEL_MISMATCH {
    base oc-ribbgp-types:INVALID_ROUTE_REASON;
    description
      "Route was invalid due to local and remote flow label mismatch";
  }

  identity INVALID_ATTR {
    base oc-ribbgp-types:INVALID_ROUTE_REASON;
    description
      "Route was invalid due to an invalid attribute";
  }

  grouping rib-out-top {
    leaf neighbor-count {
      type uint32;
    }
    leaf-list neighbors {
      type string;
    }
  }

  identity ORIGIN_VALIDATION_STATE {
    description "Base identity for BGP prefix origin validation state";
    reference "RFC 6811";
  }

  identity NONE {
    base ORIGIN_VALIDATION_STATE;
    description
      "Origin validation not performed yet";
  }

  identity NOT_FOUND {
    base ORIGIN_VALIDATION_STATE;
    description
      "No VRP Covers the Route Prefix (RFC 6811)";
  }

  identity VALID {
    base ORIGIN_VALIDATION_STATE;
    description
      "At least one VRP Matches the Route Prefix (RFC 6811)";
  }

  identity INVALID {
    base ORIGIN_VALIDATION_STATE;
    description
      "At least one VRP Covers the Route Prefix, but no VRP Matches it
      (RFC 6811)";
  }

  grouping loc-rib-large-community-index-top {
    leaf large-community-index {
      type leafref {
        path "../../../../../../../../arc-oc-rib-bgp-aug:large-communities" +
             "/arc-oc-rib-bgp-aug:large-community/arc-oc-rib-bgp-aug:state/arc-oc-rib-bgp-aug:index";
      }
      description
        "Reference to the large community attribute for the route";
    }
  }

  grouping adj-rib-large-community-index-top {
    leaf large-community-index {
      type leafref {
        path "../../../../../../../../../../arc-oc-rib-bgp-aug:large-communities" +
             "/arc-oc-rib-bgp-aug:large-community/arc-oc-rib-bgp-aug:state/arc-oc-rib-bgp-aug:index";
      }
      description
        "Reference to the large community attribute for the route";
    }
  }

  grouping adj-rib-ni-large-community-index-top {
    leaf large-community-index {
      type leafref {
        path "../../../../../../../../../../../../arc-oc-rib-bgp-aug:large-communities" +
             "/arc-oc-rib-bgp-aug:large-community/arc-oc-rib-bgp-aug:state/arc-oc-rib-bgp-aug:index";
      }
      description
        "Reference to the large community attribute for the route";
    }
  }

  grouping route-top {
    leaf next-hop {
      type inet:ip-address;
      description "Path next hop";
    }

    leaf srv6-sid-next-hop {
      description "SID next hop";
      type inet:ipv6-address;
    }

    leaf link-local-next-hop {
      type inet:ip-address;
      description "Path link local next hop";
    }

    leaf next-hop-id {
      type string;
      description "Next-hop ID in RIB";
    }

    leaf allocated-next-hop-label {
      type uint32;
      description "Local label allocated for the nexthop address";
    }

    leaf allocated-next-hop-srv6-sid {
      type inet:ipv6-address;
      description "Local SRv6 SID allocated for the nexthop address";
    }

    leaf next-hop-srv6-oam-state {
      type identityref {
        base arc-oc-bgp-types:SRV6_OAM_STATES;
      }
      description "Path next hop OAM health state for SRv6";
    }

    leaf not-best-path-reason {
      type string;
      description "The reason if the path is not selected as best-path";
    }

    container versions {
      description "Path version numbers";
      leaf path-version {
        type uint64;
        description
         "Path version";
      }
    }

    leaf tx-path-id {
      type uint32;
      default 0;
      description
        "If the route is learned from a neighbor, the tx-path-id
        corresponds to the locally assigned path-id for the route.";
    }

    leaf path-index {
      type uint64;
      description
        "Locally assigned path-index for the path.";
    }

    leaf-list path-types {
      description "Path types.";
      type identityref {
        base PATH_TYPE;
      }
    }

    leaf-list path-lists {
      description "Path lists.";
      type identityref {
        base PATH_LIST;
      }
    }

    container rib-outs {
      description "RIB outs.";
      container best-path {
        description "Best path RIB out.";
        uses rib-out-top;
      }
      container add-path {
        description "Add path RIB out.";
        uses rib-out-top;
      }
    }

    leaf stale-route {
      type boolean;
      description
        "Indicate that the route is marked as stale in graceful-restart
        procedures for the receiving speaker";
    }

    leaf origin-validation {
      type identityref {
        base ORIGIN_VALIDATION_STATE;
      }
      description
        "BGP prefix origin validation state.";
    }

    leaf auto-inbound-soft-reconfiguration {
      type boolean;
      description
        "BGP prefix is selected for auto inbound soft reconfiguration";
    }

    leaf path-flags {
      type uint64;
      description
        "BGP internal path flags.";
    }

    leaf nlri-flags {
      type uint32;
      description
        "BGP internal NLRI flags.";
    }

    leaf nlri-version {
      type uint64;
      description
        "BGP internal NLRI version number.";
    }

    leaf protection-tracker-id {
      type uint64;
      description
        "BGP path protection tracker ID.";
    }

    leaf nlri-rib-ack-pending {
      type boolean;
      description
        "BGP internal if NLRI is RIB ACK pending.";
    }

    leaf srv6-tunnel-id {
      type uint32;
      description
        "SRv6 Tunnel ID";
    }
  }

  grouping rib-in-pre-route-top {
    leaf next-hop {
      type inet:ip-address;
      description "Path next hop";
    }

    leaf srv6-sid-next-hop {
      description "SID next hop";
      type inet:ipv6-address;
    }

    leaf link-local-next-hop {
      type inet:ip-address;
      description "Path link local next hop";
    }

    leaf next-hop-id {
      type string;
      description "Next-hop Identifier";
    }

    leaf rib-next-hop {
      type string;
      description "Next-hop reference in RIB";
    }

    leaf origin-validation {
      type identityref {
        base ORIGIN_VALIDATION_STATE;
      }
      description
        "BGP prefix origin validation state.";
    }

    leaf auto-inbound-soft-reconfiguration {
      type boolean;
      description
        "BGP prefix is selected for auto inbound soft reconfiguration";
    }

    leaf path-flags {
      type uint64;
      description
        "BGP internal path flags.";
    }

    leaf nlri-flags {
      type uint32;
      description
        "BGP internal NLRI flags.";
    }

    leaf srv6-tunnel-id {
      type uint32;
      description
        "SRv6 Tunnel ID";
    }
  }

  grouping bgp-large-community-attr-top {
    description
      "Common definition of BGP Large Community attribute";

    leaf-list large-community {
       type arc-oc-bgp-types:bgp-large-community-type;
       description
         "List of BGP large community attributes.  The received
         extended community may be an explicitly modeled
         by 12 octet value formatted according to RFC 8092.";
       reference
         "RFC 8092 - BGP Large Communities Attribute";

    }
  }

  grouping pmsi-rsvp-te-p2mp {
    description
      "PMSI tunnel type RSVP
       Traffic Engineering Point-to-Multipoint Label Switched Path";

    container rsvp-te-p2mp {
      description
        "RSVP TE P2MP tunnel";

      leaf p2mp-id {
        type uint32;
        description
          "P2MP ID of the RSVP TE P2MP tunnel";
      }

      leaf tunnel-id {
        type uint16;
        description
          "Tunnel ID of the RSVP TE P2MP tunnel";
      }

      leaf extended-tunnel-id {
        type inet:ip-address;
        description
          "Extended tunnel ID of the RSVP TE P2MP Tunnel";
      }
    }
  }

  grouping pmsi-mldp-p2mp {
    description
      "PMSI MLDP P2MP tunnel";

    container mldp-p2mp {
      description
        "PMSI Tunnel type MLDP P2MP";

      leaf p2mp-type {
        type uint8;
        description
          "The type of the P2MP FEC element";
      }

      leaf afi {
        type uint16;
        description
          "IANAs address family";
      }

      leaf length {
        type uint8;
        description
          "Lenght of the root LSRs address";
      }

      leaf root-node-address {
        type inet:ip-address;
        description
          "Root node address";
      }
    }
  }

  grouping pmsi-pim-ssm {
    description
      "PMSI PIM SSM tunnel";

    container pim-ssm {
      description
        "PMSI tunnel type PIM SSM";

      leaf root-node-address {
        type inet:ip-address;
        description
          "root node address";
      }

      leaf mcast-group {
        type inet:ip-address;
        description
          "multicast group address";
      }
    }
  }

  grouping pmsi-pim-sm {
    description
      "PMSI PIM SM Tunnel";

    container pim-sm {
      description
        "PMSI tunnel type PIM SM";

      leaf sender-address {
        type inet:ip-address;
        description
          "sender address";
      }

      leaf mcast-group {
        type inet:ip-address;
        description
          "mmulticast group address";
      }
    }
  }

  grouping pmsi-pim-bidir {
    description
      "PMSI PIM BIDIR tunnel";

    container pim-bidir {
      description
        "PMSI tunnel type PIM BIDIR";

      leaf sender-address {
        type inet:ip-address;
        description
          "sender address";
      }

      leaf mcast-group {
        type inet:ip-address;
        description
          "mmulticast group address";
      }
    }
  }

  grouping pmsi-ingress-replication {
    description
      "PMSI ingress replication tunnel";

    container ingress-replication {
      description
        "PMSI tunnel type Ingress replication";

      leaf endpoint-address {
        type inet:ip-address;
        description
          "tunnel endpoint address";
      }
    }
  }

  grouping pmsi-mldp-mp2mp {
    description
      "PMSI MLDP MP2MP tunnel";

    container mldp-mp2mp {
      description
        "PMSI Tunnel type MLDP MP2MP";

      leaf mp2mp-type {
        type uint8;
        description
          "The type of the P2MP FEC element";
      }

      leaf afi {
        type uint16;
        description
          "IANAs address family";
      }

      leaf length {
        type uint8;
        description
          "Lenght of the root LSRs address";
      }

      leaf root-node-address {
        type inet:ip-address;
        description
          "Root node address";
      }
    }
  }

  grouping bgp-pmsi-tunnel-attr-top {
    description
      "High level Grouping for PMSI tunnel Attribute";

    container pmsi-tunnel-attr {
      description
        "Container for PMSI tunnel attribute";

        container state {
          description
            "Operational state for PMSI tunnel attribute";

          leaf flags {
            type uint8;
            description
              "PMSI Tunnel attr flags";
          }

          leaf tunnel-type {
            type uint8;
            description
              "PMSI attr tunnel type";
          }

          leaf mpls-label {
            type uint32;
            description
              "PMSI Tunnel attr MPLS label";
          }

          uses pmsi-rsvp-te-p2mp;
          uses pmsi-mldp-p2mp;
          uses pmsi-pim-ssm;
          uses pmsi-pim-sm;
          uses pmsi-pim-bidir;
          uses pmsi-ingress-replication;
          uses pmsi-mldp-mp2mp;
        }
    }
  }

  grouping srv6-service-data-top {
    description
      "Grouping for SRv6 service data sub-sub-TLVs";

    container sid-structure-sub-sub-tlv {
      description
        "SRv6 SID structure sub-sub-TLVs";

      container state {
        description
          "SRv6 SID structure state information";

        leaf locator-block-length {
          type uint8;
          description
            "SRv6 SID locator block length";
        }
        leaf locator-node-length {
          type uint8;
          description
            "SRv6 SID locator node length";
        }
        leaf function-length {
          type uint8;
          description
            "SRv6 SID function length";
        }
        leaf argument-length {
          type uint8;
          description
            "SRv6 SID aargument length";
        }
        leaf transposition-length {
          type uint8;
          description
            "SRv6 SID transposition length";
        }
        leaf transposition-offset {
          type uint8;
          description
            "SRv6 SID transposition offset";
        }
      }
    }
  }

  grouping srv6-l3-services-top {
    container srv6-l3-services {
      list srv6-l3-service {
        key "index";
        description
          "SRv6 SID information for L3 service";

        leaf index {
          type leafref {
            path "../state/index";
          }
          description
            "Reference to the list key";
        }

        container state {
          leaf index {
            type uint64;
            description
              "System generated index for each srv6 L3 service.";
          }

          leaf service-sid {
            description
              "Service SID information for SRv6 based L3 services";
            type inet:ipv6-address;
          }

          leaf endpoint-behavior {
            description
              "SRv6 endpoint behavior";
            type identityref {
              base arc-srv6-types:SRV6_ENDPOINT_BEHAVIOR_TYPE;
            }
          }
        }

        uses srv6-service-data-top;
      }
    }
  }

  grouping bgp-prefix-sid-attr-top {
    description
      "High level Grouping for Prefix SID Attribute";

    container prefix-sid-attr {
      description
        "Prefix SID attribute";

      container state {
        description
          "Operational state for Prefix SID attribute";

        leaf label-index {
          type uint32;
          description
            "Label index TLV carried with the prefix sid";
        }

        container originator-srgb {
          description
            "SRGB info of the originating node, as signaled in the originator SRGB TLV";

          leaf-list srgb-ranges {
            description
              "Concatenated ranges building the SRGB block";
            type string;
          }
        }
      }

      uses srv6-l3-services-top;
    }
  }

  grouping srv6-bindig-sid-subtlv-top {
    description
      "High level Grouping for Binding SID subtlv";

    container srv6-binding-sid-subtlv {
      description
        "SRV6 BSID attribute";

      container state {
        leaf srv6-binding-sid {
          description
            "BSID information for SR policy";
          type inet:ipv6-address;
        }

        // leaf flags {
        //   type uint8;
        //   description
        //     "sr policy Tunnel attr flags";
        // }

        leaf endpoint-behavior {
          description
            "SRv6 endpoint behavior";
          type identityref {
            base arc-srv6-types:SRV6_ENDPOINT_BEHAVIOR_TYPE;
          }
        }
        leaf locator-block-length {
          type uint8;
          description
            "SRv6 SID locator block length";
        }
        leaf locator-node-length {
          type uint8;
          description
            "SRv6 SID locator node length";
        }
        leaf function-length {
          type uint8;
          description
            "SRv6 SID function length";
        }
        leaf argument-length {
          type uint8;
          description
            "SRv6 SID aargument length";
        }
      }
    }
  }

  grouping tunnel-sr-policy-top {

    container tunnel-sr-policy {
      container state {
        description
          "Operational state for tunnel type SR Policy";

        leaf subtlv-type {
          type identityref {
            base oc-ribbgp-types:TUNNEL_ENCAPSULATION_SUBTLV_TYPE;
          }
          description
            "SR Policy Subtlv Type";
        }
      }

      description
        "SR policy tunnel information";
      uses srv6-bindig-sid-subtlv-top;
      // {
      //   when "state/subtlv-type='arc-oc-ribbgp-types:SRV6_SRTE_BINDING_SID'";
      // }
    }
  }

  grouping tunnel-egress-endpoint-top {
    description
      "High level Grouping for Tunnel Egress Endpoint subtlv";

    container tunnel-egress-endpoint-subtlv {
      description
        "Tunnel egress endpoint attribute";

      container state {
        leaf afi {
          description
            "Tunnel Egress Endpoint address AFI";
          type identityref {
            base oc-types:ADDRESS_FAMILY;
          }
        }

        leaf tunnel-egress-endpoint {
          description
            "Tunnel Egresss Endpoint address";
          type inet:ip-address-no-zone;
        }
      }
    }
  }

  grouping gtp-tunnel-top {

    container gtp-tunnel {
      container state {
        description
          "Operational state for GTP tunnel";

        leaf subtlv-type {
          type identityref {
            base oc-ribbgp-types:TUNNEL_ENCAPSULATION_SUBTLV_TYPE;
          }
          description
            "GTP Tunnel Subtlv Type";
        }
      }
      description
        "GTP Tunnel information";

      uses tunnel-egress-endpoint-top;
    }
  }

  grouping bgp-tunnel-encap-attr-top {
    description
      "High level Grouping for SRTE Policy encap tunnel Attribute";

    container tunnel-encap-attr {
      description
        "Container for tunnel encap attribute";
      container state {
        description
          "Operational state for tunnel encap attribute";

        leaf tunnel-type {
          type identityref {
            base oc-ribbgp-types:TUNNEL_ENCAPSULATION_TYPE;
          }
          description
            "Tunnel encap attr tunnel type";
        }
      }

      uses tunnel-sr-policy-top {
        when "state/tunnel-type='oc-ribbgp-types:SRTE_POLICY_TUNNEL'";
      }
      uses gtp-tunnel-top {
        when "state/tunnel-type='arc-oc-ribbgp-types:GTP_TUNNEL'";
      }
    }
  }

  grouping bgp-shared-common-attr-state {
    description
      "Route attributes shared across route table entries,
      common to both LOC-Rib and Adj-RIB";


    leaf origin {
      type oc-bgp-types:bgp-origin-attr-type;
      description
        "BGP attribute defining the origin of the path information.";
    }

    leaf atomic-aggregate {
      type boolean;
      description
        "BGP attribute indicating that the prefix is an atomic
        aggregate, i.e., the peer selected a less specific
        route without selecting a more specific route that is
        included in it.";
    }

    leaf med {
      type uint32;
      description
        "BGP multi-exit discriminator attribute used in BGP route
        selection process";
    }

    leaf local-pref {
      type uint32;
      description
        "BGP local preference attribute sent to internal peers to
        indicate the degree of preference for externally learned
        routes.  The route with the highest local preference value
        is preferred.";
    }

    leaf originator-id {
      type inet:ipv4-address;
      description
        "BGP attribute that provides the id as an IPv4 address
        of the originator of the announcement.";
      reference
        "RFC 4456 - BGP Route Reflection: An Alternative to Full
        Mesh Internal BGP (IBGP)";
    }

    leaf-list cluster-list {
      type inet:ipv4-address;
      description
        "Represents the reflection path that the route has passed.";
      reference
        "RFC 4456 - BGP Route Reflection: An Alternative to Full
        Mesh Internal BGP (IBGP)";
    }

    leaf aigp {
      type uint64;
      description
        "BGP path attribute representing the accumulated IGP metric
        for the path";
      reference
        "RFC 7311 - The Accumulated IGP Metric Attribute for BGP";
    }
  }

  grouping route-attr-set-top {
    container attributes {
      description
        "Path attributes for the route.";

      container state {
        config false;
        description
          "Operational state for common path attributes";

        uses bgp-shared-common-attr-state;
        uses attr-route-shared-top;
      }

      container community {
        description
          "Operational state for community attribute";

        container state {
          uses oc-rib-bgp:bgp-community-attr-state;
        }
      }

      container ext-community {
        description
          "Operational state for extended community attribute";

        container state {
          uses oc-rib-bgp:bgp-extended-community-attr-state;
        }
      }

      container large-community {
        description
          "Operational state for large community attribute";

        container state {
          uses bgp-large-community-attr-state;
        }
      }

      uses oc-rib-bgp:bgp-aggregator-attr-top;
      uses oc-rib-bgp:bgp-as-path-attr-top;
      uses oc-rib-bgp:bgp-as4-path-attr-top;
      uses bgp-pmsi-tunnel-attr-top;
      uses bgp-prefix-sid-attr-top;
      uses bgp-tunnel-encap-attr-top;
    }
  }

  /*
   * Add "adj-rib-out" with different keys than "adj-rib-out-pre" and
   * "adj-rib-out-post" in OC model.
   */
  grouping ipv4-adj-rib-out {
    description
      "Structural grouping for each IPv4 unicast adj-RIB-out table";

    uses oc-rib-bgp:bgp-common-table-attrs-top;

    container routes {
      config false;
      description
        "Enclosing container for list of routes in the routing
        table.";

      list route {
        key "prefix origin path-id";

        description
          "List of routes in the table, keyed by a combination of
          the route prefix, origin and path-id to distinguish multiple
          routes received from a neighbor for the same prefix,
          e.g., when BGP add-paths is enabled.";

        uses oc-rib-bgp:bgp-loc-rib-key-refs;

        container state {
          description
            "Operational state data for BGP Adj-RIB entries";

          leaf prefix {
            type inet:ipv4-prefix;
            description
              "Prefix for the route";
          }

          leaf origin {
            type arc-bgp-types:bgp-rib-origin-type;
            description
              "The origin of the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping ipv6-adj-rib-out {
    description
      "Structural grouping for each IPv6 unicast adj-RIB-out table";

    uses oc-rib-bgp:bgp-common-table-attrs-top;

    container routes {
      config false;
      description
        "Enclosing container for list of routes in the routing
        table.";

      list route {
        key "prefix origin path-id";

        description
          "List of routes in the table, keyed by a combination of
          the route prefix, origin and path-id to distinguish multiple
          routes received from a neighbor for the same prefix,
          e.g., when BGP add-paths is enabled.";

        uses oc-rib-bgp:bgp-loc-rib-key-refs-v6;

        container state {
          description
            "Operational state data for BGP Adj-RIB entries";

          leaf prefix {
            type inet:ipv6-prefix;
            description
              "Prefix for the route";
          }

          leaf origin {
            type arc-bgp-types:bgp-rib-origin-type;
            description
              "The origin of the route";
          }

          uses arc-bgp-types:bgp-adj-rib-attr-state;
          uses bgp-rib-ag-adj-rib-common-attr-refs;
          uses oc-rib-bgp:bgp-common-route-annotations-state;
        }

        uses oc-rib-bgp:bgp-unknown-attr-top;
      }
    }
  }

  grouping protection-tracker-top {
    description
      "Grouping for protection tracker information";
    container protection-trackers {
      config false;
      list protection-tracker {
        description
          "List of protection trackers";
        key "tracker-id";
        leaf "tracker-id" {
          type uint64;
          description
            "Protection tracker ID";
        }
        container state {
          leaf reference-count {
            type uint32;
            description
              "Reference count of users of this tracker";
          }
          leaf next-hop {
            type inet:ip-address-no-zone;
            description
              "Next hop address for primary path for tracking";
          }
          leaf network-instance {
            type string;
            description
              "Primary next hop network instance";
          }
          leaf neighbor {
            type inet:ip-address-no-zone;
            description
              "Neighbor address the primary nexthop belongs was received from";
          }
          leaf backup-next-hop {
            type inet:ip-address-no-zone;
            description
              "Next hop address for backup path tracking";
          }
          leaf backup-network-instance {
            type string;
            description
              "Backup Next hop network instance";
          }
          leaf backup-neighbor {
            type inet:ip-address-no-zone;
            description
              "Neighbor address the nexthop belongs was received from";
          }
          leaf tracker-label {
            type uint32;
            description
              "Protection tracker label if allocated";
          }
          leaf tracker-sid {
            type inet:ipv6-address;
            description
              "Protection tracker segment ID if allocated";
          }
          leaf bfd-source {
            type inet:ip-address-no-zone;
            description
              "BFD source address";
          }
          leaf bfd-destination {
            type inet:ip-address-no-zone;
            description
              "BFD destination address";
          }
          leaf bfd-session-id {
            type uint64;
            description
              "BFD Session ID for tracking";
          }
        }
      }
    }
  }

  /*
   * Augmentations for default bgp rib
   */
  augment "/oc-ni:network-instances/oc-ni:network-instance" +
          "/oc-ni:protocols/oc-ni:protocol" +
          "/oc-ni:bgp/oc-ni:rib" +
          "/oc-ni:afi-safis/oc-ni:afi-safi" {
    container l3vpn-ipv6-unicast {
      when "../oc-ni:afi-safi-name = 'oc-bgp-types:L3VPN_IPV6_UNICAST'" {
        description
          "Include this container for VPNv6 unicast RIB";
    }
    description
      "Routing tables for VPNv6 unicast -- active when the
      afi-safi name is l3vpn-ipv6-unicast";

      uses l3vpn-ipv6-loc-rib-top;
      uses l3vpn-ipv6-ni-exported-rib-top;
      uses l3vpn-ipv6-adj-rib-top;
    }
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv6-unicast/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv6-unicast/arc-oc-rib-bgp-aug:neighbors" +
          "/arc-oc-rib-bgp-aug:neighbor/arc-oc-rib-bgp-aug:adj-rib-in-pre" +
          "/arc-oc-rib-bgp-aug:routes/arc-oc-rib-bgp-aug:route" +
          "/arc-oc-rib-bgp-aug:state" {
    uses adj-rib-large-community-index-top;
    uses rib-in-pre-route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv6-unicast/arc-oc-rib-bgp-aug:neighbors" +
          "/arc-oc-rib-bgp-aug:neighbor/arc-oc-rib-bgp-aug:adj-rib-in-post" +
          "/arc-oc-rib-bgp-aug:routes/arc-oc-rib-bgp-aug:route" +
          "/arc-oc-rib-bgp-aug:state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv6-unicast/arc-oc-rib-bgp-aug:neighbors" +
          "/arc-oc-rib-bgp-aug:neighbor/arc-oc-rib-bgp-aug:adj-rib-out" +
          "/arc-oc-rib-bgp-aug:routes/arc-oc-rib-bgp-aug:route" +
          "/arc-oc-rib-bgp-aug:state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv6-unicast/arc-oc-rib-bgp-aug:neighbors" +
          "/arc-oc-rib-bgp-aug:neighbor/arc-oc-rib-bgp-aug:network-instances" +
          "/arc-oc-rib-bgp-aug:network-instance/arc-oc-rib-bgp-aug:adj-rib-out" +
          "/arc-oc-rib-bgp-aug:routes/arc-oc-rib-bgp-aug:route" +
          "/arc-oc-rib-bgp-aug:state" {
    uses adj-rib-ni-large-community-index-top;
    uses route-top;
  }

  augment "/oc-ni:network-instances/oc-ni:network-instance" +
          "/oc-ni:protocols/oc-ni:protocol" +
          "/oc-ni:bgp/oc-ni:rib" {
    uses large-community-sets-top;
  }

  augment "/oc-ni:network-instances/oc-ni:network-instance" +
          "/oc-ni:protocols/oc-ni:protocol" +
          "/oc-ni:bgp/oc-ni:rib" +
          "/oc-ni:attr-sets/oc-ni:attr-set" +
          "/oc-ni:state" {
    uses attr-top;
  }

  augment "/oc-ni:network-instances/oc-ni:network-instance" +
          "/oc-ni:protocols/oc-ni:protocol" +
          "/oc-ni:bgp/oc-ni:rib" +
          "/oc-ni:communities" +
          "/oc-ni:community/oc-ni:state" {
    uses comm-top;
  }

  augment "/oc-ni:network-instances/oc-ni:network-instance" +
          "/oc-ni:protocols/oc-ni:protocol" +
          "/oc-ni:bgp/oc-ni:rib" +
          "/oc-ni:ext-communities" +
          "/oc-ni:ext-community/oc-ni:state" {
    uses extcomm-top;
  }

  augment "/oc-ni:network-instances/oc-ni:network-instance" +
          "/oc-ni:protocols/oc-ni:protocol" +
          "/oc-ni:bgp/oc-ni:rib" +
          "/oc-ni:afi-safis/oc-ni:afi-safi" {
     container ipv4-label-unicast {
       when "../oc-ni:afi-safi-name = 'oc-bgp-types:IPV4_LABELED_UNICAST'" {
         description
           "Include this container for IPv4 label unicast RIB";
     }
     description
       "Routing tables for IPv4 Label unicast -- active when the
        afi-safi name is ipv4-label-unicast";

      uses ipv4-lu-loc-rib-top;
      uses ipv4-lu-adj-rib-top;
    }
  }

  augment "/oc-ni:network-instances/oc-ni:network-instance" +
          "/oc-ni:protocols/oc-ni:protocol" +
          "/oc-ni:bgp/oc-ni:rib" +
          "/oc-ni:afi-safis/oc-ni:afi-safi" {
     container ipv6-label-unicast {
       when "../oc-ni:afi-safi-name = 'oc-bgp-types:IPV6_LABELED_UNICAST'" {
         description
           "Include this container for IPv6 label unicast RIB";
       }
       description
         "Routing tables for IPv6 Label unicast -- active when the
          afi-safi name is ipv6-label-unicast";

       uses ipv6-lu-loc-rib-top;
       uses ipv6-lu-adj-rib-top;
     }
  }

  augment "/oc-ni:network-instances/oc-ni:network-instance" +
          "/oc-ni:protocols/oc-ni:protocol" +
          "/oc-ni:bgp/oc-ni:rib" +
          "/oc-ni:afi-safis/oc-ni:afi-safi" {
    container l3vpn-ipv4-unicast {
      when "../oc-ni:afi-safi-name = 'oc-bgp-types:L3VPN_IPV4_UNICAST'" {
        description
          "Include this container for VPNv4 label unicast RIB";
    }
    description
      "Routing tables for VPNv4 Label unicast -- active when the
      afi-safi name is l3vpn-ipv4-unicast";

      uses l3vpn-ipv4-loc-rib-top;
      uses l3vpn-ipv4-ni-exported-rib-top;
      uses l3vpn-ipv4-adj-rib-top;
    }
  }

  augment "/oc-ni:network-instances/oc-ni:network-instance" +
          "/oc-ni:protocols/oc-ni:protocol" +
          "/oc-ni:bgp/oc-ni:rib" +
          "/oc-ni:afi-safis/oc-ni:afi-safi" {
    container l2vpn-evpn {
      when "../oc-ni:afi-safi-name = 'oc-bgp-types:L2VPN_EVPN'" {
        description
          "Include this container for L2VPN EVPN RIB";
    }
    description
      "Routing tables for L2VPN EVPN -- active when the
      afi-safi name is l2vpn-evpn";

      uses l2vpn-evpn-loc-rib-top;
      uses l2vpn-evpn-adj-rib-top;
    }
  }


  augment "/oc-ni:network-instances/oc-ni:network-instance" +
          "/oc-ni:protocols/oc-ni:protocol" +
          "/oc-ni:bgp/oc-ni:rib" +
          "/oc-ni:afi-safis/oc-ni:afi-safi" {
    container ipv4-mup {
      when "../oc-ni:afi-safi-name = 'arc-oc-bgp-types:IPV4_MUP'" {
        description
          "Include this container for IPv4 MUP RIB";
      }
      description
        "Routing tables for IPv4 MUP -- active when the
         afi-safi name is ipv4-mup";

      uses mup-loc-rib-top;
      uses mup-adj-rib-top;
    }
  }

  augment "/oc-ni:network-instances/oc-ni:network-instance" +
          "/oc-ni:protocols/oc-ni:protocol" +
          "/oc-ni:bgp/oc-ni:rib" +
          "/oc-ni:afi-safis/oc-ni:afi-safi" {
    container ipv6-mup {
      when "../oc-ni:afi-safi-name = 'arc-oc-bgp-types:IPV6_MUP'" {
        description
          "Include this container for IPv6 MUP RIB";
      }
      description
        "Routing tables for IPv6 MUP -- active when the
         afi-safi name is ipv6-mup";

      uses mup-loc-rib-top;
      uses mup-adj-rib-top;
    }
  }

  augment "/oc-ni:network-instances/oc-ni:network-instance" +
          "/oc-ni:protocols/oc-ni:protocol" +
          "/oc-ni:bgp/oc-ni:rib" +
          "/oc-ni:afi-safis/oc-ni:afi-safi" {
    container ipv4-flowspec {
      when "../oc-ni:afi-safi-name = 'arc-oc-bgp-types:IPV4_FLOWSPEC'" {
        description
          "Include this container for Flowspec IPv4 unicast RIB";
    }
    description
      "Routing tables for Flowspec IPv4 unicast -- active when the
      afi-safi name is ipv4-flowspec";

      uses ipv4-flowspec-loc-rib-top;
      uses ipv4-flowspec-adj-rib-top;
    }
  }

  augment "/oc-ni:network-instances/oc-ni:network-instance" +
          "/oc-ni:protocols/oc-ni:protocol" +
          "/oc-ni:bgp/oc-ni:rib" +
          "/oc-ni:afi-safis/oc-ni:afi-safi" {
     container ipv6-flowspec {
       when "../oc-ni:afi-safi-name = 'arc-oc-bgp-types:IPV6_FLOWSPEC'" {
         description
           "Include this container for Flowspec IPv6 unicast RIB";
       }
       description
         "Routing tables for Flowspec IPv6 unicast -- active when the
          afi-safi name is ipv6-flowspec";

       uses ipv6-flowspec-loc-rib-top;
       uses ipv6-flowspec-adj-rib-top;
     }
   }

  augment "/oc-ni:network-instances/oc-ni:network-instance" +
          "/oc-ni:protocols/oc-ni:protocol" +
          "/oc-ni:bgp/oc-ni:rib" +
          "/oc-ni:afi-safis/oc-ni:afi-safi" {
    container l3vpn-ipv4-flowspec {
      when "../oc-ni:afi-safi-name = 'arc-oc-bgp-types:L3VPN_IPV4_FLOWSPEC'" {
        description
          "Include this container for Flowspec IPv4 unicast RIB";
    }
    description
      "Routing tables for Flowspec IPv4 unicast -- active when the
      afi-safi name is l3vpn-ipv4-flowspec";

      uses l3vpn-ipv4-flowspec-loc-rib-top;
      uses l3vpn-ipv4-ni-exported-rib-top;
      uses l3vpn-ipv4-flowspec-adj-rib-top;
    }
  }

  augment "/oc-ni:network-instances/oc-ni:network-instance" +
          "/oc-ni:protocols/oc-ni:protocol" +
          "/oc-ni:bgp/oc-ni:rib" +
          "/oc-ni:afi-safis/oc-ni:afi-safi" {
     container l3vpn-ipv6-flowspec {
       when "../oc-ni:afi-safi-name = 'arc-oc-bgp-types:L3VPN_IPV6_FLOWSPEC'" {
         description
           "Include this container for Flowspec IPv6 unicast RIB";
       }
       description
         "Routing tables for Flowspec IPv6 unicast -- active when the
          afi-safi name is l3vpn-ipv6-flowspec";

       uses l3vpn-ipv6-flowspec-loc-rib-top;
       uses l3vpn-ipv6-ni-exported-rib-top;
       uses l3vpn-ipv6-flowspec-adj-rib-top;
     }
   }

augment "/oc-ni:network-instances/oc-ni:network-instance" +
          "/oc-ni:protocols/oc-ni:protocol" +
          "/oc-ni:bgp/oc-ni:rib" +
          "/oc-ni:afi-safis/oc-ni:afi-safi" {
    container srte-policy-ipv4 {
      when "../oc-ni:afi-safi-name = 'oc-bgp-types:SRTE_POLICY_IPV4'" {
        description
          "Include this container for SRTE Policy IPv4 Policy RIB";
    }
    description
      "Routing tables for SRTE Policy IPv4 unicast -- active when the
      afi-safi name is srte-policy-ipv4";

      uses srte-policy-ipv4-loc-rib-top;
      uses srte-policy-ipv4-adj-rib-top;
    }
  }

  augment "/oc-ni:network-instances/oc-ni:network-instance" +
          "/oc-ni:protocols/oc-ni:protocol" +
          "/oc-ni:bgp/oc-ni:rib" +
          "/oc-ni:afi-safis/oc-ni:afi-safi" {
     container srte-policy-ipv6 {
       when "../oc-ni:afi-safi-name = 'oc-bgp-types:SRTE_POLICY_IPV6'" {
         description
           "Include this container for SRTE Policy IPv6 Policy RIB";
       }
       description
         "Routing tables for SRTE Policy IPv6 unicast -- active when the
          afi-safi name is srte-policy-ipv6";

       uses srte-policy-ipv6-loc-rib-top;
       uses srte-policy-ipv6-adj-rib-top;
     }
   }

   augment "/oc-ni:network-instances/oc-ni:network-instance" +
          "/oc-ni:protocols/oc-ni:protocol" +
          "/oc-ni:bgp/oc-ni:rib" +
          "/oc-ni:afi-safis/oc-ni:afi-safi" {
     container rtfilter {
       when "../oc-ni:afi-safi-name = 'arc-oc-bgp-types:RTFILTER'" {
         description
           "Include this container for RTFILTER RIB";
       }
       description
         "Routing tables for RTFILTER address family-- active when the
          afi-safi name is rtfilter";

       uses bgp-rtfilter-loc-rib-top;
       uses bgp-rtfilter-adj-rib-top;
     }
   }

  augment "/oc-ni:network-instances/oc-ni:network-instance" +
          "/oc-ni:protocols/oc-ni:protocol" +
          "/oc-ni:bgp/oc-ni:rib" +
          "/oc-ni:afi-safis/oc-ni:afi-safi" +
          "/oc-ni:ipv4-unicast/oc-ni:loc-rib" +
          "/oc-ni:routes/oc-ni:route/oc-ni:state" {
    uses loc-rib-large-community-index-top;
    uses route-top;
    uses bgp-loc-rib-remote-label;
  }

  augment "/oc-ni:network-instances/oc-ni:network-instance" +
          "/oc-ni:protocols/oc-ni:protocol" +
          "/oc-ni:bgp/oc-ni:rib" +
          "/oc-ni:afi-safis/oc-ni:afi-safi" +
          "/oc-ni:ipv4-unicast/oc-ni:neighbors" +
          "/oc-ni:neighbor/oc-ni:adj-rib-in-pre" +
          "/oc-ni:routes/oc-ni:route/oc-ni:state" {
    uses adj-rib-large-community-index-top;
    uses rib-in-pre-route-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv4-unicast/oc-ni:neighbors" +
          "/oc-ni:neighbor/oc-ni:adj-rib-in-post" +
          "/oc-ni:routes/oc-ni:route/oc-ni:state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv4-unicast/oc-ni:neighbors" +
          "/oc-ni:neighbor/adj-rib-out/routes/route/state" {
    uses adj-rib-large-community-index-top;
    uses route-top;
    uses bgp-loc-rib-remote-label;
  }

  augment "/oc-ni:network-instances/oc-ni:network-instance" +
          "/oc-ni:protocols/oc-ni:protocol" +
          "/oc-ni:bgp/oc-ni:rib" +
          "/oc-ni:afi-safis/oc-ni:afi-safi" +
          "/oc-ni:ipv6-unicast/oc-ni:loc-rib" +
          "/oc-ni:routes/oc-ni:route/oc-ni:state" {
    uses loc-rib-large-community-index-top;
    uses route-top;
    uses bgp-loc-rib-remote-label;
  }

  augment "/oc-ni:network-instances/oc-ni:network-instance" +
          "/oc-ni:protocols/oc-ni:protocol" +
          "/oc-ni:bgp/oc-ni:rib" +
          "/oc-ni:afi-safis/oc-ni:afi-safi" +
          "/oc-ni:ipv6-unicast/oc-ni:neighbors" +
          "/oc-ni:neighbor/oc-ni:adj-rib-in-pre" +
          "/oc-ni:routes/oc-ni:route/oc-ni:state" {
    uses adj-rib-large-community-index-top;
    uses rib-in-pre-route-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv6-unicast/oc-ni:neighbors" +
          "/oc-ni:neighbor/oc-ni:adj-rib-in-post" +
          "/oc-ni:routes/oc-ni:route/oc-ni:state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv6-unicast/oc-ni:neighbors" +
          "/oc-ni:neighbor/adj-rib-out/routes/route/state" {
    uses adj-rib-large-community-index-top;
    uses route-top;
    uses bgp-loc-rib-remote-label;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:ipv4-label-unicast/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/ipv4-label-unicast/neighbors/neighbor/adj-rib-in-pre" +
          "/routes/route/state" {
    uses adj-rib-large-community-index-top;
    uses rib-in-pre-route-top;
  }

  augment "/oc-ni:network-instances/oc-ni:network-instance" +
          "/oc-ni:protocols/oc-ni:protocol" +
          "/oc-ni:bgp/oc-ni:rib" +
          "/oc-ni:afi-safis/oc-ni:afi-safi" +
          "/ipv4-label-unicast/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/ipv4-label-unicast/neighbors/neighbor/adj-rib-out" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:ipv6-label-unicast/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/ipv6-label-unicast/neighbors/neighbor/adj-rib-in-pre" +
          "/routes/route/state" {
    uses adj-rib-large-community-index-top;
    uses rib-in-pre-route-top;
  }

  augment "/oc-ni:network-instances/oc-ni:network-instance" +
          "/oc-ni:protocols/oc-ni:protocol" +
          "/oc-ni:bgp/oc-ni:rib" +
          "/oc-ni:afi-safis/oc-ni:afi-safi" +
          "/ipv6-label-unicast/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/ipv6-label-unicast/neighbors/neighbor/adj-rib-out" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv4-unicast/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv4-unicast" +
          "/arc-oc-rib-bgp-aug:network-instances" +
          "/arc-oc-rib-bgp-aug:network-instance" +
          "/arc-oc-rib-bgp-aug:exported-rib" +
          "/arc-oc-rib-bgp-aug:routes" +
          "/arc-oc-rib-bgp-aug:route/arc-oc-rib-bgp-aug:state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv4-unicast/neighbors/neighbor/adj-rib-in-pre" +
          "/routes/route/state" {
    uses adj-rib-large-community-index-top;
    uses rib-in-pre-route-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv4-unicast/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv4-unicast/neighbors/neighbor/adj-rib-out" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv4-unicast/arc-oc-rib-bgp-aug:neighbors" +
          "/arc-oc-rib-bgp-aug:neighbor/arc-oc-rib-bgp-aug:network-instances" +
          "/arc-oc-rib-bgp-aug:network-instance/arc-oc-rib-bgp-aug:adj-rib-out" +
          "/arc-oc-rib-bgp-aug:routes/arc-oc-rib-bgp-aug:route" +
          "/arc-oc-rib-bgp-aug:state" {
    uses adj-rib-ni-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l2vpn-evpn/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/l2vpn-evpn/neighbors/neighbor/adj-rib-in-pre" +
          "/routes/route/state" {
    uses adj-rib-large-community-index-top;
    uses rib-in-pre-route-top;
  }

  augment "/oc-ni:network-instances/oc-ni:network-instance" +
          "/oc-ni:protocols/oc-ni:protocol" +
          "/oc-ni:bgp/oc-ni:rib" +
          "/oc-ni:afi-safis/oc-ni:afi-safi" +
          "/l2vpn-evpn/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/l2vpn-evpn/neighbors/neighbor/adj-rib-out" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:ipv4-mup/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/ipv4-mup/neighbors/neighbor/adj-rib-in-pre" +
          "/routes/route/state" {
    uses adj-rib-large-community-index-top;
    uses rib-in-pre-route-top;
  }

  augment "/oc-ni:network-instances/oc-ni:network-instance" +
          "/oc-ni:protocols/oc-ni:protocol" +
          "/oc-ni:bgp/oc-ni:rib" +
          "/oc-ni:afi-safis/oc-ni:afi-safi" +
          "/ipv4-mup/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/ipv4-mup/neighbors/neighbor/adj-rib-out" +
          "/routes/route/state" {
    uses adj-rib-large-community-index-top;
    uses route-top;
  }


  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:ipv6-mup/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/ipv6-mup/neighbors/neighbor/adj-rib-in-pre" +
          "/routes/route/state" {
    uses adj-rib-large-community-index-top;
    uses rib-in-pre-route-top;
  }

  augment "/oc-ni:network-instances/oc-ni:network-instance" +
          "/oc-ni:protocols/oc-ni:protocol" +
          "/oc-ni:bgp/oc-ni:rib" +
          "/oc-ni:afi-safis/oc-ni:afi-safi" +
          "/ipv6-mup/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/ipv6-mup/neighbors/neighbor/adj-rib-out" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/rtfilter/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/rtfilter/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/rtfilter/neighbors/neighbor/adj-rib-out" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv4-unicast/oc-ni:loc-rib/oc-ni:routes" +
          "/oc-ni:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv4-unicast/oc-ni:neighbors" +
          "/oc-ni:neighbor/oc-ni:adj-rib-in-pre" +
          "/oc-ni:routes/oc-ni:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv4-unicast/oc-ni:neighbors" +
          "/oc-ni:neighbor/oc-ni:adj-rib-in-post" +
          "/oc-ni:routes/oc-ni:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv4-unicast/oc-ni:neighbors" +
          "/oc-ni:neighbor/adj-rib-out/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv6-unicast/oc-ni:loc-rib/oc-ni:routes" +
          "/oc-ni:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv6-unicast/oc-ni:neighbors" +
          "/oc-ni:neighbor/oc-ni:adj-rib-in-pre" +
          "/oc-ni:routes/oc-ni:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv6-unicast/oc-ni:neighbors" +
          "/oc-ni:neighbor/oc-ni:adj-rib-in-post" +
          "/oc-ni:routes/oc-ni:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv6-unicast/oc-ni:neighbors" +
          "/oc-ni:neighbor/adj-rib-out/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:ipv4-label-unicast/arc-oc-rib-bgp-aug:loc-rib" +
          "/arc-oc-rib-bgp-aug:routes/arc-oc-rib-bgp-aug:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv4-label-unicast/neighbors/neighbor/adj-rib-in-pre" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv4-label-unicast/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv4-label-unicast/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:ipv6-label-unicast/arc-oc-rib-bgp-aug:loc-rib" +
          "/arc-oc-rib-bgp-aug:routes/arc-oc-rib-bgp-aug:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv6-label-unicast/neighbors/neighbor/adj-rib-in-pre" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv6-label-unicast/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv6-label-unicast/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv4-unicast/arc-oc-rib-bgp-aug:loc-rib" +
          "/arc-oc-rib-bgp-aug:routes/arc-oc-rib-bgp-aug:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv4-unicast/network-instances" +
          "/network-instance/exported-rib" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv4-unicast/neighbors/neighbor/adj-rib-in-pre" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv4-unicast/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv4-unicast/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv4-unicast/neighbors/neighbor/network-instances" +
          "/network-instance/adj-rib-out/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l2vpn-evpn/arc-oc-rib-bgp-aug:loc-rib" +
          "/arc-oc-rib-bgp-aug:routes/arc-oc-rib-bgp-aug:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l2vpn-evpn/neighbors/neighbor/adj-rib-in-pre" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l2vpn-evpn/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l2vpn-evpn/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:ipv4-mup/arc-oc-rib-bgp-aug:loc-rib" +
          "/arc-oc-rib-bgp-aug:routes/arc-oc-rib-bgp-aug:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv4-mup/neighbors/neighbor/adj-rib-in-pre" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv4-mup/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv4-mup/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:ipv6-mup/arc-oc-rib-bgp-aug:loc-rib" +
          "/arc-oc-rib-bgp-aug:routes/arc-oc-rib-bgp-aug:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv6-mup/neighbors/neighbor/adj-rib-in-pre" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv6-mup/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv6-mup/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/rtfilter/arc-oc-rib-bgp-aug:loc-rib" +
          "/arc-oc-rib-bgp-aug:routes/arc-oc-rib-bgp-aug:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/rtfilter/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/rtfilter/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/oc-ni:ipv4-unicast/oc-ni:neighbors" +
          "/oc-ni:neighbor" {
    container adj-rib-out {
      description
        "Per-neighbor table containing prefixes that have been
        advertised to the neighbor without applying output policy
        rules for attributes and/or next-hop change";

      uses ipv4-adj-rib-out;
    }
  }

  augment "/oc-ni:network-instances/oc-ni:network-instance" +
          "/oc-ni:protocols/oc-ni:protocol" +
          "/oc-ni:bgp/oc-ni:rib" +
          "/oc-ni:afi-safis/oc-ni:afi-safi" +
          "/oc-ni:ipv6-unicast/oc-ni:neighbors" +
          "/oc-ni:neighbor" {
    container adj-rib-out {
      description
        "Per-neighbor table containing prefixes that have been
        advertised to the neighbor without applying output policy
        rules for attributes and/or next-hop change";

      uses ipv6-adj-rib-out;
    }
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv6-unicast/arc-oc-rib-bgp-aug:loc-rib" +
          "/arc-oc-rib-bgp-aug:routes/arc-oc-rib-bgp-aug:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv6-unicast/network-instances" +
          "/network-instance/exported-rib" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv6-unicast/neighbors/neighbor/adj-rib-in-pre" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv6-unicast/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv6-unicast/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv6-unicast/neighbors/neighbor/network-instances" +
          "/network-instance/adj-rib-out/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv6-unicast" +
          "/arc-oc-rib-bgp-aug:network-instances" +
          "/arc-oc-rib-bgp-aug:network-instance" +
          "/arc-oc-rib-bgp-aug:exported-rib" +
          "/arc-oc-rib-bgp-aug:routes" +
          "/arc-oc-rib-bgp-aug:route/arc-oc-rib-bgp-aug:state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:srte-policy-ipv4/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/srte-policy-ipv4/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/srte-policy-ipv4/neighbors/neighbor/adj-rib-out" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:srte-policy-ipv6/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/srte-policy-ipv6/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/srte-policy-ipv6/neighbors/neighbor/adj-rib-out" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:srte-policy-ipv4/arc-oc-rib-bgp-aug:loc-rib" +
          "/arc-oc-rib-bgp-aug:routes/arc-oc-rib-bgp-aug:route" {
    description
      "Embedded path attributes state.";

    uses route-attr-set-top;
  }

  
  augment "/oc-ni:network-instances/oc-ni:network-instance" +
          "/oc-ni:protocols/oc-ni:protocol" +
          "/oc-ni:bgp/oc-ni:rib" +
          "/oc-ni:afi-safis/oc-ni:afi-safi" +
          "/srte-policy-ipv4/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/srte-policy-ipv4/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:srte-policy-ipv6/arc-oc-rib-bgp-aug:loc-rib" +
          "/arc-oc-rib-bgp-aug:routes/arc-oc-rib-bgp-aug:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/srte-policy-ipv6/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/srte-policy-ipv6/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:ipv4-flowspec/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/ipv4-flowspec/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/ipv4-flowspec/neighbors/neighbor/adj-rib-out" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:ipv6-flowspec/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/ipv6-flowspec/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/ipv6-flowspec/neighbors/neighbor/adj-rib-out" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:ipv4-flowspec/arc-oc-rib-bgp-aug:loc-rib" +
          "/arc-oc-rib-bgp-aug:routes/arc-oc-rib-bgp-aug:route" {
    description
      "Embedded path attributes state.";

    uses route-attr-set-top;
  }

  
  augment "/oc-ni:network-instances/oc-ni:network-instance" +
          "/oc-ni:protocols/oc-ni:protocol" +
          "/oc-ni:bgp/oc-ni:rib" +
          "/oc-ni:afi-safis/oc-ni:afi-safi" +
          "/ipv4-flowspec/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv4-flowspec/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:ipv6-flowspec/arc-oc-rib-bgp-aug:loc-rib" +
          "/arc-oc-rib-bgp-aug:routes/arc-oc-rib-bgp-aug:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv6-flowspec/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/ipv6-flowspec/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv4-flowspec/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv4-flowspec/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv4-flowspec/neighbors/neighbor/adj-rib-out" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv6-flowspec/arc-oc-rib-bgp-aug:loc-rib" +
          "/arc-oc-rib-bgp-aug:routes/arc-oc-rib-bgp-aug:route/arc-oc-rib-bgp-aug:state" {
    uses loc-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv6-flowspec/neighbors/neighbor/adj-rib-in-post" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv6-flowspec/neighbors/neighbor/adj-rib-out" +
          "/routes/route/state" {
    uses adj-rib-large-community-index-top;
    uses route-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv4-flowspec/arc-oc-rib-bgp-aug:loc-rib" +
          "/arc-oc-rib-bgp-aug:routes/arc-oc-rib-bgp-aug:route" {
    description
      "Embedded path attributes state.";

    uses route-attr-set-top;
  }

  
  augment "/oc-ni:network-instances/oc-ni:network-instance" +
          "/oc-ni:protocols/oc-ni:protocol" +
          "/oc-ni:bgp/oc-ni:rib" +
          "/oc-ni:afi-safis/oc-ni:afi-safi" +
          "/l3vpn-ipv4-flowspec/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv4-flowspec/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/arc-oc-rib-bgp-aug:l3vpn-ipv6-flowspec/arc-oc-rib-bgp-aug:loc-rib" +
          "/arc-oc-rib-bgp-aug:routes/arc-oc-rib-bgp-aug:route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv6-flowspec/neighbors/neighbor/adj-rib-in-post" +
          "/routes/route" {
    description
      "Embedded path attributes state.";

    uses route-attr-set-top;
  }

  augment "/oc-ni:network-instances/oc-ni:network-instance" +
          "/oc-ni:protocols/oc-ni:protocol" +
          "/oc-ni:bgp/oc-ni:rib" +
          "/oc-ni:afi-safis/oc-ni:afi-safi" +
          "/l3vpn-ipv6-flowspec/neighbors/neighbor/adj-rib-out" +
          "/routes/route" {
    description
      "Embedded path attributes state.";

    uses route-attr-set-top;
  }

  augment "/oc-ni:network-instances/oc-ni:network-instance" +
          "/oc-ni:protocols/oc-ni:protocol" +
          "/oc-ni:bgp/oc-ni:rib" {
    description
      "Protection tracker information";
    uses protection-tracker-top;
  }

  augment "/oc-ni:network-instances/oc-ni:network-instance" +
          "/oc-ni:protocols/oc-ni:protocol" +
          "/oc-ni:bgp/oc-ni:rib" +
          "/oc-ni:attr-sets/oc-ni:attr-set" {
      uses bgp-pmsi-tunnel-attr-top;
      uses bgp-prefix-sid-attr-top;
      uses bgp-tunnel-encap-attr-top;
  }
}
