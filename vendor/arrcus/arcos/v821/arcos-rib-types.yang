module arcos-rib-types {
  yang-version 1.1;
  namespace "http://yang.arrcus.com/arcos/rib/types";
  prefix arc-rib-types;

  organization
    "Arrcus, Inc";

  contact
    "Arrcus, Inc.
     2077 Gateway Place,
     San Jose, CA 95110
     Tel: +1 (408) 884-1965
     E-mail: yang-support@arrcus.com";

  description
    "This module lists the RIB related information.
     Copyright 2019-2024 by Arrcus, Inc.
     All rights reserved.";

  revision 2024-10-17 {
    description
      "Adding new rib-type for CLISPEC";
  }

  typedef rib-af-types {
    type enumeration {
      enum ipv4 {
        description "IPV4";
      }
      enum ipv6 {
        description "IPV6";
      }
    }
  }
}
