module arcos-mpls {
  yang-version 1.1;
  namespace "http://yang.arrcus.com/arcos/mpls";
  prefix "arc-mpls";

  import ietf-yang-types {
    prefix ietf-yang;
  }
  import ietf-inet-types {
    prefix ietf-inet;
  }
  import openconfig-yang-types {
    prefix oc-yang;
  }
  import openconfig-inet-types {
    prefix oc-inet;
  }
  import openconfig-network-instance {
    prefix oc-netinst;
  }
  import openconfig-interfaces {
    prefix oc-if;
  }
  import openconfig-mpls-types {
    prefix oc-mplst;
  }

  import openconfig-policy-types {
    prefix oc-pol-types;
  }

  import arcos-openconfig-bgp-augments {
    prefix arc-oc-bgp-aug;
  }

  import arcos-rsvp {
    prefix arc-rsvp;
  }

  organization
    "Arrcus, Inc.";

  contact
    "Arrcus, Inc.
     2077 Gateway Place
     Suite 400
     San Jose, CA 95110

     E-mail: yang-support@arrcus.com";

  description
    "This module defines configuration and state information
     for ArcOS MPLS.

     Copyright (c) 2023 by Arrcus, Inc.
     All rights reserved.";

  revision "2024-04-19" {
    description
      "Add new label block identifier for SR-Policy";
  }

  revision "2023-04-15" {
    description
      "Label database information";
  }

  revision "2023-03-15" {
    description
      "Initial version. ArcOS extensions to reserved-label-block";
  }


  /*
   * Label block usage type
   */
  identity LABEL_BLOCK_USAGE {
    description
      "Base type for label-block usage.";
  }

  identity USAGE_UNKNOWN {
    base LABEL_BLOCK_USAGE;
    description
      "Unknown";
  }

  identity LDP_COMMON {
    base LABEL_BLOCK_USAGE;
    description
      "LDP dynamic label allocation";
  }

  identity RSVP_COMMON {
    base LABEL_BLOCK_USAGE;
    description
      "RSVP dynamic label allocation";
  }

  identity ISIS_SRGB {
    base LABEL_BLOCK_USAGE;
    description
      "ISIS Segment Routing Global Block label assignment";
  }

  identity ISIS_SRLB {
    base LABEL_BLOCK_USAGE;
    description
      "ISIS Segment Routing Local Block label assignment";
  }

  identity BGP_COMMON {
    base LABEL_BLOCK_USAGE;
    description
      "BGP common dynamic label allocation";
  }

  identity BGP_SRGB {
    base LABEL_BLOCK_USAGE;
    description
      "BGP Segment Routing Global Block label assignment";
  }

  identity BGP_SRLB {
    base LABEL_BLOCK_USAGE;
    description
      "BGP Segment Routing Local Block label assignment";
  }

  identity BGP_EVPN_COMMON {
    base LABEL_BLOCK_USAGE;
    description
      "BGP EVPN common dynamic label allocation";
  }

  identity BGP_EVPN_ESI {
    base LABEL_BLOCK_USAGE;
    description
      "BGP EVPN ESI routes dynamic label allocation";
  }

  identity BGP_EVPN_IMET {
    base LABEL_BLOCK_USAGE;
    description
      "BGP EVPN IMET routes dynamic label allocation";
  }

  identity SR_POLICY_SRLB {
    base LABEL_BLOCK_USAGE;
    description
      "SR-Policy Local Block label assignment";
  }

  /*
   * Label key type
   */
  identity LABEL_KEY_TYPE {
    description
      "Base type for label key type";
  }

  identity KEY_UNKNOWN {
    base LABEL_KEY_TYPE;
    description
      "Unknown label key";
  }

  identity KEY_IPV4_PREFIX {
    base LABEL_KEY_TYPE;
    description
      "IPv4 Prefix";
  }

  identity KEY_IPV6_PREFIX {
    base LABEL_KEY_TYPE;
    description
      "IPv6 Prefix";
  }

  identity KEY_IPV4_NH {
    base LABEL_KEY_TYPE;
    description
      "IPv4 Nexthop";
  }

  identity KEY_IPV6_NH {
    base LABEL_KEY_TYPE;
    description
      "IPv6 Nexthop";
  }

  identity KEY_IPV4_ADJ {
    base LABEL_KEY_TYPE;
    description
      "IPv4 Adjacency";
  }

  identity KEY_IPV6_ADJ {
    base LABEL_KEY_TYPE;
    description
      "IPv6 Adjacency";
  }

  identity KEY_VRF {
    base LABEL_KEY_TYPE;
    description
      "VRF";
  }

  identity KEY_EVPN_PREFIX {
    base LABEL_KEY_TYPE;
    description
      "EVPN Prefix";
  }

  identity KEY_INTERFACE {
    base LABEL_KEY_TYPE;
    description
      "Interface";
  }

  identity KEY_RSVP_LSP {
    base LABEL_KEY_TYPE;
    description
      "RSVP-TE tunnel";
  }

  /*
   * MPLS label statistics
   */
  grouping arcos-label-stats {
    description
      "Label statistics";

    leaf label-space {
      type uint32;
      description
        "Total label space (range) configured";
    }

    leaf labels {
      type uint32;
      description
        "Total labels currently allocated";
    }

    leaf allocs {
      type ietf-yang:counter64;
      description
        "Label alloc operations";
    }

    leaf frees {
      type ietf-yang:counter64;
      description
        "Label free operations";
    }

    leaf alloc-errors {
      type ietf-yang:counter64;
      description
        "Label alloc errors";
    }

    leaf free-errors {
      type ietf-yang:counter64;
      description
        "Label free errors";
    }
  }

  grouping arcos-label-stats-structure {
    description
      "Label statistics structure";

    container statistics {
      description
        "Label statistics";

      uses arcos-label-stats;
    }
  }

  /*
   * MPLS label key state
   */
  grouping arcos-label-key-state {
    description
      "Label entry key state";

    leaf type {
      type identityref {
        base LABEL_KEY_TYPE;
      }
      description
        "Label key type";
    }

    leaf sub-type {
      type uint32;
      description
        "Label key sub type";
    }

    leaf table-id {
      type uint32;
      description
        "VRF Table ID";
    }

    leaf vrf-name {
      type string;
      description
        "VRF Name";
    }

    leaf vrf-id {
      type uint32;
      description
        "VRF ID";
    }

    leaf ip-prefix {
      type ietf-inet:ip-prefix;
      description
        "IP prefix";
    }

    leaf raw-prefix {
      type ietf-yang:hex-string;
      description
        "Raw prefix value in hex format";
    }

    leaf raw-prefix-length {
      type uint32;
      description
        "Raw prefix length";
    }

    leaf nh-address {
      type ietf-inet:ip-address;
      description
        "Nexthop address";
    }

    leaf ifindex {
      type uint64;
      description
        "Interface if-index";
    }

    leaf source-address {
      type ietf-inet:ip-address;
      description
        "Source IP address";
    }

    leaf destination-address {
      type ietf-inet:ip-address;
      description
        "Destination IP address";
    }

    leaf tunnel-id {
      type uint32;
      description
        "Tunnel ID";
    }

    leaf lsp-id {
      type uint32;
      description
        "LSP ID";
    }
  }

  /*
   * MPLS label key structure
   */
  grouping arcos-label-key-structure {
    description
      "Label entry key structure";

    container label-key {
      description
        "Label key";

      container state {
        description
          "Label key state";

        uses arcos-label-key-state;
      }
    }
  }

  /*
   * MPLS label entry state
   */
  grouping arcos-label-entry-state {
    description
      "Label entry state";

    leaf label {
      type oc-mplst:mpls-label;
      description
        "Label value";
    }

    leaf block-name {
      type string;
      description
        "Label block name";
    }
  }

  grouping arcos-freed-label-entry-state {
    description
      "Freed label entry state";

    leaf freed {
      type boolean;
      description
        "Indicates if the label entry is freed";
    }

    leaf stale {
      type boolean;
      description
        "Indicates if the label entry is stale";
    }

    leaf refcount {
      type boolean;
      description
        "Internal refcount";
    }
  }

  /*
   * MPLS freed label entry structure
   */
  grouping arcos-freed-label-entry-structure {
    description
      "Freed label entry structure";

    container freed-labels {
      description
        "Freed label entries";

      list freed-label {
        key "label";
        description
          "Label entry";

        leaf label {
          type leafref {
            path "../state/label";
          }
          description
            "Label value";
        }

        container state {
          description
            "Label entry state";

          uses arcos-label-entry-state;
          uses arcos-freed-label-entry-state;
        }

        uses arcos-label-key-structure;
      }
    }
  }

  /*
   * MPLS label entry structure
   */
  grouping arcos-label-entry-structure {
    description
      "Label entry structure";

    container labels {
      description
        "Label entries";

      list label {
        key "label";
        description
          "Label entry";

        leaf label {
          type leafref {
            path "../state/label";
          }
          description
            "Label value";
        }

        container state {
          description
            "Label entry state";

          uses arcos-label-entry-state;
        }

        uses arcos-label-key-structure;
      }
    }
  }

  /*
   * MPLS label block state
   */
  grouping arcos-label-block-state {
    description
      "Label block state";

    leaf lower-bound {
      type oc-mplst:mpls-label;
      description
        "Lower bound of the label block range";
    }

    leaf upper-bound {
      type oc-mplst:mpls-label;
      description
        "Upper bound for the label block range";
    }

    leaf block-name {
      type string;
      description
        "Label block name";
    }

    leaf opaque-flags {
      type ietf-yang:hex-string;
      description
        "Internal flags";
    }
  }

  /*
   * MPLS label block structure
   */
  grouping arcos-label-block-structure {
    description
      "Label block structure";

    container blocks {
      description
        "Label blocks";

      list block {
        key "lower-bound";
        description
          "Label block";

        leaf lower-bound {
          type leafref {
            path "../state/lower-bound";
          }
          description
            "Lower bound of the label block range";
        }

        container state {
          description
            "Label block state";

          uses arcos-label-block-state;
        }

        uses arcos-label-stats-structure;
      }
    }
  }

  /*
   * MPLS label usage state
   */
  grouping arcos-label-usage-state {
    description
      "Label Usage state";

    leaf usage {
      type identityref {
        base LABEL_BLOCK_USAGE;
      }
      description
        "Label usage type";
    }

    leaf blocks {
      type uint32;
      description
        "Number of active label blocks";
    }

    leaf opaque-flags {
      type ietf-yang:hex-string;
      description
        "Internal flags";
    }
  }

  /*
   * MPLS label usage structure
   */
  grouping arcos-label-usage-structure {
    description
      "Label usage structure";

    container usages {
      description
        "Label usages";

      list usage {
        key "usage";
        description
          "Label usage";

        leaf usage {
          type leafref {
            path "../state/usage";
          }
          description
            "Label usage type";
        }

        container state {
          description
            "Label usage state";

          uses arcos-label-usage-state;
        }

        uses arcos-label-stats-structure;
        uses arcos-label-block-structure;
        uses arcos-label-entry-structure;
        uses arcos-freed-label-entry-structure;
      }
    }
  }

  /*
   * MPLS Label DB state
   */
  grouping arcos-label-db-state {
    description
      "Label DB state";

    leaf protocol-identifier {
      type identityref {
        base oc-pol-types:INSTALL_PROTOCOL_TYPE;
      }
      description
        "The identifier of the protocol that owns this label DB";
    }

    leaf protocol-name {
      type string;
      description
        "The instance name of the protocol that owns this label DB";
    }

    leaf configured-blocks {
      type uint32;
      description
        "Total number of label blocks configured on this router";
    }

    leaf active-blocks {
      type uint32;
      description
        "Number of active blocks available for this client";
    }

    leaf active-usages {
      type uint32;
      description
        "Number of active usages available for this client";
    }
  }

  /*
   * MPLS Label DB top-level structure
   */
  grouping arcos-label-db-top {
    description
      "Top level label database structure";

    container label-db {
      config false;
      description
        "Top level label database.";

      container state {
        description
          "Label DB global state";

        uses arcos-label-db-state;
      }

      uses arcos-label-stats-structure;
      uses arcos-label-usage-structure;
    }
  }

  /*
   * Arcos label-block config
   */
  grouping arcos-label-block-config {
    description
      "Arcos label-block configurations";

    leaf usage {
      type identityref {
        base LABEL_BLOCK_USAGE;
      }

      description
        "The usage or purpose for which labels are allocated
         from the label-block";
    }

    leaf protocol-identifier {
      type identityref {
        base oc-pol-types:INSTALL_PROTOCOL_TYPE;
      }

      description
        "The identifier of the protocol that wants to allocate labels
         from the label-block";
    }

    leaf protocol-name {
      type string;

      description
        "The instance name of the protocol that wants to allocate labels
         from the label-block";
    }
  }

  /*
   * Augment reserved-label-block config
   */
  augment "/oc-netinst:network-instances/oc-netinst:network-instance" +
          "/oc-netinst:mpls/oc-netinst:global" +
          "/oc-netinst:reserved-label-blocks/oc-netinst:reserved-label-block" +
          "/oc-netinst:config" {
    uses arcos-label-block-config;
  }

  /*
   * Augment reserved-label-block state
   */
  augment "/oc-netinst:network-instances/oc-netinst:network-instance" +
          "/oc-netinst:mpls/oc-netinst:global" +
          "/oc-netinst:reserved-label-blocks/oc-netinst:reserved-label-block" +
          "/oc-netinst:state" {
    uses arcos-label-block-config;
  }

  /*
   * Augment label-db under BGP global mpls
   */
  augment "/oc-netinst:network-instances/oc-netinst:network-instance" +
          "/oc-netinst:protocols/oc-netinst:protocol/oc-netinst:bgp" +
          "/oc-netinst:global/arc-oc-bgp-aug:mpls" {
    uses arcos-label-db-top;
  }

  /*
   * Augment label-db under ISIS global mpls
   */
  augment "/oc-netinst:network-instances/oc-netinst:network-instance" +
          "/oc-netinst:protocols/oc-netinst:protocol/oc-netinst:isis" +
          "/oc-netinst:global/oc-netinst:mpls" {
    uses arcos-label-db-top;
  }

  /*
   * Augment label-db under LDP global
   */
  augment "/oc-netinst:network-instances/oc-netinst:network-instance" +
          "/oc-netinst:mpls/oc-netinst:signaling-protocols/oc-netinst:ldp" +
          "/oc-netinst:global" {
    uses arcos-label-db-top;
  }

  /*
   * Augment label-db under RSVP global mpls
   */
  augment "/oc-netinst:network-instances/oc-netinst:network-instance" +
          "/oc-netinst:protocols/oc-netinst:protocol/arc-rsvp:rsvp" +
          "/arc-rsvp:global/arc-rsvp:mpls" {
    uses arcos-label-db-top;
  }
}
