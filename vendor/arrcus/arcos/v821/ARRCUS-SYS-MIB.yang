/*
 * Generated by confdc --mib2yang-std
 * Source: ARRCUS-SYS-MIB.mib
 */
/*
 * This YANG module has been generated by smidump 0.5.0:
 *
 *      smidump -f yang ARRCUS-SYS-MIB
 *
 * Do not edit. Edit the source file instead!
 */

module ARRCUS-SYS-MIB {

  namespace "urn:ietf:params:xml:ns:yang:smiv2:ARRCUS-SYS-MIB";
  prefix "arrcus-sys";

  import SNMPv2-TC {
    prefix "snmpv2-tc";
  }

  import ietf-yang-smiv2 {
    prefix "smiv2";
  }

  organization
   "@ARRCUS";

  contact
   "@arrcus.com";

  description
   "This module defines the model for viewing Arrcus specific system information";

  revision 2023-07-20 {
    description
     "@REVISION-DESCRIPTION";
  }


  container ARRCUS-SYS-MIB {
    config false;

    container sysInfo {
      smiv2:oid "1.3.6.1.4.1.51604.1.1.1.1";

      leaf sysName {
        type snmpv2-tc:DisplayString;
        description
         "The name of the system.";
        smiv2:max-access "read-only";
        smiv2:oid "1.3.6.1.4.1.51604.1.1.1.1.1";
      }
    }
  }

  smiv2:alias "aRRCUS-SYS-MIB" {
    smiv2:oid "1.3.6.1.4.1.51604.1.1.1";
  }

  smiv2:alias "sysInfo" {
    smiv2:oid "1.3.6.1.4.1.51604.1.1.1.1";
  }

}
