module arcos-rsvp {
  yang-version 1.1;
  namespace "http://yang.arrcus.com/arcos/arcos-rsvp";
  prefix "arc-rsvp";

  import openconfig-yang-types {
    prefix yang;
  }
  import ietf-yang-types {
    prefix "ietf-yang";
  }
  import ietf-inet-types {
    prefix inet;
  }
  import openconfig-network-instance {
    prefix oc-netinst;
  }
  import openconfig-keychain-types {
    prefix oc-keychain-types;
  }
  import openconfig-interfaces {
    prefix oc-if;
  }
  import openconfig-mpls-types {
    prefix oc-mplst;
  }
  import openconfig-types {
    prefix oc-types;
  }
  import openconfig-policy-types {
    prefix oc-pol-types;
  }
  import arcos-openconfig-policy-types {
    prefix arc-oc-pol-types;
  }
  import arcos-rsvp-types {
    prefix arc-rsvp-types;
  }

  // Include submodules
  include arcos-rsvp-statistics;
  include arcos-rsvp-session;

  organization
    "Arrcus, Inc";

  contact
    "Arrcus, Inc.
     2077 Gateway Place
     Suite 400
     San Jose, CA 95110

     E-mail: yang-support@arrcus.com";

  description
    "This module defines configuration and state information
     for ReSource reserVation Protocol (RSVP).

     Copyright (c) 2016-2022 by Arrcus, Inc.
     All rights reserved.";

  revision "2022-05-01" {
    description
      "Add MPLS structure under global.";
  }

  revision "2022-02-24" {
    description
      "Initial version.";
  }


  /*
   * RSVP MPLS
   */
  grouping rsvp-mpls-structure {
    description
      "This grouping defines RSVP MPLS structure";

    container mpls {
      description
        "MPLS information in RSVP";
    }
  }

  /*
   * RSVP INTERFACE ADDRESS
   */
  grouping rsvp-interface-address-state {
    description
      "This grouping defines interface address state.";

    leaf address {
      type inet:ip-address;
      description
        "Interface address of the local interface";
    }

    leaf interface-id {
      type uint32;
      description
        "Interface ID of the local interface";
    }

    leaf ifindex {
      type uint32;
      description
        "IfIndex of the local interface";
    }

    leaf interface-name {
      type string;
      description
        "Name of the local interface";
    }

    leaf-list info-producers {
      type identityref {
        base "arc-rsvp-types:RSVP-INFO-PRODUCER";
      }
      description
        "Producers of interface address information";
    }
  }

  grouping rsvp-interface-address-structure {
    description
      "This grouping defines interface address info in RSVP.";

    container interface-addresses {
      config false;

      description
        "This container defines interface address info in RSVP.";

      list interface-address {
        key "address interface-id";

        description
          "Local address info in RSVP.";

        leaf address {
          type leafref {
            path "../state/address";
          }
          description
            "Local Interface Address";
        }

        leaf interface-id {
          type leafref {
            path "../state/interface-id";
          }
          description
            "Local Interface ID";
        }

        container state {
          description
            "Local Address state";

          uses rsvp-interface-address-state;
        }
      }
    }
  }


  /*
   * RSVP IGP
   */
  grouping rsvp-igp-neighbor-state {
    description
      "This grouping defines IGP neighbor state.";

    leaf address {
      type inet:ip-address;
      description
        "Interface address assigned by the neighbor for the interface
         on which the neighbor adjacency is established.";
    }

    leaf interface-id {
      type uint32;
      description
        "Interface ID assigned by the neighbor for the interface
         on which the neighbor adjacency is established.";
    }

    leaf local-ifindex {
      type uint32;
      description
        "IfIndex of the local interface";
    }

    leaf local-interface-name {
      type string;
      description
        "Name of the local interface";
    }

    leaf local-address {
      type inet:ip-address;
      description
        "Local interface address for the interface on which IGP neighbor
         adjacency is established.";
    }

    leaf local-interface-id {
      type uint32;
      description
        "Local Interface ID for the interface on which IGP neighbor
         adjacency is established.";
    }

    leaf-list info-producers {
      type identityref {
        base "arc-rsvp-types:RSVP-INFO-PRODUCER";
      }
      description
        "Producers of IGP neighbor information";
    }
  }

  grouping rsvp-igp-neighbor-structure {
    description
      "This grouping defines IGP neighbor info in RSVP.";

    container neighbors {
      config false;

      description
        "This container defines IGP neighbor info in RSVP.";

      list neighbor {
        key "address interface-id";

        description
          "IGP neighbor info in RSVP.";

        leaf address {
          type leafref {
            path "../state/address";
          }
          description
            "Neighbor Address";
        }

        leaf interface-id {
          type leafref {
            path "../state/interface-id";
          }
          description
            "Neighbor Interface ID";
        }

        container state {
          description
            "IGP Neighbor state";

          uses rsvp-igp-neighbor-state;
        }
      }
    }
  }

  grouping rsvp-igp-state {
    description
      "This grouping defines RSVP IGP state";
  }

  grouping rsvp-igp-structure {
    description
      "This grouping defines RSVP IGP structure";

    container igp {
      config false;
      description
        "IGP information in RSVP";

      container state {
        config false;
        description
          "IGP state in RSVP";

        uses rsvp-igp-state;
      }

      container statistics {
        config false;
        description
          "IGP statistics in RSVP";

        uses rsvp-igp-statistics;
      }

      uses rsvp-igp-neighbor-structure;
    }
  }


  /*
   * RSVP Interface Neighbors
   */

  grouping rsvp-interface-neighbor-state {
    description
      "This grouping defines RSVP Neighbor state.";

    leaf address {
      type inet:ip-address;
      description
        "Address of the RSVP neighbor.";
    }

    leaf epoch {
      type uint32;

      description
        "Neighbor epoch.";
      reference
        "RFC5063";
    }

    leaf expiry-timestamp {
      type string;
      description
        "Timestamp of neighbor state expiry";
    }

    leaf ifindex {
      type uint32;

      description
        "Interface Ifindex on which the neighbor was discovered.";
    }

    leaf hello-supported {
      type boolean;

      description
        "Indicates if Hello message supported.";
    }

    leaf hello-status {
      type identityref {
        base "arc-rsvp-types:RSVP-HELLO-STATUS";
      }

      description
        "Hello Status.";
    }

    leaf neighbor-status {
      type identityref {
        base "arc-rsvp-types:RSVP-NEIGHBOR-STATUS";
      }

      description
        "Neighbor Status.";
    }

    leaf refresh-reduction-status {
      type identityref {
        base "arc-rsvp-types:RSVP-NEIGHBOR-RR-STATUS";
      }

      description "Neighbor Refresh Reduction Status";
    }

    leaf tunnel-count {
      type uint32;
      description "Number of tunnels signaled from this neighbor";
    }
  }

  grouping rsvp-interface-neighbor-structure {
    description
      "This grouping defines RSVP neighbors.";

    container neighbors {
      config false;
      description
        "RSVP neighbors.";

      list neighbor {
        key "address";
        description
          "List of RSVP neighbors";

        leaf address {
          type leafref {
            path "../state/address";
          }

          description
            "Address of the RSVP neighbor.";
        }

        container state {
          description
            "Container for all RSVP neighbor state information.";

          uses rsvp-interface-neighbor-state;
        }
      }
    }
  }


  /*
   * RSVP Interfaces
   */

  grouping rsvp-interface-auth-config {
    description
      "Top level container for RSVP authentication
       parameters.";

    leaf enable {
      type boolean;
      default "false";
      description
        "'true' if RSVP Authentication is enabled.
         'false' if RSVP Authentication is disabled.";
    }

    leaf authentication-key {
      type string;
      description
        "An authentication key string.";
      reference
        "RFC2747: RSVP Cryptographic Authentication";
    }

    leaf crypto-algorithm {
      must "../enable = 'true'";
      type identityref {
        base oc-keychain-types:CRYPTO_TYPE;
      }
      description
        "Cryptographic algorithm associated with key.";
    }
  }

  grouping rsvp-interface-bw-res-state {
    description
      "Grouping for RSVP interface bandwidth reservation state
       per priority value.";

    leaf priority {
      type union {
        type uint8 {
          range 0..7;
        }
        type arc-rsvp-types:rsvp-priority-level-type;
      }

      description
        "RSVP priority level for LSPs traversing the interface";
    }

    leaf reserved-bw {
      type oc-mplst:bandwidth-mbps;

      description
        "The amount of bandwidth currently reserved on this link.";
      reference
         "RFC5305 IS-IS Extensions for Traffic Engineering";
    }

    leaf unreserved-bw {
      type oc-mplst:bandwidth-mbps;

      description
        "The amount of bandwidth reservable in this on this link.
         Note that this can be greater than the bandwidth of the
         link in case of oversubscription.";
      reference
         "RFC5305 IS-IS Extensions for Traffic Engineering";
    }

    leaf active-reservation-count {
      type yang:gauge64;

      description
        "Number of active RSVP reservations in the
         associated priority, or the sum of all
         reservations when the priority level is set to
         ALL";
    }

    leaf high-watermark {
      type oc-mplst:bandwidth-mbps;

      description
        "Maximum bandwidth reserved on the interface
         within the priority, or across all priorities
         in the case that the priority level is set
         to ALL";
    }
  }

  grouping rsvp-interface-bw-res-structure {
    description
      "Grouping for RSVP interface bandwidth per priority.";

    container reservations {
      config false;
      description
        "Enclosing container for bandwidth reservation per priority";

      list reservation {
        key "priority";
        description
          "Bandwidth reservation per priority on the interface.";

        leaf priority {
          type leafref {
            path "../state/priority";
          }

          description
            "Reference to the RSVP priority level";
        }

        container state {
          description
            "Bandwidth reservation information";

          uses rsvp-interface-bw-res-state;
        }
      }
    }
  }

  grouping rsvp-interface-bw-state {
    description
      "Grouping for RSVP interface bandwidth related state.";

    leaf max-link-bw {
      type oc-mplst:bandwidth-mbps;

      description
        "The maximum bandwidth that can be used on this interface";
      reference
         "RFC5305 IS-IS Extensions for Traffic Engineering";
    }

    leaf max-reservable-link-bw {
      type oc-mplst:bandwidth-mbps;

      description
        "The maximum bandwidth that can be reserved on this interface.
         This can be greater than the bandwidth of the link in case
         of oversubscription.";
      reference
         "RFC5305 IS-IS Extensions for Traffic Engineering";
    }

    leaf residual-bw {
      type oc-mplst:bandwidth-mbps;

      description
        "The residual bandwidth is defined to be the maximum
         bandwidth [RFC5305] minus the bandwidth currently allocated
         to RSVP-TE label switched paths. This can be greater than the
         bandwidth of the link in case of oversubscription.";
      reference
         "RFC8570 IS-IS Traffic Engineering (TE) Metric Extensions";
    }

    leaf available-bw {
      type oc-mplst:bandwidth-mbps;

      description
        "The available bandwidth is defined to be residual bandwidth
         minus the measured bandwidth used for the actual
         forwarding of non-RSVP-TE label switched path packets.";
      reference
         "RFC8570 IS-IS Traffic Engineering (TE) Metric Extensions";
    }
  }

  grouping rsvp-interface-bw-config {
    description
      "Grouping for RSVP interface bandwidth related config.";

    leaf subscription {
      type oc-types:percentage;
      description
        "The percentage of the interface bandwidth that
         RSVP can reserve";
    }
  }

  grouping rsvp-interface-bw-structure {
    description
      "Grouping for RSVP interface bandwidth reservation.";

    container bandwidth {
      description
        "RSVP interface bandwidth subscription and reservations.";

      container config {
        description
          "RSVP interface bandwidth config.";

        uses rsvp-interface-bw-config;
      }

      container state {
        config false;
        description
          "RSVP interface bandwidth state.";

        uses rsvp-interface-bw-config;
        uses rsvp-interface-bw-state;
      }

      uses rsvp-interface-bw-res-structure;
    }
  }

  grouping rsvp-interface-te-link-state {
    description
      "Grouping for RSVP interface TE Link state.";

    leaf ifindex {
      type uint32;
      description
        "IfIndex of the TE Link";
    }

    leaf te-enabled {
      type boolean;
      description
        "Indicates whether TE Link is enabled.";
    }

    leaf te-oper-status {
      type enumeration {
        enum UP {
          description
            "TE Link is UP";
        }
        enum DOWN {
          description
            "TE Link is DOWN";
        }
      }

      description
        "Oper status of the TE Link";
    }

    leaf is-bundle {
      type boolean;
      description
        "Indicates whether TE Link is a bundle.";
    }

    leaf local-address {
      type inet:ip-address;
      description
        "Local interface address";
    }

    leaf local-interface-id {
      type uint32;
      description
        "Local Interface ID";
    }

    leaf remote-address {
      type inet:ip-address;
      description
        "Remote interface address";
    }

    leaf remote-interface-id {
      type uint32;
      description
        "Remote Interface ID";
    }

    leaf remote-router-id {
      type yang:dotted-quad;
      description
        "Remote router-id";
    }

    leaf te-metric {
      type uint32;
      description
        "TE specific metric for the link";
    }

    leaf admin-group-bits {
      type ietf-yang:hex-string;
      description
        "Bits representing Admin-Groups enabled on the link";
    }

    leaf igp-advertise {
      type boolean;
      description
        "Indicates whether this link information is advertised in IGP.";
    }
  }

  grouping rsvp-interface-te-link-structure {
    description
      "Grouping for RSVP interface TE Link information.";

    container te-link {
      description
        "RSVP interface TE Link information.";

      container state {
        config false;
        description
          "RSVP interface TE Link state.";

        uses rsvp-interface-te-link-state;
      }
    }
  }

  grouping rsvp-interface-config {
    description
      "Grouping for RSVP interface config.";

    leaf interface-name {
      type oc-if:interface-id;
      description
        "Name of the interface.";
    }

    leaf enable {
      type boolean;
      description
        "Enable or disable RSVP under this interface.";
    }

    leaf hello-supported {
      type boolean;
      description
        "Enable/disable support for Hellos.";
    }
  }

  grouping rsvp-interface-state {
    description
      "Grouping for RSVP interface state.";

    leaf is-active {
      type boolean;
      description
        "Indicates if the interface is active or inactive";
    }

    leaf ifindex {
      type uint32;
      description
        "IfIndex of the interface";
    }

    leaf l3-ifindex {
      type uint32;
      description
        "IfIndex of the underlying L3 interface";
    }

    leaf l3-oper-status {
      type enumeration {
        enum UP {
          description
            "Interface is UP";
        }
        enum DOWN {
          description
            "Interface is DOWN";
        }
      }

      description
        "Oper status of the underlying L3 interface";
    }

    leaf oper-status {
      type enumeration {
        enum UP {
          description
            "Interface is UP";
        }
        enum DOWN {
          description
            "Interface is DOWN";
        }
      }

      description
        "Oper status of the RSVP interface";
    }

    leaf proto-oper-status {
      type enumeration {
        enum UP {
          description
            "Interface is UP";
        }
        enum DOWN {
          description
            "Interface is DOWN";
        }
      }

      description
        "Indicates RSVP protocol status of the RSVP interface";
    }

    leaf proto-hello-supported {
      type boolean;
      description
        "Indicates if Hellos are supported on this interface.";
    }

    leaf mtu {
      type uint32;
      description
        "MTU of the interface";
    }

    leaf speed {
      type oc-mplst:bandwidth-mbps;

      description
        "The interface speed.";
    }

    leaf ip-address {
      type inet:ip-address;
      description
        "Local interface IP address";
    }

    leaf neighbor-count {
      type uint32;
      description
        "Number of neighbors discovered on this interface";
    }

    leaf session-count {
      type uint32;
      description
        "Number of sessions on this interface";
    }

    leaf associated-tunnel-count {
      type uint32;
      description
        "Number of tunnels associated with this interface";
    }
  }

  grouping rsvp-interface-structure {
    description
      "Grouping for RSVP interfaces.";

    container interfaces {
      description
        "Interfaces level container.";

      list interface {
        key "interface-name";
        description
          "RSVP interface level configuration.";

        leaf interface-name {
          type leafref {
            path "../config/interface-name";
          }

          description
            "Name of the interface.";
        }      

        container config {
          description
            "Container for all interface level configuration.";

          uses rsvp-interface-config;
        }

        container state {
          config false;
          description
            "Container for all interface level state information.";

          uses rsvp-interface-config;
          uses rsvp-interface-state;
        }

        uses oc-if:interface-ref;

        uses rsvp-interface-te-link-structure;
        uses rsvp-interface-bw-structure;
        uses rsvp-interface-statistics-structure;

        uses rsvp-interface-neighbor-structure;
      }
    }
  }


  /*
   * RSVP preemption
   */
  grouping rsvp-preemption-config {
    description
      "Configuration for RSVP preemption";

    leaf mode {
      type identityref {
        base arc-rsvp-types:RSVP-PREEMPTION-MODE;
      }
      description
        "RSVP LSP preemption mode.";
    }

    leaf soft-timeout {
      type uint16 {
        range "0..300";
      }

      units "seconds";

      description
        "Timeout value for soft preemption to revert
         to hard preemption. The default timeout for
         soft-preemption is 30 seconds - after which
         the local system reverts to hard pre-emption.";

      reference
        "RFC5712: MPLS-TE soft preemption";
    }
  }

  grouping rsvp-preemption-structure {
    description
      "This grouping defines RSVP preemption";

    container preemption {
      description
        "RSVP preemption";

      container config {
        description
          "RSVP preemption configuration";

        uses rsvp-preemption-config;
      }

      container state {
        config false;
        description
          "RSVP preemption status";

        uses rsvp-preemption-config;
      }
    }
  }

  /*
   * RSVP Global
   */
  grouping rsvp-global-state {
    description
      "This grouping defines RSVP global state.";

    leaf admin-status {
      type identityref {
        base "arc-rsvp-types:RSVP-ADMIN-STATUS";
      }

      description
        "Indicates the global RSVP admin status";
    }

    leaf tlm-enabled {
      type boolean;
      description
        "Indicates if RSVP TE Link Module is enabled";
    }

    leaf router-id {
      type ietf-yang:dotted-quad;
      description
        "Router-ID used by RSVP. This is learned from IGP.";
    }

    leaf interface-count {
      type uint32;
      description
        "Total number of interfaces configured, across RSVP and MPLS-TE.";
    }

    leaf up-interface-count {
      type uint32;
      description
        "Total number of interfaces that are UP, across RSVP and MPLS-TE.";
    }

    leaf neighbor-count {
      type uint32;
      description
        "The number of neighbors.";
    }

    leaf up-neighbor-count {
      type uint32;
      description
        "The number of neighbors that are UP.";
    }
  }

  grouping rsvp-global-config {
    description
      "This grouping defines RSVP global configuration.";

    leaf hello-supported {
      type boolean;
      description
        "Enable/disable support for Hellos.";
    }

    leaf hello-interval {
      type uint32;
      description
        "Hello interval.";
      reference
        "RFC 3209: RSVP-TE: Extensions to RSVP for
                   LSP Tunnels.
         RFC 5495: Description of the Resource
                   Reservation Protocol - Traffic-Engineered
                   (RSVP-TE) Graceful Restart Procedures";
    }

    leaf refresh-reduction {
      type boolean;
      description
        "'true' if RSVP Refresh Reduction is enabled.
         'false' if RSVP Refresh Reduction is disabled.
         
         Enables all RSVP refresh reduction message
         bundling, RSVP message ID, reliable message delivery
         and summary refresh";
      reference
        "RFC2961 RSVP Refresh Overhead Reduction Extensions";
    }
  }

  grouping rsvp-global-structure {
    description
      "This grouping defines RSVP global structure.";

    container global {
      description
        "RSVP global level configuration and management.";

      container config {
        description
          "Container for RSVP global level configuration.";

        uses rsvp-global-config;
      }

      container state {
        config false;
        description
          "Container for RSVP global level oper data.";

        uses rsvp-global-config;
        uses rsvp-global-state;
      }

      uses rsvp-preemption-structure;
      uses rsvp-global-statistics-structure;
      uses rsvp-interface-address-structure;
      uses rsvp-igp-structure;
      uses rsvp-mpls-structure;
    }
  }


  /*
   * RSVP top-level structure
   */
  grouping rsvp-top {
    description
      "Top level RSVP protocol configuration and operational model.";

    container rsvp {
      description
        "Top level configuration for RSVP.";

      uses rsvp-global-structure;
      uses rsvp-interface-structure;
      uses rsvp-session-structure;
    }
  }


  /*
   * Define rsvp under network-instance RSVP protocol instance
   */
  augment "/oc-netinst:network-instances/oc-netinst:network-instance" +
          "/oc-netinst:protocols/oc-netinst:protocol" {

    uses rsvp-top {
      when "derived-from-or-self(./oc-netinst:config" +
      "/oc-netinst:identifier, 'arc-oc-pol-types:RSVP') and " +
      "(../../oc-netinst:name = 'default')" {

        description
          "This augmentation is valid for protocol RSVP, and only
           if the network instance is default.";
      }

      description
        "RSVP protocol augmentation of protocol.";
    }
  }
}
