module arcos-openconfig-platform-psu-augments {

  yang-version 1.1;
  namespace "http://yang.arrcus.com/arcos/openconfig/platform/psu/augments";
  prefix arc-oc-plt-psu-aug;

  // import some basic types
  import openconfig-platform {
    prefix oc-platform;
  }

  import openconfig-types {
    prefix oc-types;
  }

  organization
    "Arrcus, Inc.";
  contact
    "Arrcus, Inc.
     2077 Gateway Place
     Suite 400
     San Jose, CA 95110
     E-mail: yang-support@arrcus.com";
  description
    "This module contains definitions for the
     ArcOS Network instance augments.
     Copyright (c) 2023 by Arrcus, Inc.
     All rights reserved.";

  revision 2023-11-09 {
    description "Initial revision.";
  }

  augment "/oc-platform:components/oc-platform:component/oc-platform:power-supply/oc-platform:state" {
    leaf input-power {
      type uint32;
      units watts;
    }
    description
      "Input power supplied by Power supply in watts";
  }
}
