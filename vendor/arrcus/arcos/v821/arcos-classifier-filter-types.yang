module arcos-classifier-filter-types {
  yang-version 1.1;
  namespace "http://yang.arrcus.com/arcos/classifier/filter/types";
  prefix arc-cfr-fltr-types;

  organization
    "Arrcus, Inc.";
  contact
    "Arrcus, Inc.
     Customer Service
     Postal: 2077 Gateway Place
     San Jose, CA 95110
     Tel: +1 1XXX XXX-XXXX
     E-mail: xxx@arrcus.com";
  description
    "YANG data model for classifier filter and exception types.

     Copyright (c) 2016-2023 by Arrcus, Inc.
     All rights reserved.";
  
  revision 2023-05-05 {
    description
      "Added new Filter type ANY to match on all traffic";
  }

  identity LOGICAL_OPERATION_TYPE {
    description
      "Across the filter logical operation types: match-any, match-all";
  }

  identity MATCH_ANY_FILTER {
    base LOGICAL_OPERATION_TYPE;
    description
      "Logical OR operation across filters in a given classifier";
  }

  identity MATCH_ALL_FILTER {
    base LOGICAL_OPERATION_TYPE;
    description
      "Logical AND operation across filters in a given classifier";
  }

  identity FILTER_TYPE {
    description
      "This is an identity of base filter-type";
  }

  identity COS {
    base FILTER_TYPE;
    description
      "Layer-2 802.1p Class of Service filter-type";
  }

  identity DSCP {
    base FILTER_TYPE;
    description
      "Layer-3 IP Differentiated Service filter-type";
  }

  identity LOCAL_TC {
    base FILTER_TYPE;
    description
      "Local Priority Traffic Class filter-type";
  }

  identity MPLS_TC {
    base FILTER_TYPE;
    description
      "MPLS Traffic Class code-point filter-type";
  }

  identity ACL {
    base FILTER_TYPE;
    description
      "Access Control List filter-type";
  }

  identity ANY {
    base FILTER_TYPE;
    description
      "Filter type to match all traffic";
  }

  identity SRC_QOS_CLASS {
    base FILTER_TYPE;
    description
      "Source QoS class id filter-type";
  }

  identity DST_QOS_CLASS {
    base FILTER_TYPE;
    description
      "Destination QoS class id filter-type";
  }

  identity EXCEPTION {
    base FILTER_TYPE;
    description
      "A filter-type that captures certain exceptions";
  }

  identity EXCEPTION_TYPE {
    description
      "This is an identity of base exception-type";
  }

  identity L3DESTMISS {
    base EXCEPTION_TYPE;
    description "An exception-type that captures packets that fail "
              + "ip destination lookup in forwarding";
  }

  identity SELFIP {
    base EXCEPTION_TYPE;
    description "An exception-type that captures packets that match "
              + "router address";
  }

  identity GLEAN {
    base EXCEPTION_TYPE;
    description "An exception-type that captures packets which does "
              + "not have dest mac resolved";
  }

  identity ARP {
    base EXCEPTION_TYPE;
    description "An exception-type that captures special ARP packets";
  }

  identity MIRROR {
    base EXCEPTION_TYPE;
    description "An exception-type that captures packets which are "
              + "mirror or sflow sampled packets";
  }
}
