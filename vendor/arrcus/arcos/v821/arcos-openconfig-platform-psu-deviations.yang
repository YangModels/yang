module arcos-openconfig-platform-psu-deviations {
  yang-version 1.1;
  namespace "http://yang.arrcus.com/arcos/openconfig/platform/psu/deviations";
  prefix arc-oc-platform-psu-dev;

  import openconfig-platform {
    prefix oc-platform;
  }

  import openconfig-platform-psu {
    prefix oc-platform-psu;
  }

  organization
    "Arrcus, Inc.";

  contact
    "Email: eng@arrcus.com";

  description
    "This module defines deviation statements for Arrcus
     implemention of the openconfig platform module.";

  revision 2018-08-14 {
    description "ArcOS release 2.2.1";
  }

  revision 2017-07-10 {
    description
      "Initial Revision
       * xxx not suppsued.
      ";

    reference
      "RFC 6020: YANG - A Data Modeling Language for the
       Network Configuration Protocol (NETCONF)";
  }


  deviation "/oc-platform:components/oc-platform:component/oc-platform:power-supply/oc-platform:config" {
    deviate not-supported;
   description "Not supported in this release";
  }
  
 /* deviation "/oc-platform:components/oc-platform:component/oc-platform:power-supply/oc-platform:config/oc-platform-psu:enabled" {
     deviate not-supported;
     description "Not suppsued in this release";
  }*/


  deviation "/oc-platform:components/oc-platform:component/oc-platform:power-supply/oc-platform:state/oc-platform-psu:input-current" {
    deviate replace {
        type uint32;
    }
  }
  deviation "/oc-platform:components/oc-platform:component/oc-platform:power-supply/oc-platform:state/oc-platform-psu:input-voltage" {
    deviate replace {
        type uint32;
    }
  }
  deviation "/oc-platform:components/oc-platform:component/oc-platform:power-supply/oc-platform:state/oc-platform-psu:output-current" {
    deviate replace {
       type uint32;
    }
  }
  deviation "/oc-platform:components/oc-platform:component/oc-platform:power-supply/oc-platform:state/oc-platform-psu:output-voltage" {
    deviate replace {
        type uint32;
    }
  }
  deviation "/oc-platform:components/oc-platform:component/oc-platform:power-supply/oc-platform:state/oc-platform-psu:output-power" {
    deviate replace {
        type uint32;
    }
  }
}
