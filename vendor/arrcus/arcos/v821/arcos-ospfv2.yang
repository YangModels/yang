module arcos-ospfv2 {

  yang-version "1.1";

  namespace "http://yang.arrcus.com/arcos/ospfv2";

  prefix "arc-ospfv2";

  import openconfig-network-instance { prefix "oc-netinst"; }
  import arcos-ospf { prefix "arc-ospf"; }

  // Include submodules
  include arcos-ospfv2-common;
  include arcos-ospfv2-area-interface;
  include arcos-ospfv2-lsdb;

  organization
    "Arrcus, Inc";

  contact
    "Arrcus, Inc.
     2077 Gateway Place
     Suite 400
     San Jose, CA 95110
     
     E-mail: yang-support@arrcus.com";

  description
    "A model for Open Shortest Path First (OSPF) v2 protocol";

  revision "2020-01-01" {
    description
      "Initial version";
  }

  augment "/oc-netinst:network-instances/oc-netinst:network-instance" +
          "/oc-netinst:protocols/oc-netinst:protocol/arc-ospf:ospfv2" +
          "/arc-ospf:as-scope" {
    uses ospfv2-lsdb-structure;
  }

  /*
   * Augment ospfv2 areas area
   */
  augment "/oc-netinst:network-instances/oc-netinst:network-instance" +
          "/oc-netinst:protocols/oc-netinst:protocol/arc-ospf:ospfv2" +
          "/arc-ospf:areas/arc-ospf:area" {
    uses ospfv2-lsdb-structure;
  }

  /*
   * Augment ospfv2 areas area interfaces interface
   */
  augment "/oc-netinst:network-instances/oc-netinst:network-instance" +
          "/oc-netinst:protocols/oc-netinst:protocol/arc-ospf:ospfv2" +
          "/arc-ospf:areas/arc-ospf:area" +
          "/arc-ospf:interfaces/arc-ospf:interface" {
    uses arc-ospf:ospf-auth-structure;
  }

  /*
   * Augment ospfv2 areas area interfaces interface neighbors neighbor
   */
  augment "/oc-netinst:network-instances/oc-netinst:network-instance" +
          "/oc-netinst:protocols/oc-netinst:protocol/arc-ospf:ospfv2" +
          "/arc-ospf:areas/arc-ospf:area" +
          "/arc-ospf:interfaces/arc-ospf:interface" +
          "/arc-ospf:neighbors/arc-ospf:neighbor" {
    uses ospfv2-area-interface-neighbor-bfd-structure;
  }

  /*
   * Augment ospfv2 areas area interfaces interface neighbors neighbor state
   */
  augment "/oc-netinst:network-instances/oc-netinst:network-instance" +
          "/oc-netinst:protocols/oc-netinst:protocol/arc-ospf:ospfv2" +
          "/arc-ospf:areas/arc-ospf:area" +
          "/arc-ospf:interfaces/arc-ospf:interface" +
          "/arc-ospf:neighbors/arc-ospf:neighbor/arc-ospf:state" {
    uses ospfv2-area-interface-neighbor-state;
  }
}
