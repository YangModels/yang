module arcos-openconfig-aft {
  yang-version 1.1;
  namespace "http://yang.arrcus.com/arcos/openconfig/aft";
  prefix arc-oc-aft;

  import openconfig-aft {
    prefix oc-aft;
  }

  grouping afts-units-top {
    description
      "Top-level grouping allowing per-protocol instantiation
       of the AFT. Extends the AFT to multiple forwarding
       units";

    container afts-units {
      config false;

      description
        "Extends the AFT to multiple forwarding units.";

      list aft-unit-entry {
        key "unit-id";
        description
          "List of forwarding units";

        leaf unit-id {
          type uint32;
          description
            "Uniquely identifies a forwarding unit";
        }

        uses oc-aft:aft-top;
      }
    }
  }
}
