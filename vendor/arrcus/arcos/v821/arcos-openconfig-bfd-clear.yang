module arcos-openconfig-bfd-clear {
  yang-version 1.1;
  namespace "http://yang.arrcus.com/arcos/openconfig/bfd/clear";
  prefix arc-oc-bfd-clr;

  import arcos-common-types {
    prefix arc-common-types;
  }

  import openconfig-bfd {
    prefix oc-bfd;
  }

  import openconfig-network-instance {
    prefix oc-ni;
  }

  import openconfig-interfaces {
    prefix oc-if;
  }

  organization
    "Arrcus, Inc";

  contact
    "Arrcus, Inc.
     2077 Gateway Place 
     Suite 400
     San Jose, CA 95110
     E-mail: yang-support@arrcus.com";

  description
    "This module defines clear bfd model of the Arrcus BFD module.
     Copyright (c) 2016-2023 by Arrcus, Inc.
     All rights reserved.";

  revision 2023-05-06 {
    description
      "Initial Revision";
  }

  rpc bfd-clear-all {
    description
      "Clear all BFD sessions";

    output {
      uses arc-common-types:generic-rpc-response;
    }
  }

  rpc bfd-clear-session {
    input {
      leaf network-instance {
        type leafref {
          path "/oc-ni:network-instances/oc-ni:network-instance/oc-ni:config/oc-ni:name";
        }
        mandatory true;
        description
          "The associated VRF name";
      }

      leaf ip {
        type leafref {
          path "/oc-bfd:bfd/oc-bfd:interfaces/oc-bfd:interface/oc-bfd:peers/oc-bfd:peer/oc-bfd:state/oc-bfd:local-address";
        }
        description
          "The session local address";
      }

      leaf interface {
        type leafref {
          path "/oc-if:interfaces/oc-if:interface/oc-if:config/oc-if:name";
        }
        description
          "Interface name";
      }
    }

    output {
      uses arc-common-types:generic-rpc-response;
    }
  }

  rpc micro-bfd-clear-all {
    description
      "Clear all Micro BFD sessions";

    output {
      uses arc-common-types:generic-rpc-response;
    }
  }

  rpc micro-bfd-clear-session {
    input {
      leaf interface {
        type leafref {
          path "/oc-if:interfaces/oc-if:interface/oc-if:config/oc-if:name";
        }
        description
          "Interface name";
      }
    }

    output {
      uses arc-common-types:generic-rpc-response;
    }
  }
}
