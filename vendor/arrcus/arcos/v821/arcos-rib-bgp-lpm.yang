module arcos-rib-bgp-lpm {
  yang-version 1.1;
  namespace "http://yang.arrcus.com/arcos/rib/bgp/lpm";
  prefix arc-rib-bgp-lpm;

  import openconfig-network-instance {
    prefix oc-ni;
  }

  import ietf-inet-types {
    prefix inet;
  }

  import openconfig-rib-bgp {
    prefix oc-rib-bgp;
  }

  import arcos-openconfig-rib-bgp-augments {
    prefix arc-oc-rib-bgp-aug;
  }

  import arcos-openconfig-bgp-types {
    prefix arc-oc-bgp-types;
  }

  grouping bgp-lpm-entry {
    description
      "BGP RIB LPM show command";
    leaf prefix {
      type arc-oc-bgp-types:bgp-prefix-type;
    }
  }

  grouping bgp-rib-lpm-top {
    container bgp-rib-lpm {
      description
        "Perform a longest prefix match lookup in the BGP RIB";
      action ipv4-unicast {
        description
          "IPV4 route lookup";
          input {
            leaf prefix {
              type inet:ipv4-prefix;
              mandatory true;
              description
                "The IPV4 address to be looked up from the BGP RIB";
            }
          }
          output {
            uses bgp-lpm-entry;
          }
      }

      action ipv6-unicast {
        description
          "IPV6 route lookup";
          input {
            leaf prefix {
              type inet:ipv6-prefix;
              mandatory true;
              description
                "The IPV6 address to be looked up from the BGP RIB";
            }
          }
          output {
            uses bgp-lpm-entry;
          }
      }

      action ipv4-labeled-unicast {
        description
          "IPV4 labeled unicast route lookup";
          input {
            leaf prefix {
              type inet:ipv4-prefix;
              mandatory true;
              description
                "The IPV4 address to be looked up from the BGP RIB";
            }
          }
          output {
            uses bgp-lpm-entry;
          }
      }

      action ipv6-labeled-unicast {
        description
          "IPV6 labeled unicast route lookup";
          input {
            leaf prefix {
              type inet:ipv6-prefix;
              mandatory true;
              description
                "The IPV6 address to be looked up from the BGP RIB";
            }
          }
          output {
            uses bgp-lpm-entry;
          }
      }

      action ipv4-flowspec {
        description
          "Flowspec IPV4 unicast route lookup";
          input {
            leaf prefix {
              type string;
              mandatory true;
              description
                "The Flowspec ipv4 unicast address to be looked up from BGP RIB";
            }
          }
          output {
            uses bgp-lpm-entry;
          }
      }

      action ipv6-flowspec {
        description
          "Flowspec IPV6 unicast route lookup";
        input {
          leaf prefix {
            type string;
            mandatory true;
            description
              "The Flowspec ipv6 unicast address to be looked up from the BGP RIB";
          }
        }
        output {
          uses bgp-lpm-entry;
        }
      }

      action vpnv4-flowspec {
        description
          "Flowspec VPNV4 unicast route lookup";
          input {
            leaf prefix {
              type string;
              mandatory true;
              description
                "The Flowspec vpnv4 unicast address to be looked up from BGP RIB";
            }
          }
          output {
            uses bgp-lpm-entry;
          }
      }

      action vpnv6-flowspec {
        description
          "Flowspec VPNV6 unicast route lookup";
        input {
          leaf prefix {
            type string;
            mandatory true;
            description
              "The Flowspec vpnv6 unicast address to be looked up from the BGP RIB";
          }
        }
        output {
          uses bgp-lpm-entry;
        }
      }

      action l2vpn-evpn {
        description
          "L2VPN EVPN route lookup";
        input {
          leaf prefix {
            type string;
            mandatory true;
            description
              "The L2VPN EVPN address to be looked up from the BGP RIB";
          }
        }
        output {
          uses bgp-lpm-entry;
        }
      }

      action l3vpn-ipv4-unicast {
        description
          "L3VPN IPV4 Unicast route lookup";
        input {
          leaf prefix {
            type string;
            mandatory true;
            description
              "The l3vpn ipv4 address to be looked up from the BGP RIB";
          }
        }
        output {
          uses bgp-lpm-entry;
        }
      }

      action l3vpn-ipv6-unicast {
        description
          "L3VPN IPV6 Unicast route lookup";
        input {
          leaf prefix {
            type string;
            mandatory true;
            description
              "The l3vpn ipv6 address to be looked up from the BGP RIB";
          }
        }
        output {
          uses bgp-lpm-entry;
        }
      }
    }
  }

  augment "/oc-ni:network-instances/oc-ni:network-instance" {
    uses bgp-rib-lpm-top;
  }
}
