module arcos-hardware-platform-pfc-stats {
  yang-version 1.1;
  namespace "http://yang.arrcus.com/arcos/hardware/platform/pfc/stats";
  prefix arcos-hw-pfc-stats;

  import openconfig-interfaces { prefix "oc-if"; }

  organization
    "Arrcus, Inc.";
  contact
    "Arrcus, Inc.
     2077 Gateway Place
     San Jose, CA 95110
     Tel: +1 (408) 884-1965
     E-mail: eng@arrcus.com";
  description
    "YANG data-model for datapath pfc stats";

  revision "2025-04-14" {
    description
      "Added profile name leaf";
  }
  revision "2025-03-14" {
    description
      "Change xon to xon-offset.";
  }
  revision "2025-03-02" {
    description
      "Added lossless and watchdog status parameters";
  }
  revision "2025-02-20" {
    description
      "Reorganised the yang to support traffic-class as list";
  }
  revision "2024-05-30" {
    description
      "Enable support for PFC pause frame statistics";
  }

  grouping pfc-stats-top {
    description
      "Grouping of pfc operational data per interface.";
      list interface {
        key "ifname";

        description
          "The list of interfaces with pfc associated";

        leaf ifname {
          type leafref {
            path "/oc-if:interfaces/oc-if:interface/oc-if:config/oc-if:name";
          }
          description
            "The interface name key for interface list";
        }

        leaf profile {
          type string {
            length "0..64";
          }
          description "Name of PFC profile";
        }

        list traffic-class {
          key tcid;
          leaf tcid {
            type uint8;
            description
              "traffic-class id";
          }
          leaf port-tx-enabled{
            type boolean;
            description
              "PFC status on TX";
          }
          leaf port-rx-enabled{
            type boolean;
            description
              "PFC status on RX";
          }
          uses pfc-lossless-state;
          uses pfc-watchdog-state;
          uses pfc-statistics;
        }
      }
  }

  grouping pfc-statistics {
    container statistics {
      leaf pause-frames-tx {
        type uint64;
        description
          "Number of pause frames transmitted";
      }
      leaf pause-frames-rx {
        type uint64;
        description
          "Number of pause frames received";
      }
      leaf tx-xoff-transitions {
        type uint64;
        description
          "Number of transitions from Xon to Xoff";
      }
      leaf rx-xoff-transitions {
        type uint64;
        description
          "Number of transitions from Xon to Xoff";
      }
      leaf watchdog-recovery-count {
        type uint64;
        description
          "Number of watchdog recoveries occurred";
      }
      leaf recovery-duration {
        type uint64;
        description
          "Accumulated time (in milliseconds) a port stays in pfc
           deadlock state per-PFC priority";
      }
    }
  }

  grouping pfc-lossless-state {
    container lossless {
      leaf lossless-enabled {
        type boolean;
        description
          "Lossless state";
      }
      leaf hdrm {
        type uint64;
        description
          "Headroom buffers configured";
      }
      leaf xoff {
        type string;
        description
          "XOFF value configured";
      }
      leaf xon-offset {
        type uint64;
        description
          "XON Offset value configured";
      }
    }
  }

  grouping pfc-watchdog-state {
    container watchdog {
      leaf watchdog-enabled {
        type boolean;
        description
          "Watchdog state";
      }
      leaf detection-time {
        type uint64;
        description
          "Watchdog detection time configured";
      }
      leaf recovery-time {
        type uint64;
        description
          "Watchdog recovery time configured";
      }
    }
  }
}
