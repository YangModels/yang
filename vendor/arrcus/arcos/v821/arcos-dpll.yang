module arcos-dpll {
  yang-version 1.1;
  namespace "http://yang.arrcus.com/arcos/dpll/";
  prefix arc-dpll;

  import tailf-common {
    prefix tailf;
  }

  import openconfig-interfaces {
    prefix oc-if;
  }

  import ietf-yang-types {
    prefix yang;
  }

  import arcos-features {
    prefix arc-features;
  }

  organization
    "Arrcus, Inc";

  contact
    "Arrcus, Inc.
     2077 Gateway Place
     Suite 400
     San Jose, CA 95110
     E-mail: yang-support@arrcus.com";

  description
    "This module lists arrcus dpll related information.
     Copyright (c) 2023 by Arrcus, Inc.
     All rights reserved.";

  revision 2023-05-12 {
    description
      "Add dpll signal-status-at-input details";
  }

  typedef signal-status {
      type enumeration {
          enum not-present {
              value 0;
              description "Signal Status at input is not present";
          }
          enum present {
              value 1;
              description "Signal Status at input is present";
          }
      }
      description
          "DPLL Signal Status at input";
  }

  grouping dpll-signal-status {
      container signal-status-at-input {
              config false;
          leaf smb-1pps {
              type signal-status;
              description
                  "1PPS Sub-miniature B.";
          }
          leaf smb-10Mhz {
              type signal-status;
              description
                  "10MHz Sub-miniature B.";
          }
          leaf bits {
              type signal-status;
              description
                  "Building-Integrated Timing Supply port.";
          }
          leaf gnss-10Mhz {
              type signal-status;
              description
                  "10MHz Global Navigation Satellite System.";
          }
          leaf gnss-1pps {
              type signal-status;
              description
                  "1PPS Global Navigation Satellite System.";
          }
          leaf rj45-1pps {
              type signal-status;
              description
                  "1PPS Registered-Jack45.";
          }
      }
  }

  container dpll {
	  uses dpll-signal-status;
  }

}
