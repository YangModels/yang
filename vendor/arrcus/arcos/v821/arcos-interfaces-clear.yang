module arcos-interfaces-clear {
  yang-version 1.1;
  namespace "http://yang.arrcus.com/arcos/interfaces/clear";
  prefix arc-if-clr;

  container if-clear {
    description
      "Clear Interface statistics";

    action counters {
      description
        "Clear Interface statistic counters";

      input {
        leaf name {
          type string;
          mandatory true;
          description
            "The interface name whose counters needs to be cleared.
             Use 'all' for all interfaces";
        }
      }
      output {
        leaf result {
        type string;
          description
          "The status of operation";
        }
      }
    }
  }
}
