module arcos-sr-policy-debug {
  yang-version 1.1;
  namespace "http://yang.arrcus.com/arcos/sr-policy/debug";
  prefix arc-sr-pol-dbg;

  import openconfig-policy-types {
    prefix oc-pol-types;
  }

  import arcos-debug {
    prefix arc-dbg;
  }

  organization
    "Arrcus, Inc.";

  contact
    "Arrcus, Inc.
     2077 Gateway Place
     Suite 400
     San Jose, CA 95110
     E-mail: yang-support@arrcus.com";

  description
    "This module defines debug for SR-Policy module

     Copyright (c) 2016-2024 by Arrcus, Inc.
     All rights reserved.";

  revision 2024-01-04 {
    description
      "Move SR-Policy debug to global list";
  }

  grouping srpolicy-debug-top {
    container srpolicy {
      description
        "This container defines instance-specific SR-Policy debug information.";
      config false;

      uses arc-dbg:debug-component-top;
    }
  }

  augment "/arc-dbg:debug/arc-dbg:debug-attach-points" {
    uses srpolicy-debug-top {
      when "arc-dbg:component = 'srpolicy'" {
        description
          "SR-Policy debug";
      }
      description
        "Debug information related to a specific instance of SR-Policy";
    }
  }
}
