module arcos-datapath-aft-types {
  yang-version "1.1";

  namespace "http://yang.arrcus.com/arcos/datapath/aft/types";
  prefix "arcos-dp-aft-types";

  organization
    "Arrcus, Inc.";
  
  contact
     "Arrcus, Inc.
      2077 Gateway Place
      Suite 400
      San Jose, CA 95110 
      E-mail: yang-support@arrcus.com";
  
  description
    "Types related to the ArcOS datapath Abstract Forwarding
     Table (AFT) model
     
     Copyright (c) 2016-2024 by Arrcus, Inc. All rights reserved.";

  revision 2024-01-02 {
    description
      "Adding mandatory statements for
         - contact
         - organization
         - description
         - revision";
  }

  typedef encapsulation-header-type {
    type enumeration {
      enum GRE {
        description
          "The encapsulation header is a Generic Routing Encapsulation
          header.";
        value 5;
      }
      enum IPV4 {
        description
          "The encapsulation header is an IPv4 packet header";
        value 4;
      }
      enum IPV6 {
        description
          "The encapsulation header is an IPv6 packet header";
        value 6;
      }
      enum MPLS {
        description
          "The encapsulation header is one or more MPLS labels indicated
          by the pushed and popped label stack lists.";
        value 2;
      }
      enum VXLAN_T {
        description
          "The encapsulation header is a VXLAN header.";
        value 1;
      }
      enum SRV6 {
        description
          "The encapsulation header is used for Segment Routing.
           Destination IP comes from the top of the SID list (traverse order).
           If reduced mode is on, packet might not have SRH.";
        value 3;
      }
    }
    description
      "Types of tunnel encapsulation that are supported by systems as either
      head- or tail-end. Keep in sync with tunnel.encap.enum.";
  }

  typedef dpal-nexthop-action-type {
    type enumeration {
      enum GLEAN {
        value 1;
      }
      enum DROP {
        value 2;
      }
      enum LOCAL {
        value 3;
      }
      enum CONNECTED {
        value 4;
      }
      enum MPLS_CONNECTED {
        value 5;
      }
      enum PUNT_TO_CPU {
        value 6;
      }
      enum VXLAN {
        value 7;
      }
      enum UNRESOLVED {
        value 8;
      }
    }
  }

  typedef dpal-nexthop-type {
    type enumeration {
      enum SINGLE {
        value 1;
      }
      enum ECMP {
        value 2;
      }
      enum PROTECTED {
        value 3;
      }
      enum VXLAN_NH {
        value 4;
      }
      enum GTP {
        value 5;
      }
    }
  }

  typedef dpal-nexthop-protected-type {
    type enumeration {
      enum ACTIVE {
        value 1;
      }
      enum BACKUP {
        value 2;
      }
    }
  }
  
  typedef dpal-nexthop-protected-state {
    type enumeration {
      enum ACTIVE {
        value 1;
      }
      enum PASSIVE {
        value 2;
      }
    }
  }
}
