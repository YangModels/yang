module arcos-bridge-isolation {
  yang-version 1.1;
  namespace "http://yang.arrcus.com/arcos/bridge-isolation";
  prefix arc-brdg-isltn;

  import iana-if-type {
    prefix ianaift;
  }

  import openconfig-interfaces {
    prefix oc-if;
  }

  import openconfig-yang-types {
    prefix oc-yang;
  }


  grouping bridge-isolation-top {
    description
      "Top-level grouping for layer 2 port bridge isolation feature";

    container bridge-isolation {
      description
        "Bridge isolation feature for a layer 2 switch port";
      leaf isolation {
        description
          "Enable/Disable bridge isolation feature on a layer 2 switch port";
        type enumeration {
          enum enable {
            description
              "Enable bridge isolation feature on a layer 2 switch port";
          }
          enum disable {
            description
              "Disable bridge isolation feature on a layer 2 switch port";
          }
        }
      }
      container state {
        config false;
        leaf isolation-drop-packets {
          type oc-yang:counter64;
          description
            "egress packet drop count because of bridge isolation";
        }
        leaf isolation-drop-octets {
          type oc-yang:counter64;
          description
            "egress octet drop count because of bridge isolation";
        }
      }
    }
  }

  augment "/oc-if:interfaces/oc-if:interface" {
    uses bridge-isolation-top {
      when "(current()/oc-if:name != 'ma1' and " +
           "(starts-with(current()/oc-if:name, 'swp')))";
    }
  }
}
