module arcos-system-logging-types {
  yang-version 1.1;
  namespace "http://yang.arrcus.com/arcos/system/logging/types";
  prefix arc-sys-log-types;

  organization
    "Arrcus, Inc.";

  contact
    "Arrcus, Inc.
     2077 Gateway Place
     Suite 400
     San Jose, CA 95110

     E-mail: yang-support@arrcus.com";

  description
    "This module defines native ArcOS system logging
     types.

     Copyright (c) 2016-2023 by Arrcus, Inc.
     All rights reserved.";


  revision 2023-07-25 {
    description "Add logging format types";
  }

  revision 2020-02-26 {
    description "Initial version";
  }

  identity LOG_TIMESTAMP_FORMAT {
    description
      "Base identity for logging timestamp formats";
  }

  identity TRADITIONAL {
    base LOG_TIMESTAMP_FORMAT;
    description
      "RFC3164 Traditional timestamp format";
  }

  identity PRECISION {
    base LOG_TIMESTAMP_FORMAT;
    description
      "RFC3339 High precision timestamp format";
  }

  identity SYSLOG_FORMAT {
    description
      "Base identity for syslog format";
  }

  identity SYSLOG_TRADITIONAL {
    base SYSLOG_FORMAT;
    description
      "RFC_3164 BSD Syslog format";
  }

  identity SYSLOG_RFC_5424 {
    base SYSLOG_FORMAT;
    description
      "RFC_5424 Syslog format";
  }

}
