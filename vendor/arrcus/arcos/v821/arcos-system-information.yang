module arcos-system-information {
  yang-version 1.1;
  namespace "http://yang.arrcus.com/arcos/system-information";
  prefix arc-sys-info;

  description
    "This module is for system modifiable read/write nodes";

  grouping system-information-top {
    description
      "Top-level grouping for system information";

    container system-information {
      description
        "Top-level container for system-information data";

      leaf version {
        type string;
        description
          "The version field, while r/w is meant to be system
           defined and not editable by clients.  The purpose
           is to carry a version node within a configuration
           datastore for purposes of exported configurations.
           Access to the node is restricted on the backend.";
      }
    }
  }

  uses system-information-top;

}
