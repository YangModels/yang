module arcos-hardware-platform-types {
  yang-version 1.1;
  namespace "http://yang.arrcus.com/arcos/hardware/platform/types";
  prefix arc-hw-platform-types;

  revision 2025-02-18 {
    description
      "Adding the ACL_SCALE option from KBP_MODE identity.";
   }

  revision 2024-05-20 {
    description
      "Adding the MUP option from KBP_MODE identity.";
   }

  revision 2024-05-08 {
    description
      "Adding the FWD_AND_RPF option in KBP_MODE identity.";
  }

  revision 2024-03-12 {
    description
      "Removing the ACL_AND_FWD option from KBP_MODE identity.";
  }

  revision 2024-02-09 {
    description
      "Adding an identity KBP_MODE to represent the possible operating modes for external tcam.";
  }

  typedef MMU_QUEUE_ALPHA_VALUE {
    type enumeration {
      enum 1/128;
      enum 1/64;
      enum 1/32;
      enum 1/16;
      enum 1/8;
      enum 1/4;
      enum 1/2;
      enum 1;
      enum 2;
      enum 4;
      enum 8;
    }
  }

  identity SWITCH_FORWARDING_MODE {
    description "Base type for switch forwarding modes";
  }

  identity STORE_AND_FORWARD {
    base SWITCH_FORWARDING_MODE;
    description "Store and forward mode";
  }

  identity CUT_THROUGH {
    base SWITCH_FORWARDING_MODE;
    description "Cut through forwarding mode";
  }

  identity BUFFER_STATS_MODE {
    description "Base type for buffer stats modes";
  }

  identity BUFFER_STATS_MODE_NONE {
    base BUFFER_STATS_MODE;
    description "Buffer stats collection is disabled";
  }

  identity BUFFER_STATS_MODE_PEAK {
    base BUFFER_STATS_MODE;
    description "Buffer stats collected reflect peak usage";
  }

  identity BUFFER_STATS_MODE_PEAK_RESET {
    base BUFFER_STATS_MODE;
    description "Buffer stats collected reflect peak usage and reset the stats after every show";
  }

  identity KBP_MODE {
    description "Base type for KBP configuration mode";
  }

  identity ACL_ONLY {
    base KBP_MODE;
    description "ACL only mode";
  }

  identity ACL_SCALE {
    base KBP_MODE;
    description "Scaled ACL mode";
  }

  identity FWD_ONLY {
    base KBP_MODE;
    description "FWD only mode";
  }

  identity FWD_AND_RPF {
    base KBP_MODE;
    description "FWD and RPF mode";
  }

  identity MUP {
    base KBP_MODE;
    description "MUP only mode";
  }

  typedef ECMP_MODE {
    type enumeration {
      enum RESILIENT_MODE {
        value 1;
      }
      enum DLB_MODE {
        value 2;
      }
    }
  }

  typedef  inact-int-uint32 {
    type uint32 {
      range "16..32767";
     }
  }
}
