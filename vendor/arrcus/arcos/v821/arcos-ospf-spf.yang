submodule arcos-ospf-spf {

  yang-version "1.1";

  belongs-to arcos-ospf {
    prefix "arc-ospf";
  }

  import arcos-ospf-types { prefix "arc-ospf-types"; }

  // Include submodules
  include arcos-ospf-common;

  organization
    "Arrcus, Inc";

  contact
    "Arrcus, Inc.
     2077 Gateway Place
     Suite 400
     San Jose, CA 95110
     
     E-mail: yang-support@arrcus.com";

  description
    "This submodule provides OSPF configuration and operational
    state parameters that are related to SPF computation, timers
    and logs.";

  revision "2020-01-01" {
    description
      "Initial version";
  }

  /*
   * SPF Config and State
   */
  grouping ospf-spf-state {
    description
      "This grouping defines OSPF SPF computation state.";

    leaf spf-delay-sm-state {
      type identityref {
        base "arc-ospf-types:OSPF_SPF_DELAY_SM_STATE";
      }

      description
        "The SPF Delay state-machine current state.";
    }

    leaf spf-pending {
      type boolean;
      description
        "Indicates if SPF computation is currently pending.";
    }

    leaf full-spf-pending {
      type boolean;
      description
        "Indicates if Full SPF computation is currently pending.";
    }
  }

  grouping ospf-spf-comp-state {
    description
      "This grouping defines state corresponding to a particular
      run of SPF computation.";

    leaf log-id {
      type uint32;
      description
        "The ID of the SPF log entry.";
    }

    leaf trigger-count {
      type uint32;
      description
        "The total number of triggers generated for this SPF computation.";
    }

    leaf spf-start-timestamp {
      type string;
      description
        "The timestamp of the start of SPF computation.";
    }

    leaf spf-delay-sm-state {
      type identityref {
        base "arc-ospf-types:OSPF_SPF_DELAY_SM_STATE";
      }

      description
        "The SPF Delay state-machine state at the time
         of the SPF computation.";
    }

    leaf full-spf {
      type boolean;
      description
        "Indicates if the Full SPF was computed.";
    }

    leaf spf-duration {
      type uint64;
      units microseconds;
      description
        "The total time taken for completing this SPF computation.";
    }

    leaf spt-duration {
      type uint64;
      units microseconds;
      description
        "The total time taken for completing this SPT calculation.";
    }

    leaf spt-reachable-node-count {
      type uint32;
      description
        "The number of reachable nodes ouput from the SPF
         computation.";
    }

    leaf spt-unreachable-node-count {
      type uint32;
      description
        "The number of nodes unreachable nodes output from
         the SPF computation.";
    }
  }

  /*
   * SPF Throttle
   */
  grouping ospf-spf-throttle-timers-config {
    description
      "Configuration parameters relating to SPF throttle timers";

    leaf spf-initial-delay {
      type uint32;
      units milliseconds;
      description
        "The initial delay between IGP event and SPF computation";
    }

    leaf spf-short-delay {
      type uint32;
      units milliseconds;
      description
        "The short delay between IGP event and SPF computation";
    }

    leaf spf-long-delay {
      type uint32;
      units milliseconds;
      description
        "The long delay between IGP event and SPF computation";
    }

    leaf time-to-learn-interval {
      type uint32;
      units milliseconds;
      description
        "The maximum duration typically needed to learn all
         the IGP events related to a single failure";
    }

    leaf holddown-interval {
      type uint32;
      units milliseconds;
      description
        "The time required with no received IGP event before
         considering the IGP to be stable again";
    }
  }

  grouping ospf-spf-throttle-structure {
    description
      "This grouping defines OSPF SPF throttle control.";

    container throttle {
        description
          "This container defines OSPF SPF throttle control.";
        reference
          "RFC 8405 - Shortest Path First (SPF) Back-Off Delay Algorithm
           for Link-State IGPs";

      container timers {
        description
          "This container defines OSPF SPF throttle timers.";

        container config {
          description
            "This container defines OSPF SPF throttle timers configuration.";

          uses ospf-spf-throttle-timers-config;
        }

        container state {
          config false;
          description
            "This container defines OSPF SPF throttle timers information.";

          uses ospf-spf-throttle-timers-config;
        }
      }
    }
  }


  /*
   * OSPF SPF Logs and Triggers
   */
  grouping ospf-spf-trigger-state {
    description
      "This grouping defines OSPF SPF trigger information.";

    container state {
      description
        "This container describes SPF trigger entry state.";

      leaf trigger-id {
        type uint32;
        description
          "The ID of the SPF trigger entry.";
      }

      leaf trigger-timestamp {
        type string;
        description
          "The timestamp of the SPF trigger.";
      }

      leaf trigger-type {
        type identityref {
          base "arc-ospf-types:OSPF_SPF_TRIGGER_TYPE";
        }

        description
          "The trigger type of the SPF trigger entry.";
      }

      leaf spf-delay-sm-state {
        type identityref {
          base "arc-ospf-types:OSPF_SPF_DELAY_SM_STATE";
        }

        description
          "The SPF Delay state-machine state at the  time
           of the SPF trigger.";
      }

      leaf full-spf {
        type boolean;
        description
          "Indicates if the SPF trigger requested a full SPF computation.";
      }
    }

    container trigger-lsa {
      description
        "This container describes the LSA that triggered the
         SPF computation.";

      uses ospf-lsa-instance-info;
    }
  }

  grouping ospf-spf-spt-log-info {
    description
      "This grouping defines OSPF SPF SPT log information.";

    leaf duration {
      type uint64;
      units microseconds;
      description
        "The time taken for computing SPF SPT result.";
    }

    leaf input-node-count {
      type uint32;
      description
        "The number of nodes input to the SPF computation.";
    }

    leaf reachable-node-count {
      type uint32;
      description
        "The number of reachable nodes ouput from the SPF
         computation.";
    }

    leaf unreachable-node-count {
      type uint32;
      description
        "The number of nodes unreachable nodes output from
         the SPF computation.";
    }
  }

  grouping ospf-spf-route-log-info {
    description
      "This grouping defines OSPF SPF Route log information.";

    leaf duration {
      type uint64;
      units microseconds;
      description
        "The time taken for processing routes during this
         SPF computation.";
    }

    leaf processed-route-count {
      type uint32;
      description
        "The total number of routes processed during this
         SPF computation.";
    }

    leaf reachable-route-count {
      type uint32;
      description
        "The number of reachable routes computed during this
         SPF computation.";
    }

    leaf unreachable-route-count {
      type uint32;
      description
        "The number of unreachable routes computed during this
         SPF computation.";
    }

    leaf bestpath-change-route-count {
      type uint32;
      description
        "The number of routes whose bestpath changed during this
         SPF computation.";
    }
  }

  grouping ospf-spf-log-state {
    description
      "This grouping defines OSPF SPF log information.";

    container state {
      description
        "This container defines OSPF SPF log entry state.";

      leaf log-id {
        type uint32;
        description
          "The ID of the SPF log entry.";
      }

      leaf area-id {
        type arc-ospf-types:ospf-area-identifier;
        description
          "The area of the OSPF route. Valid for intra-area and
          inter-area route only";
      }

      leaf in-use {
        type boolean;
        description
          "Indicates if this SPF log entry is currently being updated.";
      }

      leaf spf-timer-start-timestamp {
        type string;
        description
          "The timestamp of the start of SPF timer.";
      }

      leaf spf-timer-delay {
        type uint64;
        units microseconds;
        description
          "The delay value used when the SPF timer was started.";
      }

      leaf spf-start-timestamp {
        type string;
        description
          "The timestamp of the start of SPF computation.";
      }

      leaf spf-delay-sm-state {
        type identityref {
          base "arc-ospf-types:OSPF_SPF_DELAY_SM_STATE";
        }

        description
          "The SPF Delay state-machine state at the time
           of the SPF computation.";
      }

      leaf full-spf {
        type boolean;
        description
          "Indicates if the Full SPF was computed.";
      }

      leaf spf-duration {
        type uint64;
        units microseconds;
        description
          "The total time taken for completing this SPF computation.";
      }

      container spt-log {
        description
          "This container describes results of SPT computation.";

        uses ospf-spf-spt-log-info;
      }

      container asbr-log {
        description
          "This container describes results of ASBR computation.";

        uses ospf-spf-route-log-info;
      }

      container route-log {
        description
          "This container describes results of Route computation.";

        uses ospf-spf-route-log-info;
      }

      leaf trigger-count {
        type uint32;
        description
          "The total number of triggers generated for this SPF log entry.";
      }

      leaf stored-trigger-count {
        type uint32;
        description
          "The number of triggers stored in this SPF log entry.";
      }
    }
  }


  grouping ospf-spf-log {
    description
      "This grouping defines one OSPF SPF log entry.";

    uses ospf-spf-log-state;

    container triggers {
      description
        "This container defines OSPF SPF triggers.";

      list trigger {
        key "trigger-id";

        description
          "List of OSPF SPF triggers.";

        leaf trigger-id {
          type leafref {
            path "../state/trigger-id";
          }

          description
            "Reference to the trigger ID of the SPF trigger entry.";
        }

        uses ospf-spf-trigger-state;
      }
    }
  }

  grouping ospf-spf-logs-structure {
    description
      "This grouping defines OSPF SPF log information.";

    container logs {
      config false;
      description
        "This container defines OSPF SPF logs.";

      list log {
        key "log-id";

        description
          "List of OSPF SPF logs.";

        leaf log-id {
          type leafref {
            path "../state/log-id";
          }

          description
            "Reference to the log ID of the SPF log entry.";
        }

        uses ospf-spf-log;
      }
    }
  }

  grouping ospf-spf-logging-config {
    description
      "Configuration parameters related to SPF logging";

    leaf maximum-logs {
      type uint32;
      description
        "Maximum number of SPF logs to store";
    }

    leaf maximum-triggers-per-log {
      type uint32;
      description
        "Maximum number of SPF triggers per SPF log to store";
    }
  }

  grouping ospf-spf-logging-state {
    description
      "Information related to SPF logs";

    leaf stored-log-count {
      type uint32;
      description
        "Number of SPF logs currently stored";
    }
  }

  grouping ospf-spf-logging-structure {
    description
      "This grouping defines OSPF SPF logging control.";

    container logging {
      description
        "This container defines OSPF SPF logging control.";

      container config {
        description
          "This container defines OSPF SPF logging configuration.";

        uses ospf-spf-logging-config;
      }

      container state {
        config false;
        description
          "This container defines OSPF SPF logging information.";

        uses ospf-spf-logging-config;
        uses ospf-spf-logging-state;
      }

      uses ospf-spf-logs-structure;
    }
  }
}
