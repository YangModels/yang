module arcos-confd-hafw {
  yang-version 1.1;
  namespace "http://yang.arrcus.com/arcos/confd-hafw";
  prefix arc-confd-hafw;

  import arcos-runtime {
    prefix arc-runtime;
  }
  import ietf-inet-types {
    prefix inet;
  }

  organization "Arrcus, Inc";

  contact
    "Email: eng@arrcus.com";

  description
    "This module lists the confd high availability framework related information.
     Copyright 2016-2022 by Arrcus, Inc. All rights reserved.";

  revision "2022-02-16" {
    description
      "Initial version";
  }

  grouping election-state {
    container election {
      description
        "Confd high availability election state.";
      leaf prefix {
        type string;
        description
          "Confd high availability election prefix.";
      }
      leaf leader {
        type string;
        description
          "Confd high availability election leader node name.";
      }
      leaf local-role {
        type enumeration {
          enum ACTIVE {
            description
              "Confd high availability election role is active.";
          }
          enum STANDBY {
            description
              "Confd high availability election role is stand-by.";
          }
          enum UNKNOWN {
            description
              "Confd high availability election role is unknown.";
          }
        }
      }
    }
  }

  grouping confd-hafw-state {
    leaf node-id {
      type string;
      description
        "Confd high availability framework local node id.";
    }
    leaf service-address {
      type inet:ipv4-address-no-zone;
      description
        "Confd service address.";
    }
  }

  grouping confd-hafw-top {
    container confd-hafw {
      description
        "Arrcus confd high availability framework internals.";

      config false;
      container state {
        uses confd-hafw-state;
        uses election-state;
      }
    }
  }

  augment "/arc-runtime:runtime-instances" +
          "/arc-runtime:runtime-instance" {
    uses confd-hafw-top;
  }
}
