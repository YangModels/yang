module arcos-openconfig-bgp-policy-augments-deviations {
  yang-version 1.1;
  namespace "http://yang.arrcus.com/arcos/openconfig/bgp-policy/augments/deviations";
  prefix arc-oc-bgp-pol-aug-dev;

  import openconfig-bgp-types {
    prefix oc-bgp-types;
  }
  import openconfig-routing-policy {
    prefix oc-rpol;
  }
  import openconfig-bgp-policy {
    prefix oc-bgp-pol;
  }
  import arcos-openconfig-bgp-types {
    prefix arc-oc-bgp-types;
  }

  import arcos-openconfig-bgp-policy-augments {
    prefix arc-oc-bgp-pol-aug;
  }

  organization
    "Arrcus, Inc.";
  contact
    "Arrcus, Inc.
     Customer Service
     Postal: 2077 Gateway Place
     San Jose, CA 95110
     Tel: +1 1XXX XXX-XXXX
     E-mail: xxx@arrcus.com";
  description
    "This module defines deviations to augmentation for Arrcus
     implemention of the openconfig bgp-policy module.";

  revision 2021-06-09 {
    description
      "Initial Revision
       * bgp set additional community definition deviations
      ";
    reference
      "RFC 6020: YANG - A Data Modeling Language for the
       Network Configuration Protocol (NETCONF)";
  }

  deviation "/oc-rpol:routing-policy/oc-rpol:policy-definitions" +
            "/oc-rpol:policy-definition/oc-rpol:statements" +
            "/oc-rpol:statement/oc-rpol:actions" +
            "/oc-bgp-pol:bgp-actions/arc-oc-bgp-pol-aug:set-community-additional" +
            "/arc-oc-bgp-pol-aug:inline/arc-oc-bgp-pol-aug:config" +
            "/arc-oc-bgp-pol-aug:communities" {
    deviate replace {
      type union {

        /*
         * Exclude 0x00000000 - 0x0000FFFF and 0xFFFF0000 - 0xFFFFFFFF
         * in string. Allow full range of uint32 for vendor compatibility
         */
        type uint32;
        type string {
          pattern '(6553[0-4]|655[0-2][0-9]|654[0-9]{2}|65[0-4][0-9]{2}'  +
                  '|6[0-4][0-9]{3}|[1-5][0-9]{4}|[1-9][0-9]{1,3}|[1-9]):' +
                  '(6553[0-5]|655[0-2][0-9]|654[0-9]{2}|65[0-4][0-9]{2}'  +
                  '|6[0-4][0-9]{3}|[1-5][0-9]{4}|[1-9][0-9]{1,3}|[0-9])';
        }
        type oc-bgp-types:bgp-well-known-community-type;
      }
    }
    description
      "Replacement of type due to OpenConfig non-compliance with YANG
       1.0/1.1 pattern statement";
  }

  deviation "/oc-rpol:routing-policy/oc-rpol:policy-definitions" +
            "/oc-rpol:policy-definition/oc-rpol:statements" +
            "/oc-rpol:statement/oc-rpol:actions" +
            "/oc-bgp-pol:bgp-actions/arc-oc-bgp-pol-aug:set-community-additional" +
            "/arc-oc-bgp-pol-aug:inline/arc-oc-bgp-pol-aug:config" +
            "/arc-oc-bgp-pol-aug:communities" {
    deviate add {
       max-elements 32;
    }
  }

  deviation "/oc-rpol:routing-policy/oc-rpol:policy-definitions" +
            "/oc-rpol:policy-definition/oc-rpol:statements" +
            "/oc-rpol:statement/oc-rpol:actions" +
            "/oc-bgp-pol:bgp-actions/arc-oc-bgp-pol-aug:set-ext-community-additional" +
            "/arc-oc-bgp-pol-aug:inline/arc-oc-bgp-pol-aug:config" +
            "/arc-oc-bgp-pol-aug:ext-communities" {
    deviate replace {
      type arc-oc-bgp-types:bgp-extcomm-type;
    }
    description "Use bgp-extcomm-type.";
  }

  deviation "/oc-rpol:routing-policy/oc-rpol:policy-definitions" +
            "/oc-rpol:policy-definition/oc-rpol:statements" +
            "/oc-rpol:statement/oc-rpol:actions" +
            "/oc-bgp-pol:bgp-actions/arc-oc-bgp-pol-aug:set-ext-community-additional" +
            "/arc-oc-bgp-pol-aug:inline/arc-oc-bgp-pol-aug:config" +
            "/arc-oc-bgp-pol-aug:ext-communities" {
    deviate add {
      max-elements 32;
    }
    description "Up to 32 members only.";
  }

  deviation "/oc-rpol:routing-policy/oc-rpol:defined-sets" +
            "/oc-bgp-pol:bgp-defined-sets/arc-oc-bgp-pol-aug:large-community-sets" +
            "/arc-oc-bgp-pol-aug:large-community-set/arc-oc-bgp-pol-aug:config" +
            "/arc-oc-bgp-pol-aug:large-community-set-name" {
    deviate replace {
      type string {
        length "1..79";
      }
    }
    description "Limit size to 79 characters.";
  }
}
