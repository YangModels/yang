/*
 * Generated by confdc --mib2yang-std
 * Source: ARRCUS-SYSTEM-TRAPS-MIB.mib
 */
/*
 * This YANG module has been generated by smidump 0.5.0:
 *
 *      smidump -f yang ARRCUS-SYSTEM-TRAPS-MIB
 *
 * Do not edit. Edit the source file instead!
 */

module ARRCUS-SYSTEM-TRAPS-MIB {

  namespace "urn:ietf:params:xml:ns:yang:smiv2:ARRCUS-SYSTEM-TRAPS-MIB";
  prefix "arrcus-system";

  import SNMPv2-TC {
    prefix "snmpv2-tc";
  }

  import ietf-yang-smiv2 {
    prefix "smiv2";
  }

  organization
   "@ARRCUS";

  contact
   "@arrcus.com";

  description
   "This module defines the traps for cpu and memory load average.";

  revision 2023-01-25 {
    description
     "Adding Initial version of ARRCUS-SYSTEM-TRAPS-MIB yang file
      for cpu and memory threshold trap generation";
  }


  container ARRCUS-SYSTEM-TRAPS-MIB {
    config false;

    container arrcusSystemThresholdTable {
      description
       "This is the data structure associated to
        alerts triggered by the System Threshold.";
      smiv2:oid "1.3.6.1.4.1.51604.3.7.1.3.1";

      list arrcusSystemThresholdEntry {
        key "arrucsSystemThresholdEntryID";
        description
         "This is the data structure associated to
          alerts triggered by the NetBeez BeezKeeper.";
        smiv2:oid "1.3.6.1.4.1.51604.3.7.1.3.1.1";

        leaf arrucsSystemThresholdEntryID {
          type uint32 {
            range "0..127";
          }
          description
           "The notification ID";
          smiv2:max-access "read-only";
          smiv2:oid "1.3.6.1.4.1.51604.3.7.1.3.1.1.1";
        }

        leaf arrcusSystemThresholdEntryName {
          type snmpv2-tc:DisplayString;
          description
           "Trap name";
          smiv2:max-access "read-only";
          smiv2:oid "1.3.6.1.4.1.51604.3.7.1.3.1.1.2";
        }

        leaf arrcusSystemThresholdEntryConfiguredThreshold {
          type int32;
          description
           "Threshold configured percentage";
          smiv2:max-access "read-only";
          smiv2:oid "1.3.6.1.4.1.51604.3.7.1.3.1.1.3";
        }

        leaf arrcusSystemThresholdEntrySystemValue {
          type int32;
          description
           "System usage percentage";
          smiv2:max-access "read-only";
          smiv2:oid "1.3.6.1.4.1.51604.3.7.1.3.1.1.4";
        }
      }
    }
  }

  notification arrcusCPUThreshold {
    description
     "This notification will generated when the cpu usage crosses the configured usage in percentage.";
    smiv2:oid "1.3.6.1.4.1.51604.3.7.1.0.1";

    container object-1 {

      leaf arrucsSystemThresholdEntryID {
        type leafref {
          path "/arrcus-system:ARRCUS-SYSTEM-TRAPS-MIB/arrcus-system:arrcusSystemThresholdTable/arrcus-system:arrcusSystemThresholdEntry/arrcus-system:arrucsSystemThresholdEntryID";
        }
      }
    }

    container object-2 {

      leaf arrucsSystemThresholdEntryID {
        type leafref {
          path "/arrcus-system:ARRCUS-SYSTEM-TRAPS-MIB/arrcus-system:arrcusSystemThresholdTable/arrcus-system:arrcusSystemThresholdEntry/arrcus-system:arrucsSystemThresholdEntryID";
        }
      }

      leaf arrcusSystemThresholdEntryName {
        type leafref {
          path "/arrcus-system:ARRCUS-SYSTEM-TRAPS-MIB/arrcus-system:arrcusSystemThresholdTable/arrcus-system:arrcusSystemThresholdEntry/arrcus-system:arrcusSystemThresholdEntryName";
        }
      }
    }

    container object-3 {

      leaf arrucsSystemThresholdEntryID {
        type leafref {
          path "/arrcus-system:ARRCUS-SYSTEM-TRAPS-MIB/arrcus-system:arrcusSystemThresholdTable/arrcus-system:arrcusSystemThresholdEntry/arrcus-system:arrucsSystemThresholdEntryID";
        }
      }

      leaf arrcusSystemThresholdEntryConfiguredThreshold {
        type leafref {
          path "/arrcus-system:ARRCUS-SYSTEM-TRAPS-MIB/arrcus-system:arrcusSystemThresholdTable/arrcus-system:arrcusSystemThresholdEntry/arrcus-system:arrcusSystemThresholdEntryConfiguredThreshold";
        }
      }
    }

    container object-4 {

      leaf arrucsSystemThresholdEntryID {
        type leafref {
          path "/arrcus-system:ARRCUS-SYSTEM-TRAPS-MIB/arrcus-system:arrcusSystemThresholdTable/arrcus-system:arrcusSystemThresholdEntry/arrcus-system:arrucsSystemThresholdEntryID";
        }
      }

      leaf arrcusSystemThresholdEntrySystemValue {
        type leafref {
          path "/arrcus-system:ARRCUS-SYSTEM-TRAPS-MIB/arrcus-system:arrcusSystemThresholdTable/arrcus-system:arrcusSystemThresholdEntry/arrcus-system:arrcusSystemThresholdEntrySystemValue";
        }
      }
    }
  }

  notification arrcusMemoryThreshold {
    description
     "This notification will generated when the memory usage crosses the configured usage in percentage.";
    smiv2:oid "1.3.6.1.4.1.51604.3.7.1.0.2";

    container object-1 {

      leaf arrucsSystemThresholdEntryID {
        type leafref {
          path "/arrcus-system:ARRCUS-SYSTEM-TRAPS-MIB/arrcus-system:arrcusSystemThresholdTable/arrcus-system:arrcusSystemThresholdEntry/arrcus-system:arrucsSystemThresholdEntryID";
        }
      }
    }

    container object-2 {

      leaf arrucsSystemThresholdEntryID {
        type leafref {
          path "/arrcus-system:ARRCUS-SYSTEM-TRAPS-MIB/arrcus-system:arrcusSystemThresholdTable/arrcus-system:arrcusSystemThresholdEntry/arrcus-system:arrucsSystemThresholdEntryID";
        }
      }

      leaf arrcusSystemThresholdEntryName {
        type leafref {
          path "/arrcus-system:ARRCUS-SYSTEM-TRAPS-MIB/arrcus-system:arrcusSystemThresholdTable/arrcus-system:arrcusSystemThresholdEntry/arrcus-system:arrcusSystemThresholdEntryName";
        }
      }
    }

    container object-3 {

      leaf arrucsSystemThresholdEntryID {
        type leafref {
          path "/arrcus-system:ARRCUS-SYSTEM-TRAPS-MIB/arrcus-system:arrcusSystemThresholdTable/arrcus-system:arrcusSystemThresholdEntry/arrcus-system:arrucsSystemThresholdEntryID";
        }
      }

      leaf arrcusSystemThresholdEntryConfiguredThreshold {
        type leafref {
          path "/arrcus-system:ARRCUS-SYSTEM-TRAPS-MIB/arrcus-system:arrcusSystemThresholdTable/arrcus-system:arrcusSystemThresholdEntry/arrcus-system:arrcusSystemThresholdEntryConfiguredThreshold";
        }
      }
    }

    container object-4 {

      leaf arrucsSystemThresholdEntryID {
        type leafref {
          path "/arrcus-system:ARRCUS-SYSTEM-TRAPS-MIB/arrcus-system:arrcusSystemThresholdTable/arrcus-system:arrcusSystemThresholdEntry/arrcus-system:arrucsSystemThresholdEntryID";
        }
      }

      leaf arrcusSystemThresholdEntrySystemValue {
        type leafref {
          path "/arrcus-system:ARRCUS-SYSTEM-TRAPS-MIB/arrcus-system:arrcusSystemThresholdTable/arrcus-system:arrcusSystemThresholdEntry/arrcus-system:arrcusSystemThresholdEntrySystemValue";
        }
      }
    }
  }

  smiv2:alias "arrcusSystemThresholdTrap" {
    smiv2:oid "1.3.6.1.4.1.51604.3.7";
  }

  smiv2:alias "arrcusSystemThresholdTraps" {
    smiv2:oid "1.3.6.1.4.1.51604.3.7.1";
  }

  smiv2:alias "arrcusSystemThresholdNotification" {
    smiv2:oid "1.3.6.1.4.1.51604.3.7.1.0";
  }

  smiv2:alias "arrcusSystemThresholdGroup" {
    smiv2:oid "1.3.6.1.4.1.51604.3.7.1.2";
  }

  smiv2:alias "arrcusSystemThreshold" {
    smiv2:oid "1.3.6.1.4.1.51604.3.7.1.3";
  }

}
