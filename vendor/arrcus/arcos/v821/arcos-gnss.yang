module arcos-gnss {
  yang-version 1.1;
  namespace "http://yang.arrcus.com/arcos/gnss/";
  prefix arc-gnss;

  import tailf-common {
    prefix tailf;
  }

  import arcos-features {
    prefix arc-features;
  }

  organization
    "Arrcus, Inc";

  contact
    "Arrcus, Inc.
     2077 Gateway Place
     Suite 400
     San Jose, CA 95110
     E-mail: yang-support@arrcus.com";

  description
    "This module lists arrcus gnss related information.
     Copyright (c) 2023 by Arrcus, Inc.
     All rights reserved.";

  revision 2023-10-10 {
    description
      "Included gnss receiver and survey-in details";
  }

  revision 2023-07-24 {
    description
      "Add gnss details";
  }

  grouping receiver-info {
      description
          "GNSS receiver information";
      container receiver {
          config false;
          leaf software {
              type string;
              description
                  "GNSS software information";
          }
          leaf hardware {
              type string;
              description
                  "GNSS hardware information";
          }
          leaf extended {
              tailf:cli-preformatted;
              type string;
              description
                  "GNSS detailed information";
          }
      }
  }
  grouping config-info {
      description
          "GNSS survey-in config information";
      container config {
          config false;
          leaf observation-time {
              type string;
              description
                  "Observation time in seconds";
          }
          leaf position-accuracy {
              type string;
              description
                  "Position accuracy in millimeter";
          }
      }
  }

  grouping status-info {
      description
          "GNSS survey-in status";
      container status {
          config false;
          leaf valid {
              type boolean;
              description
                  "Validity of GNSS survey-in status";
          }
          leaf active {
              type boolean;
              description
                  "Active status of GNSS survery-in";
          }
          leaf duration {
              type string;
              description
                  "Passed survery-in observation time";
          }
          leaf mean-x {
              type string;
              description
                  "Position ECEF X coordinate";
          }
          leaf mean-y {
              type string;
              description
                  "Position ECEF Y coordinate";
          }
          leaf mean-z {
              type string;
              description
                  "Position ECEF Z coordinate";
          }
          leaf variance {
              type string;
              description
                  "Position 3D variance";
          }
          leaf obs {
              type uint32;
              description
                  "Number of position observations";
          }
      }
  }

  grouping survey-in-info {
      container survery-in {
          uses config-info;
          uses status-info;
      }
  }

  container gnss {
      config false;
      leaf constellation {
          type string;
          description
              "Satellite system in use";
      }
      leaf satellite-for-navigation {
          tailf:cli-preformatted;
          type string;
          description
              "Satellite navigation information";
      }
      leaf cable-delay-compensation { 
          type uint32;
          description
              "GNSS cable delay compensation";
      }
      leaf position-mode {
          tailf:cli-preformatted;
          type string;
          description
              "GNSS fix";
      }
      leaf latitude {
          type string;
          description
              "Latitude of GPS";
      }
      leaf longitude {
          type string;
          description
              "Longitude of GPS";
      }
      leaf altitude {
          type string;
          description
              "Altitude of GPS";
      }
      leaf satellite-status {
          tailf:cli-preformatted;
          type string;
          description
              "Satellite Status";
      }
      uses receiver-info;
      uses survey-in-info;
  }

}
