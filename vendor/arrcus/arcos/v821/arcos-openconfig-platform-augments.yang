module arcos-openconfig-platform-augments {
  yang-version 1.1;
  namespace "http://yang.arrcus.com/arcos/openconfig/platform/augments";
  prefix arc-oc-platform-aug;

  import openconfig-platform { prefix oc-platform; }
  import ietf-yang-types { prefix yang; }

  organization
    "Arrcus, Inc.";

  contact
    "Arrcus, Inc.
     Customer Service
     Postal: 2077 Gateway Place
     San Jose, CA 95110
     Tel: +1 408 884-1965
     E-mail: yang-support@arrcus.com";

  description
    "This module defines augments for Arrcus
     implemention of the openconfig platform model.

     Copyright (c) 2016-2022 by Arrcus, Inc.
     All rights reserved.";

  revision 2022-11-08 {
    description
      "Cleanup commented out statements and add template YANG file headers";
  }

  grouping fabric-intf-counters {
    container counters {
      leaf tx-control-cells {
        type yang:counter64;
        description "TX Control cell counter";
      }

      leaf rx-control-cells {
        type yang:counter64;
        description "RX Control cell counter";
      }

      leaf tx-data-cells {
        type yang:counter64;
        description "TX Data cell counter";
      }

      leaf tx-data-bytes {
        type yang:counter64;
        description "TX Data byte counter";
      }

      leaf rx-data-cells {
        type yang:counter64;
        description "RX Data cell counter";
      }

      leaf rx-data-bytes {
        type yang:counter64;
        description "RX Data byte counter";
      }

      leaf crc-errors {
        type yang:counter64;
        description "RX CRC error counter";
      }

      leaf rs-fec-correctable-errors {
        type yang:counter64;
        description "RX RS-FEC correctable error counter";
      }

      leaf rs-fec-uncorrectable-errors {
        type yang:counter64;
        description "RX RS-FEC uncorrectable error counter";
      }

    }
  }

  grouping fabric-reachability-info {
    container reachability-info {
      leaf lane-status {
        type string;
        description "Operational status of  the Lane";
      }

      leaf remote-lane-number {
        type uint16;
        description "Remote lane number that represents immediate neighbor";
      }

      leaf remote-mod-id {
        type uint16;
        description "Remote module id of the immediate neighbor";
      }

      leaf-list reachable-modules {
        type uint16;
        description "List of modules that can be reachable via this fabric lane";
      }
    }
  }

  grouping fabric-lane-info {
    container lanes {
      list lane {
        key "lane-number unit";
        config false;

        leaf lane-number {
          type uint16;
          description "Lane number within the fabric interface";
        }

        leaf unit {
          type uint16;
          description "Unit associated to the lane number";
        }

        uses fabric-reachability-info;
        uses fabric-intf-counters;
      }
    }
  }

  grouping fabric-interface-info {
    container interfaces {
      list interface {
        key "name";
        config false;

        leaf name {
          type string;
          description "Fabric interface name";
        }

        leaf remote-port {
          type string;
          description "Fabric remote interface name";
        }

        leaf remote-nodename {
          type string;
          description "Remote node name";
        }

        uses fabric-lane-info;
      }
    }
  }

  grouping ul-connectivity-info {
    container underlay {
      container state {
        list topology {
          key "local-port";
          config false;

          leaf local-port {
            type string;
            description "Local port";
          }
          leaf remote-port {
            type string;
            description "Remote port";
          }
          leaf local-ip {
            type string;
            description "Ip address of the local interface";
          }
          leaf remote-ip {
            type string;
            description "Ip address of the remote interface";
          }
          leaf node-name {
            type string;
            description "Remote node name";
          }
          leaf node-id {
            type string;
            description "Remode node id";
          }
          leaf platform-type {
            type string;
            description "Type of the platform";
          }
        }
      }
    }
  }

  augment "/oc-platform:components/oc-platform:component" +
          "/oc-platform:fabric/oc-platform:state" {
    uses fabric-interface-info;
  }
  augment "/oc-platform:components/oc-platform:component" {
    uses ul-connectivity-info;
  }
}
