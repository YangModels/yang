module arcos-twamp {
  yang-version "1.1";
  namespace "http://yang.arrcus.com/arcos/twamp";
  prefix "arc-twamp";

  import ietf-yang-types { prefix "ietf-types"; }
  import ietf-inet-types { prefix "inet"; }
  import openconfig-network-instance { prefix "oc-netinst"; }

  organization
    "Arrcus, Inc";

  contact
    "Email: eng@arrcus.com";

  description
    "This YANG module is for model for the
      Two-Way Active Measurement Protocol (TWAMP) lite.

      This module has been derived from the IETF YANG module
      for TWAMP as defined in RFC 8913.

      Copyright (c) 2016-2022 by Arrcus, Inc.
      All rights reserved.";

  revision 2022-09-01 {
    description
      "Initial revision.";
  }

  typedef dynamic-port-number {
    type inet:port-number {
      range 49152..65535;
    }
    description "Dynamic range for port numbers.";
  }

  grouping twamp-test-session-common {
    description
      "List of TWAMP Session-Sender test sessions.";

    leaf name {
      type string;
      description
        "A unique name for this TWAMP-Test session to be used
          for identifying this test session by the
          Session-Sender logical entity.";
    }

    leaf admin-state {
      type boolean;
      default true;
      description
        "Indicates the Session-Sender test session state.";
    }

    leaf sender-ip {
      type inet:ip-address;
      description
        "The IP address on the remote device, which is the
          source IP address used in the TWAMP-Test (UDP) packets
          belonging to this test session.";
    }

    leaf sender-udp-port {
      type dynamic-port-number;
      description
        "The source UDP port used in the TWAMP-Test packets
          belonging to this test session.";
    }

    leaf reflector-ip {
      type inet:ip-address;
      mandatory true;
      description
        "The IP address of the local Session-Reflector
          device, which is the destination IP address used
          in the TWAMP-Test (UDP) packets belonging to this test
          session.";
    }

    leaf reflector-udp-port {
      type inet:port-number {
        range "862 | 49152..65535";
        }
      description
        "The destination UDP port number used in the
          TWAMP-Test (UDP) test packets belonging to this
          test session.";
    }

    leaf periodic-interval {
      type uint32;
      units seconds;
      mandatory true;
      description
        "Indicates the time to wait (in seconds) between
          the first bits of TWAMP-Test (UDP) packet
          transmissions for this test session.";
      reference
        "RFC 3432: Network performance measurement
                    with periodic streams";
    }
  }

  grouping twamp-test-session-if-index {
    leaf if-index {
      type uint64;
      description
        "Interface Index";
    }
  }

  grouping maintenance-statistics {
    leaf sent-packets {
      type ietf-types:zero-based-counter64;
      config false;
      description
        "Indicates the number of packets sent.";
    }

    leaf rcv-packets {
      type ietf-types:zero-based-counter64;
      config false;
      description
        "Indicates the number of packets received.";
    }

    leaf last-sent-seq {
      type ietf-types:zero-based-counter64;
      config false;
      description
        "Indicates the last sent sequence number.";
    }

    leaf last-rcv-seq {
      type ietf-types:zero-based-counter64;
      config false;
      description
        "Indicates the last received sequence number.";
    }

    leaf last-rtd {
      type ietf-types:zero-based-counter64;
      config false;
      description
        "Indicates the RTD(round trip delay)(nano seconds) of the last recved pkt.";
    }

    leaf ave-rtd {
      type ietf-types:zero-based-counter64;
      config false;
      description
        "Indicates the average RTD(round trip delay)(nano seconds) of all recved pkt.";
    }

    description
      "Used for TWAMP-Test maintenance statistics.";
  }

  grouping twamp-session-reflector-common {
    leaf admin-state {
      type boolean;
      default false;
      description
        "Indicates whether the device is allowed to operate
          as a TWAMP Session-Reflector.";
    }

    leaf reflector-udp-port {
      type inet:port-number {
        range "862 | 49152..65535";
      }
      description
        "The destination UDP port number used in the
         TWAMP-Test (UDP) test packets belonging to this
         test session.";
    }
  }

  grouping session-sender-base {
    description
    "Configuration of the TWAMP Session-Sender logical entity";
    container session-sender {
      description
        "Configuration of the TWAMP Session-Sender logical entity";

      leaf admin-state {
        type boolean;
        default true;
        description
          "Indicates whether the device is allowed to operate
           as a TWAMP Session-Sender.";
      }

      container test-sessions {
        list test-session {
          key name;
          description
            "List of TWAMP Session-Sender test sessions.";

          leaf name {
            type leafref {
              path "../config/name";
            }
            description
              "A unique name for this TWAMP-Test session to be used
                for identifying this test session by the
                Session-Sender logical entity.";
          }

          container config {
            description
              "List of TWAMP Session-Sender test sessions.";
            uses twamp-test-session-common;
          }

          container state {
            config false;
            description
              "List of TWAMP Session-Sender test sessions.";
            uses twamp-test-session-common;
            uses twamp-test-session-if-index;
            uses maintenance-statistics;
          }
        }
      }
    }
  }

  grouping session-reflector-base {
    description
      "Configuration of the TWAMP Session-Reflector logical entity";

    container session-reflector {
      description
        "Configuration of the TWAMP Session-Reflector logical
         entity";

      container config {
        description
          "Configuration of the TWAMP Session-Reflector logical entity";
        uses twamp-session-reflector-common;
      }

      container state {
        config false;
        description
          "Configuration of the TWAMP Session-Reflector logical entity";
        uses twamp-session-reflector-common;
      }
    }
  }

  grouping twamp-base {
    container twamp {
      description
        "TWAMP Session-Sender and Session-Reflector";

      uses session-sender-base;
      uses session-reflector-base;
    }
  }

  augment "/oc-netinst:network-instances/oc-netinst:network-instance" {
    description
      "TWAMP Session-Sender and Session-Reflector";
    uses twamp-base;
  }
}
