module arcos-openconfig-network-instance-augments-deviations {
  yang-version 1.1;
  namespace "http://yang.arrcus.com/arcos/openconfig/network-instance/augments/deviations";
  prefix arc-oc-netinst-aug-dev;

  import openconfig-network-instance {
    prefix oc-ni;
  }

  import arcos-openconfig-network-instance-augments {
    prefix arc-oc-netinst-aug;
  }

  organization
    "Arrcus, Inc.";

  contact
    "Email: eng@arrcus.com";

  description
    "This module defines deviation statements for Arrcus
     implemention of the openconfig network instance module.";

  revision 2024-10-18 {
    description
      "Add extension for table-connection";
  }

  revision 2019-01-05 {
    description
      "Initial Revision";

    reference
      "RFC 7950: The YANG 1.1 Data Modeling Language";
  }

  deviation "/oc-ni:network-instances/oc-ni:network-instance" +
            "/arc-oc-netinst-aug:ip-tunnels/arc-oc-netinst-aug:tunnels" +
            "/arc-oc-netinst-aug:next-hops/arc-oc-netinst-aug:next-hop" +
            "/arc-oc-netinst-aug:state/arc-oc-netinst-aug:index" {
    deviate not-supported;
    description
      "Not supported in this release";
  }

  deviation "/oc-ni:network-instances/oc-ni:network-instance" +
            "/arc-oc-netinst-aug:ip-tunnels/arc-oc-netinst-aug:tunnels" +
            "/arc-oc-netinst-aug:next-hops/arc-oc-netinst-aug:next-hop" +
            "/arc-oc-netinst-aug:state/arc-oc-netinst-aug:weight" {
    deviate not-supported;
    description
      "Not supported in this release";
  }

  deviation "/oc-ni:network-instances/oc-ni:network-instance" +
            "/arc-oc-netinst-aug:ip-tunnels/arc-oc-netinst-aug:tunnels" +
            "/arc-oc-netinst-aug:next-hops/arc-oc-netinst-aug:next-hop" +
            "/arc-oc-netinst-aug:state/arc-oc-netinst-aug:decapsulate-header" {
    deviate not-supported;
    description
      "Not supported in this release";
  }

  deviation "/oc-ni:network-instances/oc-ni:network-instance" +
            "/arc-oc-netinst-aug:ip-tunnels/arc-oc-netinst-aug:tunnels" +
            "/arc-oc-netinst-aug:next-hops/arc-oc-netinst-aug:next-hop" +
            "/arc-oc-netinst-aug:state/arc-oc-netinst-aug:encapsulate-header" {
    deviate not-supported;
    description
      "Not supported in this release";
  }

  deviation "/oc-ni:network-instances/oc-ni:network-instance" +
            "/arc-oc-netinst-aug:ip-tunnels/arc-oc-netinst-aug:tunnels" +
            "/arc-oc-netinst-aug:next-hops/arc-oc-netinst-aug:next-hop" +
            "/arc-oc-netinst-aug:state/arc-oc-netinst-aug:popped-mpls-label-stack" {
    deviate not-supported;
    description
      "Not supported in this release";
  }

  deviation "/oc-ni:network-instances/oc-ni:network-instance" +
            "/arc-oc-netinst-aug:ip-tunnels/arc-oc-netinst-aug:tunnels" +
            "/arc-oc-netinst-aug:next-hops/arc-oc-netinst-aug:next-hop" +
            "/arc-oc-netinst-aug:state/arc-oc-netinst-aug:origin-protocol" {
    deviate not-supported;
    description
      "Not supported in this release";
  }

  deviation "/oc-ni:network-instances/oc-ni:network-instance" +
            "/arc-oc-netinst-aug:ip-tunnels/arc-oc-netinst-aug:tunnels" +
            "/arc-oc-netinst-aug:next-hops/arc-oc-netinst-aug:next-hop" +
            "/arc-oc-netinst-aug:interface-ref/arc-oc-netinst-aug:config" {
    deviate not-supported;
    description
      "Not supported in this release";
  }

  deviation "/oc-ni:network-instances/oc-ni:network-instance" +
            "/oc-ni:fdb/arc-oc-netinst-aug:mac-table-state" +
            "/arc-oc-netinst-aug:entries/arc-oc-netinst-aug:entry" +
            "/arc-oc-netinst-aug:state/arc-oc-netinst-aug:age" {
    deviate not-supported;
    description
      "Not supported in this release";
  }

  deviation "/oc-ni:network-instances/oc-ni:network-instance" +
            "/arc-oc-netinst-aug:ip-tunnels-units" +
            "/arc-oc-netinst-aug:ip-tunnel-unit-entry/arc-oc-netinst-aug:tunnels" +
            "/arc-oc-netinst-aug:next-hops/arc-oc-netinst-aug:next-hop" +
            "/arc-oc-netinst-aug:state/arc-oc-netinst-aug:index" {
    deviate not-supported;
    description
      "Not supported in this release";
  }

  deviation "/oc-ni:network-instances/oc-ni:network-instance" +
            "/oc-ni:fdb/arc-oc-netinst-aug:mac-table-state" +
            "/arc-oc-netinst-aug:entries/arc-oc-netinst-aug:entry" +
            "/arc-oc-netinst-aug:interface/arc-oc-netinst-aug:interface-ref" +
            "/arc-oc-netinst-aug:config" {
    deviate not-supported;
    description
      "Not supported in this release";
  }

  deviation "/oc-ni:network-instances/oc-ni:network-instance" +
            "/arc-oc-netinst-aug:ip-tunnels-units" +
            "/arc-oc-netinst-aug:ip-tunnel-unit-entry/arc-oc-netinst-aug:tunnels" +
            "/arc-oc-netinst-aug:next-hops/arc-oc-netinst-aug:next-hop" +
            "/arc-oc-netinst-aug:state/arc-oc-netinst-aug:weight" {
    deviate not-supported;
    description
      "Not supported in this release";
  }

  deviation "/oc-ni:network-instances/oc-ni:network-instance" +
            "/oc-ni:fdb/arc-oc-netinst-aug:mac-table-state" +
            "/arc-oc-netinst-aug:entries/arc-oc-netinst-aug:entry" +
            "/arc-oc-netinst-aug:interface/arc-oc-netinst-aug:interface-ref" +
            "/arc-oc-netinst-aug:state/arc-oc-netinst-aug:subinterface" {
    deviate not-supported;
    description
      "Not supported in this release";
  }

  deviation "/oc-ni:network-instances/oc-ni:network-instance" +
            "/arc-oc-netinst-aug:ip-tunnels-units" +
            "/arc-oc-netinst-aug:ip-tunnel-unit-entry/arc-oc-netinst-aug:tunnels" +
            "/arc-oc-netinst-aug:next-hops/arc-oc-netinst-aug:next-hop" +
            "/arc-oc-netinst-aug:state/arc-oc-netinst-aug:decapsulate-header" {
    deviate not-supported;
    description
      "Not supported in this release";
  }

  deviation "/oc-ni:network-instances/oc-ni:network-instance" +
            "/arc-oc-netinst-aug:fdb-units/arc-oc-netinst-aug:fdb-unit-entry" +
            "/arc-oc-netinst-aug:mac-table-state/arc-oc-netinst-aug:entries" +
            "/arc-oc-netinst-aug:entry/arc-oc-netinst-aug:state/arc-oc-netinst-aug:age" {
    deviate not-supported;
    description
      "Not supported in this release";
  }

  deviation "/oc-ni:network-instances/oc-ni:network-instance" +
            "/arc-oc-netinst-aug:ip-tunnels-units" +
            "/arc-oc-netinst-aug:ip-tunnel-unit-entry/arc-oc-netinst-aug:tunnels" +
            "/arc-oc-netinst-aug:next-hops/arc-oc-netinst-aug:next-hop" +
            "/arc-oc-netinst-aug:state/arc-oc-netinst-aug:encapsulate-header" {
    deviate not-supported;
    description
      "Not supported in this release";
  }

  deviation "/oc-ni:network-instances/oc-ni:network-instance" +
            "/arc-oc-netinst-aug:fdb-units/arc-oc-netinst-aug:fdb-unit-entry" +
            "/arc-oc-netinst-aug:mac-table-state/arc-oc-netinst-aug:entries" +
            "/arc-oc-netinst-aug:entry/arc-oc-netinst-aug:interface" +
            "/arc-oc-netinst-aug:interface-ref/arc-oc-netinst-aug:config" {
    deviate not-supported;
    description
      "Not supported in this release";
  }

  deviation "/oc-ni:network-instances/oc-ni:network-instance" +
            "/arc-oc-netinst-aug:ip-tunnels-units" +
            "/arc-oc-netinst-aug:ip-tunnel-unit-entry/arc-oc-netinst-aug:tunnels" +
            "/arc-oc-netinst-aug:next-hops/arc-oc-netinst-aug:next-hop" +
            "/arc-oc-netinst-aug:state/arc-oc-netinst-aug:popped-mpls-label-stack" {
    deviate not-supported;
    description
      "Not supported in this release";
  }

  deviation "/oc-ni:network-instances/oc-ni:network-instance" +
            "/arc-oc-netinst-aug:fdb-units/arc-oc-netinst-aug:fdb-unit-entry" +
            "/arc-oc-netinst-aug:mac-table-state/arc-oc-netinst-aug:entries" +
            "/arc-oc-netinst-aug:entry/arc-oc-netinst-aug:interface" +
            "/arc-oc-netinst-aug:interface-ref/arc-oc-netinst-aug:state" +
            "/arc-oc-netinst-aug:subinterface" {
    deviate not-supported;
    description
      "Not supported in this release";
  }

  deviation "/oc-ni:network-instances/oc-ni:network-instance" +
            "/arc-oc-netinst-aug:ip-tunnels-units" +
            "/arc-oc-netinst-aug:ip-tunnel-unit-entry/arc-oc-netinst-aug:tunnels" +
            "/arc-oc-netinst-aug:next-hops/arc-oc-netinst-aug:next-hop" +
            "/arc-oc-netinst-aug:state/arc-oc-netinst-aug:origin-protocol" {
    deviate not-supported;
    description
      "Not supported in this release";
  }

  deviation "/oc-ni:network-instances/oc-ni:network-instance" +
            "/arc-oc-netinst-aug:ip-tunnels-units" +
            "/arc-oc-netinst-aug:ip-tunnel-unit-entry/arc-oc-netinst-aug:tunnels" +
            "/arc-oc-netinst-aug:next-hops/arc-oc-netinst-aug:next-hop" +
            "/arc-oc-netinst-aug:interface-ref/arc-oc-netinst-aug:config" {
    deviate not-supported;
    description
      "Not supported in this release";
  }

  deviation "/oc-ni:network-instances/oc-ni:network-instance"
          + "/oc-ni:table-connections/oc-ni:table-connection"
          + "/arc-oc-netinst-aug:src-dst-instances/arc-oc-netinst-aug:src-dst-instance"
          + "/arc-oc-netinst-aug:config/arc-oc-netinst-aug:import-policy" {
    deviate add {
      max-elements 1;
    }
    description
      "Only support one policy in this release.";
  }

  deviation "/oc-ni:network-instances/oc-ni:network-instance"
          + "/oc-ni:table-connections/oc-ni:table-connection"
          + "/arc-oc-netinst-aug:src-dst-instances/arc-oc-netinst-aug:src-dst-instance"
          + "/arc-oc-netinst-aug:config/arc-oc-netinst-aug:default-import-policy" {
    deviate not-supported;
    description
      "Not supported in this release.";
  }

  deviation "/oc-ni:network-instances/oc-ni:network-instance"
          + "/oc-ni:table-connections/oc-ni:table-connection"
          + "/arc-oc-netinst-aug:src-dst-instances/arc-oc-netinst-aug:src-dst-instance"
          + "/arc-oc-netinst-aug:state/arc-oc-netinst-aug:default-import-policy" {
    deviate not-supported;
    description
      "Not supported in this release.";
  }
}
