module arcos-process {
  yang-version 1.1;
  namespace "http://yang.arrcus.com/arcos/process";
  prefix arc-process;

  import openconfig-types { prefix oc-types; }

  organization
    "Arrcus, Inc.";

  contact
    "Arrcus, Inc.
     2077 Gateway Place,
     San Jose, CA 95110
     Tel: +1 (408) 884-1965
     E-mail: yang-support@arrcus.com";

  description
    "This module contains process related information.
    
    Copyright (c) 2016-2024 by Arrcus, Inc.
     All rights reserved.";


  revision "2024-05-20" {
    description
      "Add cpu-utilization and memory-usage leafs";
  }
  
  container processes {
    description
      "ArcOS list of process";
    config false;

    list process {
      key "name";

      description
        "Display Arrcus Process Details.";

      config false;

      leaf name {
        type string;
        description
          "Name of the process";
      }

      leaf status {
        type string;
        description
          "Process status";
      }

      leaf cpu-util {
        type oc-types:percentage;
        description
          "Process CPU Utilization Percentage";
      }

      leaf mem-usage {
        type uint64;
        description
          "Total # of pages of memory in KiB of the process";
      }

    }
  }
}
