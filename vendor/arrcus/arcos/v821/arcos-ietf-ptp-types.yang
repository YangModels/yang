/**
 * Filename: arcos-ietf-ptp-types.yang
 *
 * Description:
 * YANG data-model for Arcos PTP types
 *
 * Copyright 2022-2022 by Arrcus, Inc.
 * All rights reserved.
 */

module arcos-ietf-ptp-types {
  yang-version 1.1;
  namespace "http://yang.arrcus.com/arcos/ietf/ptp/types";
  prefix arc-ietf-ptp-types;

  organization
    "Arrcus, Inc";

  contact
    "Arrcus, Inc.
     2077 Gateway Place
     Suite 400
     San Jose, CA 95110
     E-mail: yang-support@arrcus.com";

  description
    "This module list arrcus implemenation of PTP types related information.
     Copyright (c) 2022-2022 by Arrcus, Inc.
     All rights reserved.";

  revision 2023-07-24 {
    description
      "Add support to include clock-role in ptp profile";
  }

  revision 2023-03-07 {
    description
      "Add servo algorithm mode configuration";
  }

  revision 2023-02-20 {
    description
      "Add G.8275.2 profile";
  }
  
  revision 2023-01-30 {
    description
      "Change arc-clock-profile type enum g_8275_1_profile --> G8275.1";
  }

  revision 2022-08-08 {
    description
      "Initial revision.";

    reference
      "RFC 8575: YANG Data Model for the Precision Time Protocol (PTP)";
  }
  

  typedef arc-dm-enum {
    type enumeration {
      enum e2e {
        value 1;
      }
      enum disabled {
        value 254;
      }
    }
  }

  typedef arc-clock-profile-type {
    type enumeration {
      /*
      enum default_profile {
        value 1;
        description
          "IEEE 1588 default profile";
      }
      */
      enum G8275.1 {
        value 2;
        description
          "g8275.1 profile.";
      }
      enum G8275.2 {
        value 3;
        description
          "G8275.2 profile";
      }
    }
  }

  typedef arc-servo-algo-type {
    type enumeration {
      enum default-algorithm {
        value 0;
        description
          "Default servo algorithm as determined by service.";
      }
      enum full {
        value 1;
        description
          "Full On-Path Support for G.8275.1 and G.8275.2 profiles.";
      }
      enum full-synce {
        value 2;
        description
          "Full On-Path Support with SyncE for G.8275.1 profile.";
      }
      enum partial {
        value 3;
        description
          "Partial On-Path Support for G.8275.2 and Default profiles.";
      }
      enum partial-synce {
        value 4;
        description
          "Partial On-Path Support with SyncE for G.8275.2 and Default " +
          "profiles.";
      }
      enum partial-low-pdv {
        value 6;
        description
          "Partial On-Path Support with low PDV for G.8275.2 profile.";
      }
      enum partial-high-pdv {
        value 7;
        description
          "Partial On-Path Support with high PDV for G.8275.2 profile.";
      }
    }
  }

  typedef arc-transport-type {
    type enumeration {
      enum ipv4 {
        value 1;
        description
          "IPv4 protocol";
      }
      enum ipv6 {
        value 2;
        description
          "IPv6 protocol";
      }
    }
  }

  typedef arc-clock-role {
    type enumeration {
      enum T-GM {
        value 1;
        description
          "Telecom-Grand Master clock";
      }
      enum T-BC {
        value 2;
        description
          "Telecom-Boundary Clock";
      }
    }
  }
}
