module arcos-corefile {
  yang-version 1.1;
  namespace "http://yang.arrcus.com/arcos/corefile";
  prefix arc-corefile;

  organization
    "Arrcus, Inc.";

  contact
    "Arrcus, Inc.
     2077 Gateway Place
     Suite 400
     San Jose, CA 95110

     E-mail: yang-support@arrcus.com";

  description
    "This module defines native ArcOS core file management commands

     Copyright (c) 2016-2022 by Arrcus, Inc.
     All rights reserved.";

  revision 2022-04-18 {
    description "Added support for clean core";
  }
  
  container cores {
    description
      "ArcOS list of core files";
    config false;

    list core {
      key "filename";

      description
        "Display system process generated coredump files";

      config false;

      leaf filename {
        type string;
        description
          "Name of the core file";
      }

      leaf time {
        type string;
        description
          "Time and date when the coredump file was generated";
      }
    }
  }

  container core-clear {
    description
      "Clear core files";

    action all {
      description
        "Clear all core files";

      output {
        leaf result {
          type string;
          description
            "The status of the operation";
        }
      }
    }
  }
}
