module arcos-common-types {
  yang-version 1.1;
  namespace "http://yang.arrcus.com/arcos/common/types";
  prefix arc-common-types;

  import ietf-yang-types {
    prefix "yang";
  }

  organization
    "Arrcus, Inc.";

  contact
    "Email: yang-support@arrcus.com";

  description
    "ArcOS Common Types Data Model";

  revision 2025-07-17 {
    description "Added common-state-attrs grouping with last-updated-time leaf to record when entries were last updated.";
  }

  revision 2019-08-20 {
    description "ArcOS 3.3.1";
  }

  typedef generic-status-code {
    type enumeration {
      enum SUCCESS {
        description
          "Operation Successful";
      }
      enum FAILURE {
        description
          "Operation Failed";
      }
    }
  }


  grouping generic-rpc-response {
    leaf status {
      type generic-status-code;
      description
        "Result of the operation";
    }
    leaf message {
      type string;
      description
        "Description of the result of the operation";
    }
  }

  grouping common-state-attrs {
    description
      "Grouping for when the routing entries were last updated";

    leaf last-updated-time {
      config false;
      type yang:date-and-time;
      description
        "The timestamp when the entry was last updated";
    }
  }
}
