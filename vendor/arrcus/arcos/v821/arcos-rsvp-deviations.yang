module arcos-rsvp-deviations {
  yang-version 1.1;
  namespace "http://yang.arrcus.com/arcos/rsvp/deviations";
  prefix arc-rsvp-dev;

  import arcos-rsvp {
    prefix arc-rsvp;
  }

  import tailf-common {
    prefix tailf;
  }

  import openconfig-network-instance {
    prefix oc-netinst;
  }
  
  organization 
    "Arrcus, Inc";

  contact
    "Arrcus, Inc.
     2077 Gateway Place
     Suite 400
     San Jose, CA 95110

     E-mail: yang-support@arrcus.com";

  description
    "This module lists the deviations for RSVP module.

     Copyright (c) 2016-2022 by Arrcus, Inc.
     All rights reserved.";


  deviation "/oc-netinst:network-instances/oc-netinst:network-instance" +
            "/oc-netinst:protocols/oc-netinst:protocol" +
            "/arc-rsvp:rsvp/arc-rsvp:global" +
            "/arc-rsvp:preemption/arc-rsvp:config" {
    deviate not-supported;
    description
      "Not supported in this release";
  }
}
