module arcos-oam-types {
  yang-version 1.1;
  namespace "http://yang.arrcus.com/arcos/oam/types";
  prefix arc-oam-types;

  import iana-crypt-hash {
    prefix ianach;
  }

  import tailf-common {
    prefix tailf;
  }

  organization
    "Arrcus, Inc.";

  contact
    "Arrcus, Inc.
     2077 Gateway Place
     Suite 400
     San Jose, CA 95110

     E-mail: yang-support@arrcus.com";

  description
    "This module defines native ArcOS system
     types.

     Copyright (c) 2016-2019 by Arrcus, Inc.
     All rights reserved.";


  revision 2019-10-01 {
    description "Initial version";
  }

  identity OAM_MONITOR_INTERVAL_TYPE {
    description
      "Base identity for OAM endpoint type.";
  }
  identity OAM_MONITOR_INTERVAL_10s {
    base OAM_MONITOR_INTERVAL_TYPE;
    description
      "OAM monitor interval of 10 seconds.";
  }
  identity OAM_MONITOR_INTERVAL_30s {
    base OAM_MONITOR_INTERVAL_TYPE;
    description
      "OAM monitor interval of 30 seconds.";
  }
  identity OAM_MONITOR_INTERVAL_60s {
    base OAM_MONITOR_INTERVAL_TYPE;
    description
      "OAM monitor interval of 60 seconds.";
  }
  identity OAM_MONITOR_INTERVAL_300s {
    base OAM_MONITOR_INTERVAL_TYPE;
    description
      "OAM monitor interval of 300 seconds.";
  }
  identity OAM_ENDPOINT_TYPE {
    description
      "Base identity for OAM endpoint type.";
  }
  identity OAM_ENDPOINT_SID {
    base OAM_ENDPOINT_TYPE;
    description
      "OAM endpoint type SID.";
  }
  identity OAM_HISTORY_DURATION {
    description
      "Base identity for OAM history duration.";
  }
  identity HOUR {
    base OAM_HISTORY_DURATION;
    description
      "an hour of hisory.";
  }
  identity DAY {
    base OAM_HISTORY_DURATION;
    description
      "a day of hisory.";
  }
  identity WEEK {
    base OAM_HISTORY_DURATION;
    description
      "a week of hisory.";
  }
  identity OAM_ENDPOINT_STATE {
    description
      "Base identity for OAM endpoint state.";
  }
  identity NOT_TRACKED {
    base OAM_ENDPOINT_STATE;
    description
      "OAM endpoint state not tracked.";
  }
  identity ELIGIBLE {
    base OAM_ENDPOINT_STATE;
    description
      "OAM endpoint state eligible.";
  }
  identity INELIGIBLE {
    base OAM_ENDPOINT_STATE;
    description
      "OAM endpoint state ineligible.";
  }
  identity OAM_INELIGIBILITY_REASON_TYPE {
    description
      "Base identity for OAM endpoint ineligibility state.";
  }
  identity LATENCY_VIOLATION {
    base OAM_INELIGIBILITY_REASON_TYPE;
    description
      "OAM endpoint state ineligible because latency criterion was violated.";
  }
  identity LONG_LATENCY_VIOLATION {
    base OAM_INELIGIBILITY_REASON_TYPE;
    description
      "OAM endpoint state ineligible because long latency criterion was violated.";
  }
  identity LATENCY_THRESHOLD {
    base OAM_INELIGIBILITY_REASON_TYPE;
    description
      "OAM endpoint state ineligible because latency threshold criterion was violated.";
  }
  identity PKT_LOSS_PERCENT_VIOLATION {
    base OAM_INELIGIBILITY_REASON_TYPE;
    description
      "OAM endpoint state ineligible because pkt_loss_percent criterion was violated.";
  }
  identity CONSECUTIVE_PKT_LOSS_VIOLATION {
    base OAM_INELIGIBILITY_REASON_TYPE;
    description
      "OAM endpoint state ineligible because maximum pkt loss criterion was violated.";
  }
  identity OAM_STAT_TYPE {
    description
      "Base identity for OAM stat type.";
  }
  identity RAW {
    base OAM_STAT_TYPE;
    description
      "OAM raw stats.";
  }
  identity AVG {
    base OAM_STAT_TYPE;
    description
      "OAM averaged stats.";
  }
}
