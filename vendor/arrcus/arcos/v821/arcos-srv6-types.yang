module arcos-srv6-types {
  yang-version 1.1;
  namespace "http://yang.arrcus.com/arcos/srv6-types";
  prefix arc-srv6-types;

  import ietf-inet-types {
    prefix inet;
  }

  organization
    "Arrcus, Inc.";

  contact
    "Arrcus, Inc.
     2077 Gateway Place
     Suite 400
     San Jose, CA 95110

     E-mail: yang-support@arrcus.com";

  description
    "This module contains definitions for the
     native ArcOS SRv6 domain.

     Copyright (c) 2016-2019 by Arrcus, Inc.
     All rights reserved.";

  revision 2020-03-26 {
    description "Initial version";
  }

  //
  // SRv6 Endpoint Behavior types.
  //
  identity SRV6_ENDPOINT_BEHAVIOR_TYPE {
    description
      "Base identity for SRV6 End SID Endpoint Behavior";
    reference
      "draft-ietf-spring-srv6-network-programming";
  }

  identity END {
    base "SRV6_ENDPOINT_BEHAVIOR_TYPE";
    description "End (no PSP, no USP). Codepoint 1.";
  }

  identity END_PSP {
    base "SRV6_ENDPOINT_BEHAVIOR_TYPE";
    description "End with PSP. Codepoint 2.";
  }

  identity END_USP {
    base "SRV6_ENDPOINT_BEHAVIOR_TYPE";
    description "End with USP. Codepoint 3.";
  }

  identity END_PSP_USP {
    base "SRV6_ENDPOINT_BEHAVIOR_TYPE";
    description "End with PSP and USP. Codepoint 4.";
  }

  identity END_X {
    base "SRV6_ENDPOINT_BEHAVIOR_TYPE";
    description "End.X (no PSP, no USP. Codepoint 5.";
  }

  identity END_X_PSP {
    base "SRV6_ENDPOINT_BEHAVIOR_TYPE";
    description "End.X with PSP. Codepoint 6.";
  }

  identity END_X_USP {
    base "SRV6_ENDPOINT_BEHAVIOR_TYPE";
    description "End.X with USP. Codepoint 7.";
  }

  identity END_X_PSP_USP {
    base "SRV6_ENDPOINT_BEHAVIOR_TYPE";
    description "End.X with PSP and USP. Codepoint 8.";
  }

  identity END_T {
    base "SRV6_ENDPOINT_BEHAVIOR_TYPE";
    description "End.T (no PSP, no USP). Codepoint 9.";
  }

  identity END_T_PSP {
    base "SRV6_ENDPOINT_BEHAVIOR_TYPE";
    description "End.T with PSP. Codepoint 10.";
  }

  identity END_T_USP {
    base "SRV6_ENDPOINT_BEHAVIOR_TYPE";
    description "End.T with USP. Codepoint 11.";
  }

  identity END_T_PSP_USP {
    base "SRV6_ENDPOINT_BEHAVIOR_TYPE";
    description "End.T with PSP and USP. Codepoint 12.";
  }

  identity END_B6_ENCAPS {
    base "SRV6_ENDPOINT_BEHAVIOR_TYPE";
    description "End.B6.Encaps. Codepoint 14.";
  }

  identity END_BM {
    base "SRV6_ENDPOINT_BEHAVIOR_TYPE";
    description "End.BM. Codepoint 15.";
  }

  identity END_DX6 {
    base "SRV6_ENDPOINT_BEHAVIOR_TYPE";
    description "End.DX6. Codepoint 16.";
  }

  identity END_DX4 {
    base "SRV6_ENDPOINT_BEHAVIOR_TYPE";
    description "End.DX4. Codepoint 17.";
  }

  identity END_DT6 {
    base "SRV6_ENDPOINT_BEHAVIOR_TYPE";
    description "End.DT6. Codepoint 18.";
  }

  identity END_DT4 {
    base "SRV6_ENDPOINT_BEHAVIOR_TYPE";
    description "End.DT4. Codepoint 19.";
  }

  identity END_DT46 {
    base "SRV6_ENDPOINT_BEHAVIOR_TYPE";
    description "End.DT46. Codepoint 20.";
  }

  identity END_DX2 {
    base "SRV6_ENDPOINT_BEHAVIOR_TYPE";
    description "End.DX2. Codepoint 21.";
  }

  identity END_DX2V {
    base "SRV6_ENDPOINT_BEHAVIOR_TYPE";
    description "End.DX2V. Codepoint 22.";
  }

  identity END_DT2U {
    base "SRV6_ENDPOINT_BEHAVIOR_TYPE";
    description "End.DT2U. Codepoint 23.";
  }

  identity END_DT2M {
    base "SRV6_ENDPOINT_BEHAVIOR_TYPE";
    description "End.DT2M. Codepoint 24.";
  }

  identity END_B6_ENCAPS_RED {
    base "SRV6_ENDPOINT_BEHAVIOR_TYPE";
    description "End.DT2M. Codepoint 27.";
  }

  identity END_USD {
    base "SRV6_ENDPOINT_BEHAVIOR_TYPE";
    description "End with USD. Codepoint 28.";
  }

  identity END_PSP_USD {
    base "SRV6_ENDPOINT_BEHAVIOR_TYPE";
    description "End with PSP and USD. Codepoint 29.";
  }

  identity END_USP_USD {
    base "SRV6_ENDPOINT_BEHAVIOR_TYPE";
    description "End with USP and USD. Codepoint 30.";
  }

  identity END_PSP_USP_USD {
    base "SRV6_ENDPOINT_BEHAVIOR_TYPE";
    description "End with PSP, USP and USD. Codepoint 31.";
  }

  identity END_X_USD {
    base "SRV6_ENDPOINT_BEHAVIOR_TYPE";
    description "End.X with USD. Codepoint 32.";
  }

  identity END_X_PSP_USD {
    base "SRV6_ENDPOINT_BEHAVIOR_TYPE";
    description "End.X with PSP and USD. Codepoint 33.";
  }

  identity END_X_USP_USD {
    base "SRV6_ENDPOINT_BEHAVIOR_TYPE";
    description "End.X with USP and USD. Codepoint 34.";
  }

  identity END_X_PSP_USP_USD {
    base "SRV6_ENDPOINT_BEHAVIOR_TYPE";
    description "End.X with PSP, USP and USD. Codepoint 35.";
  }

  identity END_T_USD {
    base "SRV6_ENDPOINT_BEHAVIOR_TYPE";
    description "End.T with USD. Codepoint 36.";
  }

  identity END_T_PSP_USD {
    base "SRV6_ENDPOINT_BEHAVIOR_TYPE";
    description "End.T with PSP and USD. Codepoint 37.";
  }

  identity END_T_USP_USD {
    base "SRV6_ENDPOINT_BEHAVIOR_TYPE";
    description "End.T with USP and USD. Codepoint 38.";
  }

  identity END_T_PSP_USP_USD {
    base "SRV6_ENDPOINT_BEHAVIOR_TYPE";
    description "End.T with PSP, USP and USD. Codepoint 39.";
  }

  identity END_OP {
    base "SRV6_ENDPOINT_BEHAVIOR_TYPE";
    description "End.OP. Codepoint 40.";
  }

  identity END_OTP {
    base "SRV6_ENDPOINT_BEHAVIOR_TYPE";
    description "End.OTP. Codepoint 41.";
  }

  identity UN_SL_ONLY {
    base "SRV6_ENDPOINT_BEHAVIOR_TYPE";
    description "uN. Codepoint 42.";
  }

  identity UN_SL_END {
    base "SRV6_ENDPOINT_BEHAVIOR_TYPE";
    description "uN (S&L+End). Codepoint 43.";
  }

  identity UN_SL_END_PSP {
    base "SRV6_ENDPOINT_BEHAVIOR_TYPE";
    description "uN (S&L+End PSP). Codepoint 44.";
  }

  identity UN_SL_END_USP {
    base "SRV6_ENDPOINT_BEHAVIOR_TYPE";
    description "uN (S&L+End USP). Codepoint 45.";
  }

  identity UN_SL_END_PSP_USP {
    base "SRV6_ENDPOINT_BEHAVIOR_TYPE";
    description "uN (S&L+End PSP/USP). Codepoint 46.";
  }

  identity UN_SL_END_USD {
    base "SRV6_ENDPOINT_BEHAVIOR_TYPE";
    description "uN (S&L+End USD). Codepoint 47.";
  }

  identity UN_SL_END_PSP_USD {
    base "SRV6_ENDPOINT_BEHAVIOR_TYPE";
    description "uN (S&L+End PSP/USD). Codepoint 48.";
  }

  identity UN_SL_END_USP_USD {
    base "SRV6_ENDPOINT_BEHAVIOR_TYPE";
    description "uN (S&L+End USP/USD). Codepoint 49.";
  }

  identity UN_SL_END_PSP_USP_USD {
    base "SRV6_ENDPOINT_BEHAVIOR_TYPE";
    description "uN (S&L+End PSP/USP/USD). Codepoint 50.";
  }

  identity UA_SX_ONLY {
    base "SRV6_ENDPOINT_BEHAVIOR_TYPE";
    description "uA. Codepoint 51.";
  }

  identity UA_SX_END_X {
    base "SRV6_ENDPOINT_BEHAVIOR_TYPE";
    description "uA (S&L+End.X). Codepoint 52.";
  }

  identity UA_SX_END_X_PSP {
    base "SRV6_ENDPOINT_BEHAVIOR_TYPE";
    description "uA (S&L+End.X PSP). Codepoint 53.";
  }

  identity UA_SX_END_X_USP {
    base "SRV6_ENDPOINT_BEHAVIOR_TYPE";
    description "uA (S&L+End.X USP). Codepoint 54.";
  }

  identity UA_SX_END_X_PSP_USP {
    base "SRV6_ENDPOINT_BEHAVIOR_TYPE";
    description "uA (S&L+End.X PSP/USP). Codepoint 55.";
  }

  identity UA_SX_END_X_USD {
    base "SRV6_ENDPOINT_BEHAVIOR_TYPE";
    description "uA (S&L+End.X USD). Codepoint 56.";
  }

  identity UA_SX_END_X_PSP_USD {
    base "SRV6_ENDPOINT_BEHAVIOR_TYPE";
    description "uA (S&L+End.X PSP/USD). Codepoint 57.";
  }

  identity UA_SX_END_X_USP_USD {
    base "SRV6_ENDPOINT_BEHAVIOR_TYPE";
    description "uA (S&L+End.X USP/USD). Codepoint 58.";
  }

  identity UA_SX_END_X_PSP_USP_USD {
    base "SRV6_ENDPOINT_BEHAVIOR_TYPE";
    description "uA (S&L+End.X PSP/USP/USD). Codepoint 59.";
  }

  identity UDX6 {
    base "SRV6_ENDPOINT_BEHAVIOR_TYPE";
    description "uDX6. Codepoint 60.";
  }

  identity UDX4 {
    base "SRV6_ENDPOINT_BEHAVIOR_TYPE";
    description "uDX4. Codepoint 61.";
  }

  identity UDT6 {
    base "SRV6_ENDPOINT_BEHAVIOR_TYPE";
    description "uDT6. Codepoint 62.";
  }

  identity UDT4 {
    base "SRV6_ENDPOINT_BEHAVIOR_TYPE";
    description "uDT4. Codepoint 63.";
  }

  identity UDT46 {
    base "SRV6_ENDPOINT_BEHAVIOR_TYPE";
    description "uDT46. Codepoint 64.";
  }

  identity UDX2 {
    base "SRV6_ENDPOINT_BEHAVIOR_TYPE";
    description "uDX2. Codepoint 65.";
  }

  identity UDX2V {
    base "SRV6_ENDPOINT_BEHAVIOR_TYPE";
    description "uDX2V. Codepoint 66.";
  }

  identity UDT2U {
    base "SRV6_ENDPOINT_BEHAVIOR_TYPE";
    description "uDX2U. Codepoint 67.";
  }

  identity UDT2M {
    base "SRV6_ENDPOINT_BEHAVIOR_TYPE";
    description "uDX2M. Codepoint 68.";
  }

  identity END_DTM {
    base "SRV6_ENDPOINT_BEHAVIOR_TYPE";
    description "END_DTM. Codepoint 73.";
  }

  identity OPAQUE {
    base "SRV6_ENDPOINT_BEHAVIOR_TYPE";
    description "Opaque. Codepoint 65535.";
  }

  typedef srv6-endpoint-behavior-type {
    type union {
      type identityref {
        base "SRV6_ENDPOINT_BEHAVIOR_TYPE";
      }
      type uint16;
    }
    description
      "Type definition for SRV6 endpoint behavior. Unknown
       values are represented as the numeric value.";
    reference
      "draft-ietf-spring-srv6-network-programming";
  }

  typedef srv6-sid-type {
    type enumeration {
      enum CLASSIC_SID {
        value 1;
      }
      enum USID {
        value 2;
      }
    }
  }

  typedef srv6-sid {
      type inet:ipv6-address;
      description
      "This type defines a SID value in SRv6";
  }

  identity SRV6_MOBILE_FUNCTION_TYPE {
    description
      "Base identity for SRV6 Mobile Function Types";
    reference
      "draft-ietf-dmm-srv6-mobile-uplane";
  }

  identity T_M_GTP4_D {
    base "SRV6_MOBILE_FUNCTION_TYPE";
    description "GTP4.D Mobile Function.";
  }

  identity END_M_GTP6_D {
    base "SRV6_MOBILE_FUNCTION_TYPE";
    description "GTP6.D Mobile Function.";
  }

  identity END_M_GTP6_DI {
    base "SRV6_MOBILE_FUNCTION_TYPE";
    description "GTP6.DI Mobile Function.";
  }

  identity END_M_GTP4_E {
    base "SRV6_MOBILE_FUNCTION_TYPE";
    description "GTP4.E Mobile Function.";
  }

  identity END_M_GTP6_E {
    base "SRV6_MOBILE_FUNCTION_TYPE";
    description "GTP6.E Mobile Function.";
  }

  typedef srv6-mobile-function-type {
    type union {
      type identityref {
        base "SRV6_MOBILE_FUNCTION_TYPE";
      }
      type uint16;
    }
    description
      "Type definition for SRV6 mobile function. Unknown
       values are represented as the numeric value.";
    reference
      "draft-ietf-dmm-srv6-mobile-uplane";
  }

/*
  typedef srv6-function-type {
    type enumeration {
      enum END_NO_PSP_USP {
        value 1;
      }
      enum END_PSP {
        value 2;
      }
      enum END_USP {
        value 3;
      }
      enum END_PSP_USP {
        value 4;
      }
      enum END_X_NO_PSP_USP {
        value 5;
      }
      enum END_X_PSP {
        value 6;
      }
      enum END_X_USP {
        value 7;
      }
      enum END_X_PSP_USP {
        value 8;
      }
      enum END_T_NO_PSP_USP {
        value 9;
      }
      enum END_T_PSP {
        value 10;
      }
      enum END_T_USP {
        value 11;
      }
      enum END_T_PSP_USP {
        value 12;
      }
      enum RESERVED {
        value 13;
      }
      enum END_B6_ENCAP {
        value 14;
      }
      enum END_BM {
        value 15;
      }
      enum END_DX6 {
        value 16;
      }
      enum END_DX4 {
        value 17;
      }
      enum END_DT6 {
        value 18;
      }
      enum END_DT4 {
        value 19;
      }
      enum END_DT46 {
        value 20;
      }
      enum END_DX2 {
        value 21;
      }
      enum END_DX2V {
        value 22;
      }
      enum END_DT2U {
        value 23;
      }
      enum END_DT2M {
        value 24;
      }
      enum RESERVED2 {
        value 25;
      }
      enum RESERVED3 {
        value 26;
      }
      enum END_B6_ENCAPS_RED {
        value 27;
      }
      enum END_USD {
        value 28;
      }
      enum END_PSP_USD {
        value 29;
      }
      enum END_USP_USD {
        value 30;
      }
      enum END_PSP_USP_USD {
        value 31;
      }
      enum END_X_USD {
        value 32;
      }
      enum END_X_PSP_USD {
        value 33;
      }
      enum END_X_USP_USD {
        value 34;
      }
      enum END_X_PSP_USP_USD {
        value 35;
      }
      enum END_T_USD {
        value 36;
      }
      enum END_T_PSP_USD {
        value 37;
      }
      enum END_T_USP_USD {
        value 38;
      }
      enum END_T_PSP_USP_USD {
        value 39;
      }
      enum END_OP {
        value 40;
      }
      enum END_OTP {
        value 41;
      }
      enum UN_SHIFTONLY {
        value 42;
      }
      enum UN {
        value 43;
      }
      enum UN_PSP {
        value 44;
      }
      enum UN_USP {
        value  45;
      }
      enum UN_PSP_USP {
        value  46;
      }
      enum UN_USD {
        value  47;
      }
      enum UN_PSP_USD {
        value  48;
      }
      enum UN_USP_USD {
        value  49;
      }
      enum UN_PSP_USP_USD {
        value  50;
      }
      enum UA_SHIFTONLY {
        value  51;
      }
      enum UA {
        value  52;
      }
      enum UA_PSP {
        value  53;
      }
      enum UA_USP {
        value  54;
      }
      enum UA_PSP_USP {
        value  55;
      }
      enum UA_USD {
        value  56;
      }
      enum UA_PSP_USD {
        value  57;
      }
      enum UA_USP_USD {
        value  58;
      }
      enum UA_PSP_USP_USD {
        value  59;
      }
      enum MAX {
        value 60;
      }
    }
  }
*/
}
