module arcos-relay-agent {
  yang-version 1.1;
  namespace "http://yang.arrcus.com/arcos/relay-agent";
  prefix arc-relay;

  import openconfig-interfaces {
    prefix oc-if;
  }

  organization
    "Arrcus, Inc.";

  contact
    "Arrcus, Inc.
     2077 Gateway Place
     Suite 400
     San Jose, CA 95110
     E-mail: yang-support@arrcus.com";

  description
    "This module contains definitions for the
     native ArcOS DHCP Relay Agent.
     Copyright (c) 2020 by Arrcus, Inc.
     All rights reserved.";

  rpc clear-relay-agent-counters {
    description
      "Request to clear the DHCP relay counters, either globally
       or per interface, if specified";

    input {
      leaf interface {
        type oc-if:interface-id;
        description
          "Interface ID for which to clear the counters";
      }
    }
  }

}
