module arcos-classifier {
  yang-version 1.1;
  namespace "http://yang.arrcus.com/arcos/classifier";
  prefix arc-cfr;

  import arcos-classifier-filter-types {
    prefix arc-cfr-fltr-types;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for generic classifier definitions.
     This is a base data model for classifier that different
     apps can make use of.  This base data model itself does
     not expose container for classifier(For an example look
     at arrcus-qos-classifier.yang)
     
     Copyright (c) 2016-2023 by Arrcus, Inc.
     All rights reserved.";

  revision 2023-06-27 {
    description
      "Initial revision.";
  }

  identity logical-operation-type {
    description
      "Across the filter logical operation types: match-any, match-all";
  }

  identity match-any-filter {
    base logical-operation-type;
    description
      "Logical OR operation across filters in a given classifier";
  }

  identity match-all-filter {
    base logical-operation-type;
    description
      "Logical AND operation across filters in a given classifier";
  }

  grouping filter-attributes {
    description
      "Filter attributes like filter type";
    leaf type {
      type identityref {
        base arc-cfr-fltr-types:FILTER_TYPE;
      }
      description
        "This leaf defines type of a filter";
    }
  }

  grouping filters-top {
    description
      "Grouping for a filter definition. A filter holds a filter specific attributes";
    container filters {
      description
        "Container for filter data-base in a specific classifier";
      list filter {
        key "type";
        description
          "List of filters in a specific classifier. Each filter is
           defined by the grouping filter-attributes";
        leaf type {
          type leafref {
            path "../config/type";
          }
          description
            "unique type identifying filter";
        }
        container config {
          description
            "Configuration parameters relating to filter";
          uses filter-attributes;
        }
        container state {
          config false;
          description
            "Operational state parameters relating to filter";
          uses filter-attributes;
        }
      }
    }
  }

  grouping classifier-attributes {
    description
      "Grouping for classifier attributes like name, description, logical operation";
    leaf name {
      type string {
        length "1..79";
      }
      description
        "Name of a Classifier entry in a list of Classifiers";
    }
    leaf description {
      type string {
        length "1..254";
      }
      description
        "Description of a Classifier entry in a list of Classifiers";
    }
  }

  grouping classifiers-top {
    description
      "Grouping for generic definition of Classifiers";
    container classifiers {
      description
        "Container for classifier data-base";
      list classifier {
        key "name";
        ordered-by user;
        description
          "A specific classifier in the classifier data-base";
        leaf name {
          type leafref {
            path "../config/name";
          }
          description
            "unique name identifying classifier <string, min: 1 chars, max: 79 chars>";
        }
        container config {
          description
            "Configuration parameters relating to classifier";
          uses classifier-attributes;
        }
        container state {
          config false;
          description
            "Operational state parameters relating to classifier";
          uses classifier-attributes;
        }
        uses filters-top;
      }
    }
  }
}
