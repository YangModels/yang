module arcos-openconfig-if-tunnel-augments {
  yang-version 1.1;
  namespace "http://yang.arrcus.com/arcos/openconfig/interfaces/tunnel/augments";
  prefix arc-oc-if-tun-aug;

  import openconfig-if-tunnel {
    prefix oc-tun;
  }

  import openconfig-interfaces {
    prefix oc-if;
  }

  import iana-if-type {
    prefix ianaift;
  }

  import tailf-common {
    prefix tailf;
  }

  organization
    "Arrcus, Inc.";

  contact
    "Arrcus, Inc.
     2077 Gateway Place
     Suite 400
     San Jose, CA 95110

     E-mail: yang-support@arrcus.com";

  description
    "This module defines augments for managing tunnel interfaces.

     Copyright (c) 2016-2021 by Arrcus, Inc.
     All rights reserved.";

  revision 2023-09-12 {
    description "Display tunnel interface config/state based on interface name";
  }

  revision "2021-08-30" {
    description "Initial version";
  }

  grouping vti-config {
    description
      "Configuration data specific for VTI Tunnel";

    leaf dscp-key {
      type uint32 {
        range "0..63";
      }
      description
        "The DSCP value to be specified for the tunnel. This key
         is used to identify a traffic flow within a tunnel.";
    }
  }

  typedef tunnel-mode-type {
    type enumeration {
      enum gre {
        value 1;
        description
          "Tunnel is of type GRE";
      }
      enum vti {
        value 2;
        description
          "Tunnel is of type VTI. Used with IPSEC";
      }
      enum gretap {
        value 3;
        description
          "Tunnel is of type GRETAP";
      }
    }
  }

  grouping tunnel-mode {
    description
      "Configuration mode of the Tunnel";

    leaf mode {
      type tunnel-mode-type;
      default vti;
      description
        "Default mode of the tunnel will be VTI";
      tailf:info "Encapsulation mode of the tunnel";
    }
  }

  augment "/oc-if:interfaces/oc-if:interface/oc-tun:tunnel/oc-tun:config" {
    when "starts-with(current()/../../oc-if:name, 'tunnel')" {
      description "active when the interface is set to type Tunnel";
    }
    description "Adds VTI Tunnel specific configuration to the tunnel interface module";
    uses vti-config;
    uses tunnel-mode;
  }

  augment "/oc-if:interfaces/oc-if:interface/oc-tun:tunnel/oc-tun:state" {
    when "starts-with(current()/../../oc-if:name, 'tunnel')" {
      description "active when the interface is set to type Tunnel";
    }

    description "Adds VTI Tunnel specific configuration to the tunnel interface module";
    uses vti-config;
    uses tunnel-mode;
  }
}
