module arcos-openconfig-macsec-deviations {
  yang-version 1.1;
  namespace "http://yang.arrcus.com/arcos/openconfig/macsec/deviations";
  prefix arc-oc-macsec-dev;

  import openconfig-macsec {
    prefix oc-macsec;
  }

  import openconfig-interfaces {
    prefix oc-if;
  }

  organization
    "Arrcus, Inc";

  contact
    "Arrcus, Inc.
     2077 Gateway Place
     Suite 400
     San Jose, CA 95110

     E-mail: yang-support@arrcus.com";

  description
    "This module defines deviations statements for the
     for OpenConfig MACsec module.
     Copyright (c) 2016-2024 by Arrcus, Inc.
     All rights reserved.";

  revision "2025-01-20" {
    description
      "Enabling confidentiality offset leafs";
  }

  revision "2024-05-10" {
    description
      "Initial version, macsec deviations for unsupported leafs";
  }

  deviation "/oc-macsec:macsec/oc-macsec:mka/oc-macsec:policies/oc-macsec:policy" +
                 "/oc-macsec:state/oc-macsec:sak-rekey-on-live-peer-loss" {
    deviate not-supported;
    description "Not Supported in this release";
  }

  deviation "/oc-macsec:macsec/oc-macsec:mka/oc-macsec:policies/oc-macsec:policy" +
                 "/oc-macsec:config/oc-macsec:sak-rekey-on-live-peer-loss" {
    deviate not-supported;
    description "Not Supported in this release";
  }

  deviation "/oc-macsec:macsec/oc-macsec:mka/oc-macsec:policies/oc-macsec:policy" +
                 "/oc-macsec:state/oc-macsec:use-updated-eth-header" {
    deviate not-supported;
    description "Not Supported in this release";
  }

  deviation "/oc-macsec:macsec/oc-macsec:mka/oc-macsec:policies/oc-macsec:policy" +
                 "/oc-macsec:config/oc-macsec:use-updated-eth-header" {
    deviate not-supported;
    description "Not Supported in this release";
  }

  deviation "/oc-macsec:macsec/oc-macsec:mka/oc-macsec:policies/oc-macsec:policy" +
                 "/oc-macsec:config/oc-macsec:macsec-cipher-suite" {
    deviate not-supported;
    description "Not Supported in this release";
  }

  deviation "/oc-macsec:macsec/oc-macsec:mka/oc-macsec:policies/oc-macsec:policy" +
                 "/oc-macsec:state/oc-macsec:macsec-cipher-suite" {
    deviate not-supported;
    description "Not Supported in this release";
  }

  deviation "/oc-macsec:macsec/oc-macsec:mka/oc-macsec:policies/oc-macsec:policy" +
                 "/oc-macsec:state/oc-macsec:delay-protection" {
    deviate not-supported;
    description "Not Supported in this release";
  }

  deviation "/oc-macsec:macsec/oc-macsec:mka/oc-macsec:policies/oc-macsec:policy" +
                 "/oc-macsec:config/oc-macsec:delay-protection" {
    deviate not-supported;
    description "Not Supported in this release";
  }

  deviation "/oc-macsec:macsec/oc-macsec:mka/oc-macsec:policies/oc-macsec:policy" +
                 "/oc-macsec:state/oc-macsec:include-icv-indicator" {
    deviate not-supported;
    description "Not Supported in this release";
  }

  deviation "/oc-macsec:macsec/oc-macsec:mka/oc-macsec:policies/oc-macsec:policy" +
                 "/oc-macsec:config/oc-macsec:include-icv-indicator" {
    deviate not-supported;
    description "Not Supported in this release";
  }

  deviation "/oc-macsec:macsec/oc-macsec:interfaces/oc-macsec:interface/oc-macsec:mka/oc-macsec:config/oc-macsec:key-chain" {
    deviate not-supported;
    description "Not Supported in this release";
  }

  deviation "/oc-macsec:macsec/oc-macsec:interfaces/oc-macsec:interface/oc-macsec:config/oc-macsec:replay-protection" {
    deviate replace {
      type uint16 {
        range "0..1024";
      }
    }
  }

  deviation "/oc-macsec:macsec/oc-macsec:mka/oc-macsec:policies/oc-macsec:policy" +
                 "/oc-macsec:config/oc-macsec:key-server-priority" {
    deviate replace {
      type uint8 {
        range "97..127";
      }
    }
    deviate replace { default 97; }
  }

  deviation "/oc-macsec:macsec/oc-macsec:mka/oc-macsec:policies/oc-macsec:policy" +
                 "/oc-macsec:config/oc-macsec:macsec-cipher-suite" {
    deviate replace {
      type enumeration {
        enum GCM_AES_128 {
          value 1;
          description
            "GCM-AES-128 Cipher Suite";
        }
        enum GCM_XPN_128 {
          value 3;
          description
            "GCM-XPN-128 Cipher Suite";
        }
      }
    }
  }

}
