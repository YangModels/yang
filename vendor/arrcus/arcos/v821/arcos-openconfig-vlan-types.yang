module arcos-openconfig-vlan-types {
  yang-version 1.1;
  namespace "http://yang.arrcus.com/arcos/openconfig/vlan-types";
  prefix arc-oc-vlan-types;

  import openconfig-interfaces {prefix oc-if; }
  import openconfig-vlan {prefix oc-vlan; }
  import openconfig-vlan-types { prefix oc-vlan-types; }

  organization
    "Arrcus, Inc.";
  contact
    "Arrcus, Inc.
     2077 Gateway Place
     Suite 400
     San Jose, CA 95110
     E-mail: yang-support@arrcus.com";
  description
    "This module defines types to extend the existing 
     openconfig vlan types module.
     Copyright (c) 2016-2023 by Arrcus, Inc.
     All rights reserved.";

  revision 2024-07-01 {
    description
      "Add ARC_TPID_TYPES under tpid and inner-tpid";
  }

  revision 2023-06-29 {
    description
      "Add vlan-stack-action extention for swap-swap and pop-swap actions";
  }

  revision 2023-03-13 {
    description
      "Add vlan-stack-action extention for double tag actions";
  }

  identity ARC_TPID_TYPES {
    description
        "Base identity for TPID values that can be matched
        to tpid and inner-tpid under ingress/engress mapping";
  }

  identity TPID_0X8100 {
    base ARC_TPID_TYPES;
    description
        "Default TPID value for 802.1q single-tagged VLANs.";
  }

  identity TPID_0X88A8 {
    base ARC_TPID_TYPES;
    description
        "TPID value for 802.1ad provider bridging, QinQ or
        stacked VLANs.";
  }

  identity TPID_0X9100 {
    base ARC_TPID_TYPES;
    description
        "Alternate TPID value.";
  }

  identity TPID_0X9200 {
    base ARC_TPID_TYPES;
    description
        "Alternate TPID value.";
  }

  typedef vlan-stack-action-extend {
    type enumeration {
      enum PUSH {
        description
          "Push a VLAN onto the VLAN stack.";
      }
      enum POP {
        description
          "Pop a VLAN from the VLAN stack.";
      }
      enum SWAP {
        description
          "Swap the VLAN at the top of the VLAN stack.";
      }
      enum PUSH-PUSH {
        description
          "double push  the VLAN ids.";
      }
      enum POP-POP {
        description
          "Double pop the tags.";
      }
      enum PUSH-SWAP {
        description
          "Push outer swap inner tags";
      }
      enum POP-SWAP {
        description
          "POP outer swap inner tags";
      }
      enum SWAP-SWAP {
        description
          "swap outer and inner tags";
      }
    }
    description
      "Operations that can be performed on a VLAN stack.";
  }
}
