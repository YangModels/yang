module arcos-hardware-platform-dnx {
  yang-version 1.1;
  namespace "http://yang.arrcus.com/arcos/hardware/platform/dnx";
  prefix arc-hw-platform-dnx;

  revision "2025-08-22" {
    description
      "Adding a hidden debug for BFD hold down timer";
  }

  grouping linkscan-interval {
    leaf interval {
      description "Time interval in millseconds between each linkscan polling. Default 250 milliseconds";
        type uint32 {
          range "10..250";
         }
        units milliseconds;
        default 250;
    }
  }

  grouping dnx-linkscan-interval {
    description "Controls for tuning device specific load balancing configuration";

    container linkscan {
      description "Polling interval for Linkscan";
      uses linkscan-interval;
    }
  }

  grouping force-bfd-holddown-timer {
    leaf enabled {
      description "Enable forced BFD holddown timer";
        type boolean;
        default false;
    }
  }

  grouping dnx-force-bfd-holddown-timer {
    description "Controls for BFD holddown timer configuration";

    container force-bfd-holddown-timer {
      description "Enable forced BFD holddown timer";
      uses force-bfd-holddown-timer;
    }
  }
}
