module arcos-igp-types {
  yang-version 1.1;
  namespace "http://yang.arrcus.com/arcos/igp-types";
  prefix arc-igp-types;

  import openconfig-routing-policy {
    prefix oc-rpol;
  }

  organization
    "Arrcus, Inc.";

  contact
    "Arrcus, Inc.
     2077 Gateway Place
     Suite 400
     San Jose, CA 95110

     E-mail: yang-support@arrcus.com";

  description
    "This module contains definitions for the
     native ArcOS IGP domain.

     Copyright (c) 2016-2020 by Arrcus, Inc.
     All rights reserved.";

  revision 2020-06-23 {
    description "Initial version";
  }

  /*
   * IGP Algorithm Types identity.
   */
  identity IGP_ALGORITHM_TYPE {
    description
      "Base identity for IGP algorithms.";
  }

  identity SPF {
    base "IGP_ALGORITHM_TYPE";
    description
      "Shortest Path First (SPF) algorithm based on link metric. This
       algorithm is advertised as numeric value 0.";
    reference
      "RFC8665: OSPF Extensions for Segment Routing section 8.5";
  }

  identity STRICT_SPF {
    base "IGP_ALGORITHM_TYPE";
    description
      "Strict shortest Path First (SPF) algorithm based on link metric.
       This algorithm is advertised as numeric value 1.";
    reference
      "RFC8665: OSPF Extensions for Segment Routing section 8.5";
  }

  typedef igp-algorithm-type {
    type union {
      type identityref {
        base "IGP_ALGORITHM_TYPE";
      }
      type uint8;
    }
    description
      "Type definition for IGP Algorithm Types. Unknown types are
       represented as a numeric value.";
    reference
      "RFC8665: OSPF Extensions for Segment Routing section 8.5";
  }

  /*
   * IGP MSD Types identity.
   */
  identity MSD_TYPE {
    description "Base identity for Maximum SIDs Depth (MSD) type";
  }

  identity SRV6_MAX_SEGMENTS_LEFT {
    base MSD_TYPE;
    description
      "The maximum value of 'SL' field in the SRH of a
       received packet. Value 41.";
  }

  identity SRV6_MAX_END_POP {
    base MSD_TYPE;
    description
      "The maximum number of SIDS in the top SRH in an SRH
       stack to which the router can apply 'PSP' or 'USP'. Value 42.";
  }

/*
  identity SRV6_MAX_T_INSERT {
    base MSD_TYPE;
    description
      "The maximum number of SIDs can be inserted as port of
       the 'T.insert' behavior.";
  }
*/

  identity SRV6_MAX_H_ENCAPS {
    base MSD_TYPE;
    description
      "The maximum number of SIDs can be included as part of
       the 'H.Encaps' behavior. Value 44.";
  }

  identity SRV6_MAX_END_D {
    base MSD_TYPE;
     description
       "The maximum number of SIDs in an SRH when performing
        decapsulation associated with 'End.Dx' functions
        (e.g., 'End.DX6' and 'End.DT6'). Value 45.";
  }

  typedef msd-type {
    type union {
      type identityref {
        base MSD_TYPE;
      }
      type uint8;
    }
  }

  grouping default-information-originate-config {
    leaf enabled {
      type boolean;
      description
        "Enable advertisement of default route";
    }

    leaf always {
      type boolean;
      description
        "Always advertise default route regardless of RIB state";
    }

    uses oc-rpol:apply-policy-export-config;
  }

  grouping default-information-originate-config-top {
    container config {
      description
        "Configuration parameters relating to default-information originate";
      uses default-information-originate-config;
    }
  }

  grouping default-information-originate-state-top {
    container state {
      config false;
      description
        "State information relating to default-information originate";
      uses default-information-originate-config;

      leaf advertised {
        type boolean;
        description
          "This boolean being set to true indicates that default route is advertised";
      }
    }
  }

  grouping default-information-top {
    container default-information {
      description
        "IGP default-information parameters";
      container originate {
        description
          "IGP default-information parameters";
        uses default-information-originate-config-top;
        uses default-information-originate-state-top;
      }
    }
  }
}
