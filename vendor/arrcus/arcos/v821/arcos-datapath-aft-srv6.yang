submodule arcos-datapath-aft-srv6 {
  yang-version "1.1";

  belongs-to "arcos-datapath-aft" {
    prefix "arcos-dp-aft";
  }

  import ietf-inet-types { prefix "inet"; }

  import arcos-aft-types { prefix "arc-aft-types"; }
  import arcos-srv6-types { prefix "arc-srv6-types"; }


  // Include common cross-AFT groupings from the common submodule.
  include arcos-datapath-aft-common;

  organization
    "Arrcus, Inc";

  contact
    "Email: eng@arrcus.com";

  description
    "Submodule containing definitions of groupings for the abstract
    forwarding table for SRv6 SID forwarding.";

  grouping aft-srv6-sid-structural {
    description
      "Structural grouping defining the schema for the SRv6 SID
      abstract forwarding table.";

    list srv6-sid-entry {
      key "local-sid";

      description
        "List of the SRv6 SID entries within the abstract
        forwarding table. This list is keyed by the SRv6 Local
        SID.";

      leaf local-sid {
        type leafref {
          path "../state/local-sid";
        }
        description
          "Reference to the local-sid  matched by the
          entry.";
      }

      container state {
        config false;
        description
          "Operational state parameters for the SRv6 SID AFT
          entry.";
        uses aft-srv6-sid-entry-config;
        uses aft-srv6-sid-entry-state;
      }

    }
  }

  grouping aft-srv6-sid-entry-config {
    description
      "Configuration parameters for the SRv6 SID entry.";

    leaf local-sid {
      description
        "SRv6 Local SID";
      type inet:ipv6-prefix;
    }
  }

  grouping aft-srv6-sid-entry-state {
    description
      "Operational state parameters for the SRv6 SID entry.";
    uses aft-common-entry-state;

    leaf sid-type {
      description
        "SRv6 SID Type";
      type arc-srv6-types:srv6-sid-type;
    }

    leaf function {
      description
        "SRv6 Function";
      type arc-srv6-types:srv6-endpoint-behavior-type;
    }

    leaf nh-id {
      description
        "NH ID for End.DX/End.X";
      type uint32;
    }
    
    leaf sid-vrf-id {
      description
        "HW VRF ID for End.DT/uDT";
      type uint32;
    }
    
    leaf sid-vrf-name {
      description
        "VRF name for End.DT/uDT";
      type string;
    }
    
    leaf flags {
      description
        "SID specific flag";
      type uint32;
    }

    leaf tunnel-terminator-id {
      description
        "SRv6 tunnel terminator HW ID";
      type uint32;
    }
    
    leaf tunnel-terminator-priority {
      description
        "SRv6 tunnel terminator TCAM entry priority";
      type uint32;
    }
  }
}
