module arcos-clear-pfc-stats {

  yang-version "1.1";

  namespace "http://yang.arrcus.com/arcos/clear/pfc/statistics";

  prefix "arc-clr-pfc-stats";

  import tailf-common {
    prefix tailf;
  }
  import arcos-platform {prefix arc-platform;}
  import openconfig-interfaces { prefix "oc-if"; }
  import arcos-runtime {
    prefix arc-runtime;
  }

  organization
    "Arrcus, Inc";

  contact
    "Arrcus, Inc.
     2077 Gateway Place
     Suite 400
     San Jose, CA 95110
     E-mail: yang-support@arrcus.com";

  description
     "This model defines a clear pfc instance to clear interface pfc statistics.
     Copyright (c) 2023 by Arrcus, Inc.
     All rights reserved.";

  revision "2025-01-31" {
    description
      "Enable clear pfc stats";
  }

  grouping pfc-stats-top {
      container pfc {
      action statistics {
        input {
          leaf interface {
            mandatory true;
            type leafref {
              path "/oc-if:interfaces/oc-if:interface/oc-if:config/oc-if:name";
            }
          }
        }
        output {
          leaf result {
            type string;
            description "The status of operation";
          }
          leaf result_code {
            type boolean;
            description "The status code of operation";
          }
        }
      }
    }
  }


  augment "/arc-runtime:runtime-instances" +
          "/arc-runtime:runtime-instance" {
      uses pfc-stats-top;
  }
  uses pfc-stats-top {
      when "(/arc-platform:platform/arc-platform:asic = 'arc-platform:BROADCOM_TOMAHAWK5')";
  }
}
