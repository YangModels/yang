module arcos-openconfig-bgp-deviations {
  yang-version 1.1;
  namespace "http://yang.arrcus.com/arcos/openconfig/bgp/deviations";
  prefix arc-oc-bgp-dev;

  import openconfig-bgp {
    prefix oc-bgp;  
  }

  organization
    "Arrcus, Inc.";

  contact
    "Arrcus, Inc.
     2077 Gateway Place
     Suite 400
     San Jose, CA 95110
     E-mail: yang-support@arrcus.com";

  description
    "This module defines deviations for Arrcus
     implementation of the openconfig BGP module.

     Copyright (c) 2016-2023 by Arrcus, Inc.
     All rights reserved.";

  revision 2023-12-19 {
    description
      "Addition of the four mandatory headers.";
  }

  deviation "/oc-bgp:bgp" {
    deviate not-supported;
    description "BGP configuration is allowed under network instance,
                 and is not supported at root level.";
  }
}
