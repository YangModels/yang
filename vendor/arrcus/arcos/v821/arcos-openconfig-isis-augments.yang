module arcos-openconfig-isis-augments {
  yang-version 1.1;
  namespace "http://yang.arrcus.com/arcos/openconfig/isis/augments";
  prefix arc-oc-isis-aug;

  import ietf-inet-types {
    prefix inet;
  }

  import ietf-yang-types {
    prefix yang;
  }

  import openconfig-network-instance {
    prefix oc-ni;
  }

  import openconfig-types {
    prefix oc-types;
  }

  import openconfig-interfaces {
    prefix oc-if;
  }

  import openconfig-policy-types {
    prefix oc-pol-types;
  }

  import openconfig-isis {
    prefix oc-isis;
  }

  import openconfig-isis-types {
    prefix oc-isis-types;
  }

  import openconfig-isis-lsdb-types {
    prefix oc-isis-lsdb-types;
  }

  import arcos-isis-types {
    prefix arc-isis-types;
  }

  import openconfig-mpls-types {
    prefix oc-mpls-types;
  }

  import arcos-srv6 {
    prefix arc-srv6;
  }

  import arcos-srv6-types {
    prefix arc-srv6-types;
  }

  import arcos-igp-types {
    prefix arc-igp-types;
  }

  import arcos-te {
    prefix arc-te;
  }

  import openconfig-bfd {
    prefix oc-bfd;
  }

  import openconfig-network-instance {
    prefix oc-netinst;
  }

  import arcos-openconfig-segment-routing-augments {
    prefix arc-oc-sr-aug;
  }

  import openconfig-routing-policy {
    prefix oc-rpol;
  }

  import arcos-common-types {
    prefix arc-common-types;
  }

  organization
    "Arrcus, Inc.";

  contact
    "Arrcus, Inc.
     2077 Gateway Place
     Suite 400
     San Jose, CA 95110
     E-mail: yang-support@arrcus.com";

  description
    "This module defines augmentation for Arrcus
     implemention of the openconfig ISIS module.
     Copyright (c) 2018-2024 by Arrcus, Inc.
     All rights reserved.";

  revision "2025-09-08" {
    description
      "Updated rib-update-delay to 10 minutes";
  }

  revision "2025-08-11" {
    description
      "Add support for Adjacency uptime.";
  }

  revision "2025-07-27" {
    description
      "Add rpol support to summary prefix configuration";
  }

  revision "2025-07-22" {
    description
      "Add System-ID to Dynamic-hostname mapping (TLV-137).";
  }   

  revision "2025-07-17" {
    description
      "Added adjacency state change tracking fields including:
       * num-state-changes counter
       * last-state-change-timestamp
       * last-down-reason with detailed enumeration";
  }

  revision "2025-04-08" {
    description
      "Add SPF MircoLoop Avoidance timer configuration";
  }

  revision 2025-04-07 {
    description
      "Add fast-reroute timer configuration";
  }

  revision 2025-04-01 {
    description "Add Purge Originator Identification (POI) TLV config";
  }

  revision 2025-03-26 {
    description "Removed default metric of 10 for summary";
  }

  revision 2025-02-11 {
    description "Use the ASLA bitmask position from RFC 8919 for standard application";
  }

  revision "2025-01-10" {
    description
      "Update maximum srlg membership per interface to 30.";
  }

  revision "2024-12-12" {
    description
      "Add system-id attribute to the LSP information";
  }

  revision "2024-11-11" {
    description
      " * Remove SID from P / Q / PQ Node information in fast-reroute
        * Remove incorrect state container for selected-definitions";
  }

  revision "2024-09-23" {
    description
      "Add unreachable prefix announcement (UPA) config";
  }

  revision "2024-09-13" {
    description
      "Add P_AND_Q_ARE_REMOTE flags and SRLG_PROTECTION type";
  }

  revision "2024-08-12" {
    description
      "Add mgd-memory stats";
  }

  revision "2024-08-09" {
    description
      "Add interface/srlg-membership
       Add interface/fast-reroute/tiebreaker";
  }

  revision "2024-06-20" {
    description
      "Removing when check for advertise-enabled";
  }

  revision "2024-06-17" {
    description
    "* Add interface/[config|state]/tag
     * Add interface/[config|state]/tag64
     * Add global/afi-safi/af/routes/route/levels/level/state/route-tag
     * Add global/afi-safi/af/redistribute-routes/route/levels/level/state/route-tag
     * Add global/afi-safi/af/summary-prefix";
  }

  revision "2024-04-19" {
    description
      "Add metric and maximum-hop-count attributes in nexthop";
  }

  revision "2024-03-28" {
    description
      "* Support for configuration of ASLA for SR-Policy application
       * The state model for ASLA sub-TLV now accomodates multiple
         sub-tlvs for same application";
  }

  revision "2024-03-21" {
    description
      "Add level stats summary container with lsp-count";
  }

  revision "2024-03-20" {
    description
      "Add circuit counters for dropped IIH packets due to
       address misconfiguration";
  }

  revision "2024-03-07" {
    description
      "Active measurement based config and state parameters";
  }

  revision "2024-02-12" {
    description
      "Admin group subtlv support based on RFC 5305";
  }

  revision "2024-01-17" {
    description
      "Move route-levels-top out-labels to next-hops container";
  }

  revision "2024-01-10" {
    description
      "Add config option for per-level labeled preference";
  }

  revision "2023-11-25" {
    description
      "Added status for IP unnumbered interface";
  }

  revision 2023-09-20 {
    description
      "Change default value of IGP-LDP sync per interface";
  }

  revision "2023-05-03" {
    description
      "Updated to add support for Segment Routing Mapping Server";
  }

  revision "2023-04-12" {
    description
      "Use level-number directly in as key instead of leafref in
       global route, redistribute-route and fast-reroute oper status";
  }

  revision "2023-03-26" {
    description
      "ASLA subTLVs for IS Reachability";
  }

  revision "2023-01-22" {
    description
      "Add per address family microloop avoidance config option for mpls";
  }

  revision "2023-01-15" {
    description
      "Updated to add support for multiple BFD profiles";
  }

  revision "2022-12-30" {
    description
      "Add mpls config option for fast re-route ti-lfa";
  }

  revision "2022-12-20" {
    description
      "Add global hello authentication configuration";
  }

  revision 2022-11-03 {
    description
      "Added option to disable CSNP per interface";
  }

  revision "2022-11-03" {
    description
      "Add network-instance table ID to global state";
  }

  revision "2022-06-18" {
    description
      "Updated to add support for IP Fast Reroute (RFC 5286)";
  }

  revision "2018-10-20" {
    description
      "Initial Revision
       * Add global/state/is-type.
       * Add global/af/routes.
       * Add global/af/redistribute-routes.
       * Add global/af/prefix-trackings.
       * Add level/authentication/key/[config|state]/crypto-algorithm.
       * Add level/link-state-database/lsp/state/[srm-count|ssn-count].
       * Add level/link-state-database/lsp/state/[srm-set|ssn-set].
       * Add level/link-state-database/lsp/state/[overload-bit|attached-bit].
       * Add level/link-state-database/lsp/state/[is-type].
       * Add level/link-state-database/lsp/state/received-remaining-lifetime.
       * Add level/link-state-database/lsp/state/last-update-ifindex.
       * Add level/link-state-database/lsp/state/last-update-time.
       * Add level/link-state-database/.../neighbor/state/two-way-connectivity.
       * Add interface/[config|state]/network-type.
       * Add interface/state/circuit-id.
       * Add interface/state/protocol-up.
       * Add interface/state/mtu.
       * Add interface/state/update-index.
       * Add interface/state/ifindex.
       * Add interface/state/next-lsp-transmission.
       * Add interface/state/next-lsp-retransmission.
       * Add interface/state/snpa.
       * Add interface/authentication/crypto-algorithm.
       * Add interface/level/adjacency/state/neighbor-lan-id.
       * Add interface/level/adjacency/state/usable.
       * Add interface/level/adjacency/bfd/[...]
       * Add interface/level/[config|state]/metric.
       * Add interface/level/state/lan-id.
       * Add interface/level/packet-counters/lsp/state/no-memory.
       * Add interface/level/hello-authentication/key/[config|state]
       *     /crypto-algorithm.
       * Add interface/timers/[hello-interval|hello-multiplier].
       * Add circuit-counters to interface/level.
       * Add global/spf-log.
       * Add level/state/next-spf.
      ";
    reference
      "RFC 6020: YANG - A Data Modeling Language for the
       Network Configuration Protocol (NETCONF)";
  }

  /*
   * Route flag identity.
   */
  identity route-flag {
    description "Base identity for route flag.";
  }

  identity connected {
    base route-flag;
    description "Connected route.";
  }

  identity remote {
    base route-flag;
    description "Remote route.";
  }

  identity srv6-locator {
    base route-flag;
    description "SRv6 locator route.";
  }

  identity redistribute {
    base route-flag;
    description "Redistributed route.";
  }

  identity distribute {
    base route-flag;
    description "Distributed route.";
  }

  identity default-information {
    base route-flag;
    description "Default-information originate route.";
  }

  identity down {
    base route-flag;
    description "Down bit set.";
  }

  identity summary {
    base route-flag;
    description "Summary route.";
  }

  identity upa {
    base route-flag;
    description "Unreachable prefix announcement (UPA) route";
  }

  identity suppressed {
    base route-flag;
    description "Suppressed by a summary route.";
  }

  identity best {
    base route-flag;
    description "Best route.";
  }

  identity unnumbered {
    base route-flag;
    description "Unnumbered route.";
  }

  identity prefix-tracking-flag {
    description "Base identity for prefix tracking flag.";
  }

  identity conditional {
    base prefix-tracking-flag;
    description "Conditional prefix tracking.";
  }

  identity routing-policy {
    base prefix-tracking-flag;
    description "Routing policy prefix tracking.";
  }

  identity pending {
    base prefix-tracking-flag;
    description "Pending prefix tracking.";
  }

  identity stale {
    base prefix-tracking-flag;
    description "Stale prefix tracking.";
  }

  /*
   * Crypto type identity.
   */
  identity CRYPTO_TYPE {
    description "Base identity for crypto-algorithm.";
  }

  identity MD5 {
    base CRYPTO_TYPE;
    description "The MD5 algorithm.";
  }

  typedef node-id {
    type string {
      pattern
        '[0-9A-Fa-f]{4}\.[0-9A-Fa-f]{4}\.[0-9A-Fa-f]{4}\.[0-9][0-9]';
    }
    description
      "This type defines ISIS node ID. ISIS node ID type should be in
       the form of xxxx.xxxx.xxxx.xx. It is used to represent LAN ID
       and circuit ID";
  }

  grouping global-tracker-top {
    description
      "Protection tracker information";
    leaf id {
      type leafref {
        path "../state/id";
      }
      description
        "Unique identifier for specific tunnel";
    }
    container state {
      leaf id {
        type uint64;
        description
          "Unique identifier for protection tracker";
      }
      leaf reference-count {
        type uint32;
        description
          "Count of nexthops refers to this protection tracker";
      }
      leaf interface {
        type oc-if:interface-id;
        description
          "The outgoing interface.";
      }
      leaf system-id {
        type arc-isis-types:system-name;
        description
          "Neighbor system-id this protection tracks";
      }
      leaf bfd-source {
        type inet:ip-address;
        description
          "BFD Source address";
      }
      leaf bfd-destination {
        type inet:ip-address;
        description
          "BFD Destination address";
      }
      leaf bfd-session-id {
        type uint64;
        description
          "BFD Session ID";
      }
      uses arc-common-types:common-state-attrs;
    }
  }

  grouping global-trackers-top {
    description
      "This grouping defines protection trackers used by ISIS nexthops";
    container protection-trackers {
      config false;
      description
        "This container defines tunnels used by nexthop";
      list protection-tracker {
        description
          "Protection tracker information";
        key "id";
        uses global-tracker-top;
      }
    }
  }

  identity TUNNEL_USER {
    description "Base identity for tunnel user type";
  }
  identity TI_LFA_TUNNEL {
    base TUNNEL_USER;
    description "Used by TI-LFA.";
  }
  identity MICRO_LOOP_AVOID_TUNNEL {
    base TUNNEL_USER;
    description "Used by Micro-loop avoidance.";
  }

  grouping srv6-tunnel-top {
    description
      "SRv6 tunnel information";
    container srv6-tunnel {
      description
        "SRv6 tunnel information";
      leaf source {
        type inet:ip-address;
        description
          "SRv6 tunnel source";
      }
      leaf destination {
        type inet:ip-address;
        description
          "SRv6 tunnel destination";
      }
      leaf num-sids {
        type uint32;
        description
          "Number of SIDs";
      }
      leaf-list sids {
        type inet:ipv6-address;
        description
          "SID List information";
      }
    }
  }

  grouping global-tunnel-top {
    description
      "Tunnel informaiton";
    leaf id {
      type leafref {
        path "../state/id";
      }
    }
    container state {
      leaf id {
        type uint64;
        description
          "Unique identifier for specific tunnel";
      }
      leaf nexthop-address {
        description "Nexthop address";
        type inet:ip-address;
      }
      leaf nexthop-interface {
        description "Nexthop interface";
        type string;
      }
      leaf-list users {
        type identityref {
          base TUNNEL_USER;
        }
        description "Users of this tunnel.";
      }
      leaf tunnel-type {
        type enumeration {
          enum SRV6_TUNNEL {
            description
              "SRv6 tunnel type";
          }
        }
      }
      leaf reference-count {
        type uint32;
        description
          "Number of nexthops that uses this tunnel";
      }
      uses srv6-tunnel-top;
    }
  }

  grouping global-tunnels-top {
    description
      "This grouping defines tunnels used by ISIS nexthops";
    container tunnels {
      config false;
      description
        "This container defines tunnels used by nexthop";
      list tunnel {
        description
          "Tunnel information";
        key "id";
        uses global-tunnel-top;
      }
    }
  }

  identity PROTECTION_TYPE {
    description "Base identity for protection type";
  }
  identity LINK_PROTECTION {
    base PROTECTION_TYPE;
    description "Link protection";
  }
  identity NODE_PROTECTION {
    base PROTECTION_TYPE;
    description "Node protection";
  }
  identity SRLG_PROTECTION {
    base PROTECTION_TYPE;
    description "SRLG protection";
  }

  identity SRV6_LFA_FLAG {
    description "Base identity for SRv6 Flag";
  }

  identity PQ_IS_ADJACENT {
    base SRV6_LFA_FLAG;
    description "PQ Node is adjacent";
  }

  identity P_AND_Q_ARE_ADJACENT {
    base SRV6_LFA_FLAG;
    description "P and Q nodes are adjacent";
  }

  identity PQ_IS_REMOTE {
    base SRV6_LFA_FLAG;
    description "PQ node is remote";
  }

  identity P_AND_Q_ARE_REMOTE {
    base SRV6_LFA_FLAG;
    description "P and Q nodes are remote";
  }

  typedef node-sid-type {
    type union {
      type inet:ipv6-address;
      type uint32;
    }
    description
      "Type definition for NODE SID";
  }

  grouping global-fast-reroute-top {
    description
      "Protection information";

    container levels {
      description
        "This container defines ISIS level specific route information.";

      list level {
        key "level-number";

        description
          "List of ISIS level specific route information.";

        leaf level-number {
          type oc-isis-types:level-number;
          description
            "ISIS level-number.";
        }

        container state {
          leaf level-number {
            type oc-isis-types:level-number;
            description
              "ISIS level number (level-1, level-2).";
          }
          leaf reroute-type {
            type enumeration {
              enum MICRO_LOOP_AVOIDANCE {
                description "Micro-loop avoidance";
              }
              enum TI_LFA {
                description "Topology independant loop free alternate";
              }
              enum IP_FRR {
                description "IP Fast Reroute Loop Free Alternate";
              }
            }
            description "Fast reroute type";
          }
          leaf-list protection-types {
            description "Protection types";
            type identityref {
              base PROTECTION_TYPE;
            }
          }
          leaf origin-system-id {
            type arc-isis-types:system-name;
            description
              "Route origin system ID";
          }
          leaf metric {
            description "Metric to reach the node";
            type uint32;
          }
          leaf nexthop-address {
            description "Nexthop address";
            type inet:ip-address;
          }
          leaf nexthop-interface {
            description "Nexthop interface";
            type string;
          }
          leaf-list flags {
            description "Fast-reroute flags";
            type identityref {
              base SRV6_LFA_FLAG;
            }
          }
          uses arc-common-types:common-state-attrs;
        }
        container p-node {
          container state {
            leaf system-id {
              type oc-isis-types:system-id;
              description
                "Node system ID";
            }
          }
          description "P node information";
        }
        container q-node {
          container state {
            leaf system-id {
              type oc-isis-types:system-id;
              description
                "Node system ID";
            }
          }
          description "Q node information";
        }
        container pq-node {
          container state {
            leaf system-id {
              type oc-isis-types:system-id;
              description
                "Node system ID";
            }
          }
          description "PQ node information";
        }
      }
    }
  }

  /*
   * Multi-topology pre-defined topology IDs
   */
  identity ISIS_MT_TOPO_ID {
    description "Base identity for multi-topology ID.";

    reference "RFC 5120: Multi Topology (MT) Routing in Intermediate
               System to Intermediate Systems (IS-ISs).";
  }

  identity ISIS_MT_ID0_STANDARD {
    base ISIS_MT_TOPO_ID;
    description "Topology ID #0 defined for 'standard' topology.";
  }

  identity ISIS_MT_ID2_IPV6_UNICAST {
    base ISIS_MT_TOPO_ID;
    description "Topology ID #2 defined for 'IPv6 routing' topology.";
  }

  /*
   * Multi-Topology topology ID
   */
  typedef isis-multi-topology-id {
    type union {
      type uint16 {
        range "0..4095";
      }

      type identityref {
        base ISIS_MT_TOPO_ID;
      }
    }

    description
      "ISIS multi-topology identifier.";
  }

  /* 
  * SABM
  */
  typedef isis-sabm {
    type union {
      type bits {
        bit rsvp-te {
          position 0;
        }
        bit sr-policy {
          position 1;
        }
        bit lfa {
          position 2;
        }
        bit flexible-algorithm {
          position 3;
        }
      }
      type uint64;
    }
    description
      "ISIS standard-applications identifier.";
  }

  /*
   * Nexthops
   */
  grouping global-nexthops-top {
    description
      "This grouping defines ISIS nexthop paths sets.";

    container next-hop-sets {
      config false;
      description
        "This container defines a set of ISIS nexthop path information.";

      list next-hop-set {
        key "id";

        description
          "List of ISIS next-hop path set information.";

        leaf id {
          type leafref {
            path "../state/id";
          }
          description
            "Unique Identfier for the specific set of Next-hops.";
        }

        container state {
          description
            "This container defines ISIS next-hop path information.";

          leaf id {
            type uint64;
            description
              "Unique Identfier for the specific set of Next-hops.";
          }

          leaf next-hop-count {
            type uint32;
            description
              "Number of path information to be found in the next-hop-set.";
          }

          leaf reference-count {
            type uint32;
            description
              "Number of routes referring to this next-hop-set.";
          }

          leaf protection-tracker-id {
            type uint64;
            description
              "Protection tracker identifier";
          }
        }

        container next-hops {
          config false;
          description
            "This container defines a specific individual next-hop path information.";

          list next-hop {
            key "outgoing-interface next-hop-address";
            description
              "List ISIS level specific route next hop information.";

            leaf outgoing-interface {
              type leafref {
                path "../state/outgoing-interface";
              }
              description
                "Reference to ISIS interface.";
            }

            leaf next-hop-address {
              type leafref {
                path "../state/next-hop-address";
              }
              description
                "Reference to ISIS next hop address.";
            }

            container state {
              description
                "This container defines ISIS level specific route next hops
                state information.";

              leaf outgoing-interface {
                type oc-if:interface-id;
                description
                  "The outgoing interface.";
              }

              leaf outgoing-ifindex {
                type uint32;
                description
                  "The outgoing interface index.";
              }

              leaf next-hop-address {
                type inet:ip-address;
                description
                  "The next hop address.";
              }

              leaf maximum-hop-count {
                type uint32;
                description
                  "Maximum hops to reach the destination";
              }

              leaf metric {
                type uint32;
                description
                  "Metric to reach the destination";
              }

              leaf tunnel-id {
                type uint64;
                description
                  "The next hop tunnel identifier.";
              }

              leaf-list out-labels {
                type oc-mpls-types:mpls-label;
                description
                  "Indicates the out-label list for the SR LSP paths";
              }

              leaf backup {
                type boolean;
                description
                  "The next hop used as backup.";
              }
              uses arc-common-types:common-state-attrs;
            }
          }
        }
      }
    }
  }

  augment "/oc-ni:network-instances/oc-ni:network-instance" +
          "/oc-ni:protocols/oc-ni:protocol/oc-ni:isis/oc-ni:global" {
    uses global-nexthops-top;
    uses global-tunnels-top;
    uses global-trackers-top;
  }

  grouping global-state-top {
    leaf is-type {
      type identityref {
        base arc-isis-types:level-bits;
      }
      description
        "ISIS is-type.";
    }
    leaf table-id {
      type uint32;
      description
        "System table ID of this network-instance.";
    }
  }

  augment "/oc-ni:network-instances/oc-ni:network-instance" +
          "/oc-ni:protocols/oc-ni:protocol/oc-ni:isis/oc-ni:global" +
          "/oc-ni:state" {
    uses global-state-top;
  }

  identity FLEX_ALGO_METRIC_TYPE {
    description
      "Base identity for metric-type in flexible algorithm";
  }
  identity LINK_DELAY {
    base FLEX_ALGO_METRIC_TYPE;
    description
      "Link delay metric";
  }
  identity TE_METRIC {
    base FLEX_ALGO_METRIC_TYPE;
    description "Traffic-engineering metric";
  }
  identity IGP_METRIC {
    base FLEX_ALGO_METRIC_TYPE;
    description "IGP metric";
  }

  grouping flexible-algorithms-top {
    container flexible-algorithms {
      list flexible-algorithm {
        key "id";
        leaf id {
          type leafref {
            path "../config/id";
          }
          description
            "Flexible algorithm identifier";
        }
        container config {
          uses flexible-algorithm-config-top;
        }
        container state {
          config false;
          uses flexible-algorithm-config-top;
        }
        container selected-definitions {
          config false;
          description
            "Selected flexible algorithm defintion for IS-IS levels";
          list selected-definition {
            key "level-number";

            leaf level-number {
              type oc-isis-types:level-number;
              description
                "ISIS level number (level-1, level-2).";
            }

            container state {
              uses flexible-algorithm-state-top;
            }
          }
        }
      }
    }
  }

  grouping flexible-algorithm-definition-common {
    leaf id {
      type uint8 {
        range "128..255";
      }
      description "Flexible algorithm identifier";
    }
    leaf priority {
      type uint8;
      default 128;
      description "Flexible algorithm priority";
    }
    leaf metric-type {
      type identityref {
        base FLEX_ALGO_METRIC_TYPE;
      }
      default IGP_METRIC;
      description
        "Metric-type for flexible algorithm";
    }
  }

  grouping flexible-algorithm-definition-config-top {
    uses flexible-algorithm-definition-common;

    container admin-groups {
      leaf-list exclude-any {
        type leafref {
          path "/oc-ni:network-instances/oc-ni:network-instance" +
            "/arc-te:te/arc-te:admin-groups/arc-te:admin-group" +
            "/arc-te:config/arc-te:name";
        }
        description
          "list of admin-groups that are to be excluded
          in this algorithm";
      }
      leaf-list include-any {
        type leafref {
          path "/oc-ni:network-instances/oc-ni:network-instance" +
            "/arc-te:te/arc-te:admin-groups/arc-te:admin-group" +
            "/arc-te:config/arc-te:name";
        }
        description
          "list of admin-groups that are to be included
          in this algorithm";
      }
      leaf-list include-all {
        type leafref {
          path "/oc-ni:network-instances/oc-ni:network-instance" +
            "/arc-te:te/arc-te:admin-groups/arc-te:admin-group" +
            "/arc-te:config/arc-te:name";
        }
        description
          "list of admin-groups that must be included
          in this algorithm";
      }
    }
  }

  grouping flexible-algorithm-definition-state-top {
    uses flexible-algorithm-definition-common;

    container admin-groups {
      leaf-list exclude-any {
        type union {
          type string;
          type uint32;
        }
        description
          "list of admin-groups that are to be excluded
          in this algorithm";
      }
      leaf-list include-any {
        type union {
          type string;
          type uint32;
        }
        description
          "list of admin-groups that are to be included
          in this algorithm";
      }
      leaf-list include-all {
        type union {
          type string;
          type uint32;
        }
        description
          "list of admin-groups that must be included
          in this algorithm";
      }
    }
  }

  grouping flexible-algorithm-config-top {
    container advertise-definition {
      leaf enabled {
        type boolean;
        default false;
        description
          "Advertisement of algorithm definition";
      }
    }
    uses flexible-algorithm-definition-config-top;
  }

  grouping flexible-algorithm-state-top {
    leaf level-number {
      type oc-isis-types:level-number;
      description
        "ISIS level number (level-1, level-2).";
    }
    leaf system-id {
      type arc-isis-types:system-name;
      description "Describes the system ID whose
                          flexible-algorithm was selected.";
    }
    uses flexible-algorithm-definition-state-top;
  }

  grouping flexible-algorithm-interface-top {
    container flexible-algorithm {
      container config {
        uses admin-group-affinity-top;
        description
          "Flexible algorithm interface configuration";
      }
      container state {
        config false;
        uses admin-group-affinity-top;
        description
          "Flexible algorithm interface state";
      }
      description
        "Flexible algorithm interface configuration";
    }
  }

  grouping admin-group-affinity-top {
    leaf-list admin-groups {
      type leafref {
        path "../../../../../../../../arc-te:te/arc-te:admin-groups" +
             "/arc-te:admin-group/arc-te:config/arc-te:name";
      }
    }
  }

  grouping sr-policy-interface-top {
    container sr-policy {
      container config {
        uses admin-group-affinity-top;
        description
          "SR-Policy interface configuration";
      }
      container state {
        config false;
        uses admin-group-affinity-top;
        description
          "SR-Policy interface state";
      }
      description
        "SR-Policy interface configuration";
    }
  }

  grouping te-config-top {
    container traffic-engineering {
      description
        "This container defines ISIS TE.";

      container config {
        description
          "This container defines ISIS TE configuration.";

        uses oc-isis:isis-te-config;
      }

      container state {
        config false;
        description
          "This container defines ISIS TE state information.";

        uses oc-isis:isis-te-config;
      }
    }
  }

  grouping srv6-config {
    description
      "SRV6 Configuration.";

    leaf enabled {
      description
        "Enable SRV6.";

      type boolean;
    }
  }

  grouping srv6-locator-config {
    description
      "SRV6 Locator Configuration.";

    list locator {
      key "name";

      description
        "List of locators advertised by ISIS.";

      leaf name {
        description
          "Reference to SRV6 locator name.";

        type leafref {
          path "../../../../../../../../../arc-srv6:srv6/arc-srv6:locator/arc-srv6:name";
        }
      }
    }
  }

  grouping srv6-locator-state {
    description
      "SRV6 Locator Configuration.";

    list locator {
      key "name";

      description
        "List of locators advertised by ISIS.";

      leaf name {
        description
          "Reference to SRV6 locator name.";

        type leafref {
          path "../../../../../../../../../arc-srv6:srv6/arc-srv6:locator/arc-srv6:name";
        }
      }

      leaf prefix {
        type inet:ipv6-prefix;
        description
          "SRv6 locator prefix";
      }

      leaf node-length {
        type uint8;
        description
          "SRv6 locator prefix node length in bits";
      }

      leaf algorithm {
        type uint8;
        description
          "SRv6 algorithm ID";
      }

      leaf micro-sid {
        type boolean;
        description
          "SRv6 locator is micro-SID";
      }

      leaf registered {
        type boolean;
        description
          "SRv6 locator is registered with SIDmgr";
      }

      leaf valid {
        type boolean;
        description
          "SRv6 locator notification was received from SIDmgr";
      }
    }
  }

  grouping srv6-locator-top {
    description
      "Top-level SRV6 Locator Configuration.";

    container locators {
      description
        "SRV6 Locator.";

      container config {
        uses srv6-locator-config;
      }

      container state {
        config false;
        uses srv6-locator-state;
      }
    }
  }

  grouping srv6-config-top {
    description
      "Top-level SRV6 Configuration.";

    container srv6 {
      description
        "SRV6 Configuration.";

      container config {
        uses srv6-config;
      }

      container state {
        config false;
        uses srv6-config;
      }

      uses srv6-locator-top;
    }
  }

  grouping poi-originate-config {
    description
      "POI Originate Configuration.";

    leaf enabled {
      description
        "Enable POI origination.";

      type boolean;
    }
  }

  grouping poi-config-top {
    description
      "Top-level Purge Originator Identification (POI) TLV Configuration.";

    container poi-originate {
      description
        "POI originate Configuration.";

      container config {
        uses poi-originate-config;
      }

      container state {
        config false;
        uses poi-originate-config;
      }
    }
  }

  grouping fast-reroute-ti-lfa-config {
    leaf srv6-enabled {
      type boolean;
      description
        "TI-LFA using SRv6";
    }
  }

  grouping fast-reroute-tilfa {
    container ti-lfa {
      description
        "TI-LFA Configuration";
      container config {
        uses fast-reroute-ti-lfa-config;
      }
      container state {
        config false;
        uses fast-reroute-ti-lfa-config;
      }
    }
  }

  grouping fast-reroute-protection-srlg-disjoint-config {
    leaf priority {
      type uint8;
      default 10;
      must "current() != ../../../node-protecting/config/priority" {
        error-message "tiebreaker priority values must be unique";
      }
      description
       "SRLG srlg-disjoint protection tiebreaker priority.
       Lower values are higher precedence.";
    }
  }

  grouping fast-reroute-protection-node-protecting-config {
    leaf priority {
      type uint8;
      default 20;
      must "current() != ../../../srlg-disjoint/config/priority" {
        error-message "tiebreaker priority values must be unique";
      }
      description
       "SRLG node-protecting protection tiebreaker priority.
       Lower values are higher precedence.";
    }
  }

  grouping fast-reroute-protection-tiebreak {
    container tiebreaker {
      description
        "Protection tiebreaker priority configuration.";
      container srlg-disjoint {
        description
          "SRLG protection tiebreaker configuration";
        container config {
          uses fast-reroute-protection-srlg-disjoint-config;
        }
        container state {
          config false;
          uses fast-reroute-protection-srlg-disjoint-config;
        }
      }
      container node-protecting {
        description
          "Node protection tiebreaker configuration";
        container config {
          uses fast-reroute-protection-node-protecting-config;
        }
        container state {
          config false;
          uses fast-reroute-protection-node-protecting-config;
        }
      }
    }
  }

  grouping fast-reroute-top {
    description
      "Top fast-reroute configuration.";
    container fast-reroute {
      description
        "Fast reroute configuration";
      uses fast-reroute-tilfa;
      uses fast-reroute-protection-tiebreak;
    }
  }

  grouping micro-loop-avoidance-config {
    description
      "Micro-loop avoidance configuration";
    leaf srv6-enabled {
      type boolean;
      description
        "micro-loop-avoidance SRv6 configuration";
    }
    leaf rib-update-delay {
      type uint32 {
        range "1..600000";
      }
      default 5000;
      description
        "RIB update delay configuration";
    }
  }

  grouping micro-loop-avoidance-top {
    description
      "Micro-loop avoidance configuration.";
    container micro-loop-avoidance {
      description
        "Micro-loop avoidance Configuration";
      container config {
        uses micro-loop-avoidance-config;
      }
      container state {
        config false;
        uses micro-loop-avoidance-config;
      }
    }
  }

  grouping dynamic-delay-measurement-config {
    leaf twamp-port {
      type uint16;
      default 862;
    }
    leaf probe-interval {
      type uint16 {
        range "1..30";
      }
      default 1;
      units seconds;
    }
    leaf advertisement-interval {
      type uint16 {
        range "10..60";
      }
      default 30;
      units seconds;
    }
    leaf advertisement-threshold-percentage {
      type oc-types:percentage;
      default 10;
    }
    leaf advertisement-minimum-change {
      type uint32;
      default 1000;
      units microseconds;
    }
  }

  grouping dynamic-delay-measurement-top {
    container dynamic-delay-measurement {
      container config {
        uses dynamic-delay-measurement-config;
      }
      container state {
        config false;
        uses dynamic-delay-measurement-config;
      }
    }
  }

  augment "/oc-ni:network-instances/oc-ni:network-instance" +
          "/oc-ni:protocols/oc-ni:protocol/oc-ni:isis/oc-ni:global" {
    uses srv6-config-top;
    uses te-config-top;
    uses micro-loop-avoidance-top;
    uses flexible-algorithms-top;
    uses dynamic-delay-measurement-top;
    uses poi-config-top;
  }

  augment "/oc-ni:network-instances/oc-ni:network-instance" +
          "/oc-ni:protocols/oc-ni:protocol/oc-ni:isis/oc-ni:interfaces" +
          "/oc-ni:interface" {
    uses fast-reroute-top;
    uses flexible-algorithm-interface-top;
    uses sr-policy-interface-top;
  }

  grouping route-state-top {
    description
      "This grouping defines ISIS route.";

    leaf prefix {
     type inet:ip-prefix;
      description
        "ISIS route prefix.";
    }
    leaf best-level-number {
      type oc-isis-types:level-number;
      description
        "Indicate which level contributes the best route.";
    }
  }

  grouping route-levels-top {
    description
      "This grouping defines ISIS route levels.";

    container levels {
      description
        "This container defines ISIS level specific route information.";

      list level {
        key "level-number";

        description
          "List of ISIS level specific route information.";

        leaf level-number {
          type oc-isis-types:level-number;
          description
            "ISIS level-number.";
        }

        container state {
          description
            "This container defines ISIS level specific route state
            information.";

          leaf level-number {
            type oc-isis-types:level-number;
            description
              "ISIS level number (level-1, level-2).";
          }

          leaf in-label {
            type oc-mpls-types:mpls-label;
            description
            "Indicates the In-label of SR LSP.";
          }

          leaf metric {
            type uint32;
            description
              "ISIS route metric.";
          }

          leaf-list flags {
            type identityref {
              base route-flag;
            }
            description
              "ISIS route flags.";
          }

          leaf next-hop-id {
            type uint64;
            description
              "Unique Identfier for the specific set of Next-hop paths.";
          }

          leaf prefix-origin-count {
            type uint32;
            description
              "Number of prefix originators found in Link-state-database.";
          }

          leaf route-tag {
            type uint32;
            description
              "ISIS route tag";
          }
          uses arc-common-types:common-state-attrs;
        }

        container next-hops {
          description
            "This container defines ISIS level specific route next hops
            information.";

          list next-hop {
            key "outgoing-interface next-hop-address";
            description
              "List ISIS level specific route next hop information.";

            leaf outgoing-interface {
              type leafref {
                path "../state/outgoing-interface";
              }
              description
                "Reference to ISIS interface.";
            }

            leaf next-hop-address {
              type leafref {
                path "../state/next-hop-address";
              }
              description
                "Reference to ISIS next hop address.";
            }
            container state {
              description
                "This container defines ISIS level specific route next hops
                state information.";

              leaf outgoing-interface {
                type oc-if:interface-id;
                description
                  "The outgoing interface.";
              }

              leaf next-hop-address {
                type inet:ip-address;
                description
                  "The next hop address.";
              }

              leaf tunnel-id {
                type uint64;
                description
                  "Tunnel identifier referred by this next hop.";
              }

              leaf-list out-labels {
                type oc-mpls-types:mpls-label;
                description
                  "Indicates the out-label list for the SR LSP paths";
              }

              leaf backup {
                type boolean;
                description
                  "This next hop is used as backup.";
              }
            }
          }
        }
      }
    }
  }

  grouping global-spf-logs-top {
    description "Grouping for spf-log events.";

    container spf-log {
      description
        "This container lists the SPF computation events.";
      config false;

      list event {
        key id;
        description
          "List of computation events - implemented as a
          wrapping buffer.";

        leaf id {
          type uint32;
          description
            "Event identifier -  purely internal value.";
        }

        leaf spf-type {
          type enumeration {
            enum full {
              description "Full SPF computation.";
            }
            enum route-only {
              description
                "Route reachability only SPF computation";
            }
          }
          description "Type of SPF computation performed.";
        }

        leaf level {
          type oc-isis-types:level-number;
          description
            "IS-IS level number for SPF computation";
        }

        leaf topology-id {
          type isis-multi-topology-id;
          description
            "IS-IS multi-topology ID for SPF computation";
        }

        leaf algorithm {
          type uint8;
          description
            "IGP Algorithm Type";
        }

        leaf schedule-time {
          type yang:date-and-time;
          description
            "Time when the SPF computation was
            scheduled.";
        }

        leaf delay {
          type uint64;
          description
            "Delay in micro-seconds  applied for this SPF event.";
        }

        leaf start-time {
          type yang:date-and-time;
          description
            "Time when the SPF computation started.";
        }

        leaf end-time {
          type yang:date-and-time;
          description
            "Time when the SPF computation ended.";
        }

        leaf duration {
          type uint64;
          description
            "Time taken in micro-seconds to execute the SPF computations.";
        }

        leaf node-count {
          type uint64;
          description
            "Number of nodes involved in the SPF computations.";
        }

        leaf prefix-count {
          type uint64;
          description
            "Number of prefixes involved in the SPF computations.";
        }

        leaf route-download-count {
          type uint64;
          description
            "Number of routes updated in the SPF computations.";
        }

        list trigger-lsp {
          key "id";
          description
            "This list includes the LSPs that triggered the
            SPF computation.";

          leaf id {
            type uint32;
            description
              "Trigger identifier -  purely internal value.";
          }

          leaf lsp-id {
            type oc-isis-types:lsp-id;
            description
              "LSPID of the LSP triggering SPF computation.";
          }

          leaf sequence {
            type uint32;
            description
              "Sequence number of the LSP triggering SPF
              computation";
          }

          leaf trigger-time {
            type yang:date-and-time;
            description
              "Time when the trigger event was recorded.";
          }
        }
      }
    }
  }

  grouping memory-counter-attributes-top {
    leaf id {
      type uint16;
      description
        "Memory counter ID";
    }
    leaf type {
      type string;
      description
        "Memmory counter type";
    }
    leaf alloc-counter {
      type yang:counter32;
      description
        "Memory allocation counter";
    }
    leaf free-counter {
      type yang:counter32;
      description
        "Memory free counter";
    }
    leaf slab-count {
      type yang:counter32;
      description
        "Current slabs allocated";
    }
  }

  grouping memory-counters-top {
    description
      "Grouipng for memory usage counters";
    container memory-counters {
      config false;
      list memory-counter {
        key "id";

        leaf id {
          type leafref {
            path "../state/id";
          }
          description
            "Counter ID";
        }
        container state {
          uses memory-counter-attributes-top;
        }
      }
    }
  }

  augment "/oc-ni:network-instances/oc-ni:network-instance" +
          "/oc-ni:protocols/oc-ni:protocol/oc-ni:isis/oc-ni:global" {
    uses global-spf-logs-top;
    uses memory-counters-top;
  }

  grouping level-spf-top {
    description "Grouping for per-level spf details.";

    leaf next-spf {
      type uint64;
      description "Time in microseconds left before next SPF computations.";
    }
  }

  grouping level-stats-summary-top {
    description "Grouping for per-level stats summary";

    container level-stats-summary {
      config false;
      description
        "This container contains per-level summary stats";

      leaf lsp-count {
        type yang:zero-based-counter64;
        description "Number of lsps in link-state-database for a given level.";
      }
    }
  }


  augment "/oc-ni:network-instances/oc-ni:network-instance" +
          "/oc-ni:protocols/oc-ni:protocol/oc-ni:isis/oc-ni:levels" +
          "/oc-ni:level/oc-ni:state" {
    uses level-spf-top;
    uses level-stats-summary-top;
  }

  grouping labeled-preference-config {
    description
      "Labeled preference configuration.";

    leaf labeled-preference {
      description
        "Preference value to use for remote SR labels.";
      type uint8 {
        range "1..max";
      }
    }
  }

  grouping level-labeled-route-preference-top {
    container labeled-preference {
      description
        "Configuration and operational state for per-level labeled route
        preference.";

      container config {
        description
          "Configuration of labeled route preference.";

          uses labeled-preference-config;
      }

      container state {
        config false;
        description
          "Operational state of labeled route preference.";

          uses labeled-preference-config;
      }
    }
  }

  augment "/oc-ni:network-instances/oc-ni:network-instance" +
          "/oc-ni:protocols/oc-ni:protocol/oc-ni:isis/oc-ni:levels" +
          "/oc-ni:level" {
    uses level-labeled-route-preference-top;
  }

  grouping global-af-fast-reroute-top {
    container fast-reroutes {
      config false;
      description
        "Routes with fast re-route.";

      list fast-reroute {
        key "prefix";
        description
          "Routes with fast re-route.";

        leaf prefix {
          type leafref {
            path "../state/prefix";
          }
          description
            "Route prefix.";
        }

        container state {
          leaf prefix {
          type inet:ip-prefix;
            description
              "ISIS route prefix.";
          }
        }
        uses global-fast-reroute-top;
      }
    }
  }

  grouping global-af-routes-top {
    container routes {
      config false;
      description
        "This container defines ISIS routes.";

      list route {
        key "prefix";

        description
          "List of the local system's ISIS routes information learned
          and calculated.";

        leaf prefix {
          type leafref {
            path "../state/prefix";
          }
          description
            "Reference to the prefix of the ISIS route.";
        }

        container state {
          description
            "Operational state relating to the ISIS routes information
            learned and calculated.";

          uses route-state-top;
        }
        uses route-levels-top;
      }
    }
  }

  grouping global-af-flexalgo-routes-top {
    container flexible-algorithms {
      config false;
      description
        "This container defines ISIS AF flexible algorithm information.";

      list flexible-algorithm {
        key "id";

        description
          "List of flexible algorithm information for this AF.";

        leaf id {
          type leafref {
            path "../state/id";
          }
          description
            "Reference to the flexible algorithm ID.";
        }

        container state {
          description
            "Operational state of flexible algorithm for this AF.";

          leaf id {
            type uint8;

            description
              "Flexible algorithm ID.";
          }
        }

        uses global-af-routes-top;
        uses global-af-fast-reroute-top;
      }
    }
  }

  grouping redist-route-levels-top {
    description
      "This grouping defines ISIS redistribute route levels.";

    container levels {
      description
        "This container defines ISIS redistribute route level information.";

      list level {
        key "level-number";

        description
          "List of ISIS level specific route information.";

        leaf level-number {
          type oc-isis-types:level-number;
          description
            "ISIS level-number.";
        }

        container state {
          description
            "This container defines ISIS level specific route state
            information.";

          leaf level-number {
            type oc-isis-types:level-number;
            description
              "ISIS level number (level-1, level-2).";
          }

          leaf metric {
            type uint32;
            description
              "ISIS route metric.";
          }

          leaf route-tag {
            type uint32;
            description
              "ISIS route tag";
          }

          leaf srv6-locator-metric {
            type uint32;
            description
              "ISIS SRv6 locator route metric.";
          }

          leaf-list flags {
            type identityref {
              base route-flag;
            }
            description
              "ISIS redistribute route flags.";
          }
        }

        container source {
          container state {
            leaf identifier {
              type identityref {
              base "oc-pol-types:INSTALL_PROTOCOL_TYPE";
            }
            description
              "The protocol identifier for the instance";
            }

            leaf name {
              type string;
               description
                 "A unique name for the protocol instance";
            }

            leaf level-number {
              type oc-isis-types:level-number;
              description
                "Level number.";
            }
          }
          description
            "Source information for redistributed route.";
        }
      }
    }
  }

  grouping redist-route-state-top {
    description
      "This grouping defines ISIS redistribute route.";

    leaf prefix {
     type inet:ip-prefix;
      description
        "ISIS route prefix.";
    }
  }

  grouping global-af-redist-routes-top {
    container redistribute-routes {
      config false;
      description
        "This container defines ISIS redistribute routes.";

      list redistribute-route {
        key "prefix";

        description
          "List of the local system's ISIS redistributed routes
          information.";

        leaf prefix {
          type leafref {
            path "../state/prefix";
          }
          description
            "Reference to the prefix of the ISIS redistribute route.";
        }

        container state {
          description
            "Operational state relating to the ISIS redistributed routes
             information";

          uses redist-route-state-top;
        }
        uses redist-route-levels-top;
      }
    }
  }

  grouping prefix-tracking-state-top {
    description
      "Operational state data for prefix tracking information";

    leaf prefix {
      type inet:ip-prefix;
      description
        "The prefix key";
    }

    leaf masklength-range {
      type string {
        pattern '(([0-9]|[1-9][0-9]|1[0-2][0-8])\.\.([0-9]|[1-9][0-9]' +
                '|1[0-2][0-8]))|exact';
      }
      description
        "The range for the masklength, or 'exact' if
         the prefix has an exact length";
    }

    leaf-list flags {
      type identityref {
        base prefix-tracking-flag;
      }
      description
        "Prefix tracking flags.";
    }

    leaf resolved {
      type boolean;
      description
        "Indicate if the prefix tracking is resolved";
    }

    leaf match-prefix {
      type inet:ip-prefix;
      description
        "The prefix that match the prefix tracking";
    }
  }

  grouping sr-isis-mapping-config {
    description
      "Configuration parameters relating to segment routing mapping
      server within an IGP.";

    leaf mapping {
      type leafref {
          path "/oc-netinst:network-instances/oc-netinst:network-instance" +
               "/oc-netinst:segment-routing/arc-oc-sr-aug:srms" +
               "/arc-oc-sr-aug:mappings/arc-oc-sr-aug:mapping" +
               "/arc-oc-sr-aug:config/arc-oc-sr-aug:local-id";
      }
      description
        "A reference to the Segment Routing mapping server list that is
        to be used by this IGP instance.";
    }

    leaf receive-enabled {
      type boolean;
      default true;
      description
        "When set to true, we allow the node to receive SRMS mappings";
    }

    leaf advertise-enabled {
      type boolean;
      default true;
      description
        "When set to true, we allow the node to advertise SRMS mappings";
    }
  }

  grouping sr-isis-mapping-top {
    description
      "Per-instance configuration and state parameters for Segment Routing
      mapping server in an IGP.";

    container srms {
      description
        "Segment Routing Mapping Server configuration.";

      container config {
        description
          "This container defines the ISIS/IGP configuration.";
          uses sr-isis-mapping-config;
      }
      container state {
        config false;
        description
          "This container defines state information for SRMS.";
        uses sr-isis-mapping-config;
      }
    }
  }

  augment "/oc-ni:network-instances/oc-ni:network-instance" +
          "/oc-ni:protocols/oc-ni:protocol/oc-ni:isis/oc-ni:global" +
          "/oc-ni:segment-routing" {
    uses sr-isis-mapping-top;
  }

  grouping global-af-prefix-trackings-top {
    container prefix-trackings {
      config false;
      description
        "This container defines ISIS prefix tracking.";

      list prefix-tracking {
        key "prefix masklength-range";

        description
          "List of the local system's ISIS prefix tracking information";

        leaf prefix {
          type leafref {
            path "../state/prefix";
          }
          description
            "Reference to the prefix of the ISIS prefix tracking information";
        }

        leaf masklength-range {
          type leafref {
            path "../state/masklength-range";
          }
          description
            "Reference to the masklength-range of the ISIS prefix tracking information";
        }

        container state {
          description
            "Operational state relating to the ISIS prefix trackings
             information";

          uses prefix-tracking-state-top;
        }

        container source {
          container state {
            leaf identifier {
              type identityref {
              base "oc-pol-types:INSTALL_PROTOCOL_TYPE";
            }
            description
              "The protocol identifier for the instance";
            }

            leaf name {
              type string;
               description
                 "A unique name for the protocol instance";
            }
          }
          description
            "Source information for matching prefix.";
        }
      }
    }
  }

  augment "/oc-ni:network-instances/oc-ni:network-instance" +
          "/oc-ni:protocols/oc-ni:protocol/oc-ni:isis/oc-ni:global" +
          "/oc-ni:afi-safi/oc-ni:af" {
    uses global-af-routes-top;
    uses global-af-flexalgo-routes-top;
    uses global-af-redist-routes-top;
    uses global-af-prefix-trackings-top;
    uses arc-igp-types:default-information-top;
    uses global-af-fast-reroute-top;
  }

  grouping lsp-state-top {
    leaf system-id {
      type oc-isis-types:system-id;
      description
        "ISIS node system-id (LAN Identifier)";
    }

    leaf overload-bit {
      type boolean;
      description
        "LSDB overload bit.";
    }

    leaf attached-bit {
      type boolean;
      description
        "LSDB attached bit.";
    }

    leaf is-type {
      type identityref {
        base arc-isis-types:level-bits;
      }
      description
        "IS type.";
    }

    leaf received-remaining-lifetime {
      type uint16;
      description
        "The received remaining lifetime.";
    }

    leaf last-update-ifindex {
      type uint32;
      description
        "The ifindex of the index this LSP is last received from.";
    }

    leaf last-update-time {
      type yang:date-and-time;
      description
        "Last time this LSP is updated.";
    }

    leaf srm-count {
      type uint32;
      description
        "Number of SRM bits set.";
    }

    leaf-list srm-set {
      type uint16;
      description
        "The SRM set.";
    }

    leaf ssn-count {
      type uint32;
      description
        "Number of SSN bits set.";
    }

    leaf-list ssn-set {
      type uint16;
      description
        "The SSN set.";
    }
  }

  augment "/oc-ni:network-instances/oc-ni:network-instance" +
          "/oc-ni:protocols/oc-ni:protocol/oc-ni:isis" +
          "/oc-ni:levels/oc-ni:level/oc-ni:link-state-database" +
          "/oc-ni:lsp/oc-ni:state" {
    uses lsp-state-top;
  }

  grouping lsp-extended-is-reachability-neighbor-state-top {
    leaf two-way-connectivity {
      type boolean;
      description
        "The ISIS node the fulfill the two way connectivity check.";
    }
  }

  augment "/oc-ni:network-instances/oc-ni:network-instance" +
          "/oc-ni:protocols/oc-ni:protocol/oc-ni:isis" +
          "/oc-ni:levels/oc-ni:level/oc-ni:link-state-database" +
          "/oc-ni:lsp/oc-ni:tlvs/oc-ni:tlv/oc-ni:extended-is-reachability" +
          "/oc-ni:neighbors/oc-ni:neighbor/oc-ni:state" {
    uses lsp-extended-is-reachability-neighbor-state-top;
  }

  grouping lsp-is-neighbor-instance-state-top {
    leaf two-way-connectivity {
      type boolean;
      description
        "Indicates if ISIS neighbor instance fulfils the
         two way connectivity check.";
    }
  }

  augment "/oc-ni:network-instances/oc-ni:network-instance" +
          "/oc-ni:protocols/oc-ni:protocol/oc-ni:isis" +
          "/oc-ni:levels/oc-ni:level/oc-ni:link-state-database" +
          "/oc-ni:lsp/oc-ni:tlvs/oc-ni:tlv/oc-ni:mt-isn" +
          "/oc-ni:neighbors/oc-ni:neighbor" +
          "/oc-ni:instances/oc-ni:instance/oc-ni:state" {
    uses lsp-is-neighbor-instance-state-top;
  }

  identity ROUTER_CAPABILITY_IPV6_TE_ROUTER_ID {
    base "oc-isis-lsdb-types:ROUTER_CAPABILITY_SUBTLVS_TYPE";
    description
      "sub-TLV 12. IPv6 TE router ID.";
    reference
      "RFC5316 ISIS Extensions in Support of Inter-Autonomous System (AS)
       MPLS and GMPLS Traffic Engineering.";
  }

  identity ROUTER_CAPABILITY_SRLB {
    base "oc-isis-lsdb-types:ROUTER_CAPABILITY_SUBTLVS_TYPE";
    description
      "sub-TLV 22. SRLB.";
    reference
      "RFC8667 IS-IS Extensions for Segment Routing.";
  }

  identity ROUTER_CAPABILITY_NODE_MSD {
    base "oc-isis-lsdb-types:ROUTER_CAPABILITY_SUBTLVS_TYPE";
    description
      "sub-TLV 23. Node MSD.";
    reference
      "RFC8491 Signaling Maximum SID Depth (MSD) Using IS-IS.";
  }

  identity ROUTER_CAPABILITY_SRV6_CAPABILITY {
    base "oc-isis-lsdb-types:ROUTER_CAPABILITY_SUBTLVS_TYPE";
    description
      "sub-TLV 25. SRv6 Capability.";
    reference
      "draft-bashandy-isis-srv6-extensions.";
  }

  identity ROUTER_CAPABILITY_FLEX_ALGO_DEFINITION {
    base "oc-isis-lsdb-types:ROUTER_CAPABILITY_SUBTLVS_TYPE";
    description
      "sub-TLV 26. IS-IS Flexible Algorithm Definition.";
    reference
      "draft-ietf-lsr-flex-algo.";
  }

  grouping lsp-ipv6-te-router-id-top {
    description
      "IPV6 TE router ID grouping.";
    container ipv6-te-router-id {
      when "../oc-ni:state/oc-ni:subtlv-type = " +
           "'arc-oc-isis-aug:ROUTER_CAPABILITY_IPV6_TE_ROUTER_ID'" {
        description
           "Only include IPv6 TE router ID when the sub-TLV is type 12.";
      }
      description
        "IPv6 TE router ID.";
      container state {
        description
          "State parameter of IPv6 TE router ID.";
        leaf router-id {
          type inet:ipv6-address;
        }
      }
    }
  }

  grouping lsp-node-msd-top {
    description
      "Means to advertise to advertise node/link specific
       values for Maxium Sid Depths(MSD) of various types";
    container node-msds {
      when "../oc-ni:state/oc-ni:subtlv-type = " +
           "'arc-oc-isis-aug:ROUTER_CAPABILITY_NODE_MSD'" {
        description
           "Only include node MSD when the sub-TLV is type 23.";
      }
      description
        "Maximum SRv6 SID Depths.";
      list msd {
        key "type";
        leaf type {
          type leafref {
            path "../state/type";
          }
          description
            "Reference to the MSD type being described.";
        }
        container state {
          description
            "State parameter of MSD.";
          leaf type {
            description
              "The MSD type.";
            type arc-igp-types:msd-type;
          }
          leaf value {
            description
              "The MSD value.";
            type uint8;
          }
        }
      }
    }
  }

augment "/oc-netinst:network-instances/oc-netinst:network-instance"
      + "/oc-netinst:protocols/oc-netinst:protocol"
      + "/oc-netinst:isis"
      + "/oc-netinst:levels/oc-netinst:level"
      + "/oc-netinst:state" {

  list dynamic-hostname {
    key "system-id";
    config false;
    description "System ID to Dynamic Hostname mapping (TLV 137)";

    leaf system-id {
      type oc-isis-types:system-id;
    }
    leaf hostname {
      type string;
    }
  }
}

  /*
   * SRv6 capability flags identity.
   */
  identity SRV6_CAPABILITY_FLAG {
    description "Base identity for SRv6 Capability flag.";
  }

  identity O_BIT {
    base SRV6_CAPABILITY_FLAG;
    description
      "If set, then the router is able to
       use of the O-bit in the Segment Routing Header(SRH)
       as defined in [draft-ietf-6man-segment-routing-header].";
  }

  typedef srv6-capability-flag {
    type union {
      type identityref {
        base SRV6_CAPABILITY_FLAG;
      }
      type uint8;
    }
  }

  grouping lsp-srv6-capability-top {
    description
      "SRV6 capability grouping.";
    container srv6-capability {
      when "../oc-ni:state/oc-ni:subtlv-type = " +
           "'arc-oc-isis-aug:ROUTER_CAPABILITY_SRV6_CAPABILITY'" {
        description
           "Only include node MSD when the sub-TLV is type 25.";
      }
      description
        "SRv6 capability.";
      container state {
        description
          "State parameter of SRv6 Capability.";
        leaf-list flags {
          type srv6-capability-flag;
          description
            "Flags.";
        }
      }
    }
  }

  grouping lsp-node-srlb-top {
    description
      "Node SRLB grouping.";
    container node-srlb {
      when "../oc-ni:state/oc-ni:subtlv-type = " +
           "'arc-oc-isis-aug:ROUTER_CAPABILITY_SRLB'" {
        description
           "Only include node SRLB when the sub-TLV is type 22.";
      }
      description
        "Node SRLB Info.";
      container state {
        description
          "State parameter of SRLB.";
             leaf range {
               type uint32;
               description
                  "Number of SRLB elements. The range value MUST be higher than 0. ";
             }
             leaf label {
               type uint32;
               description
                  "The first value of the SRLB.";
            }
      }
    }
  }

  grouping lsp-flex-algo-definition-top {
    description
      "Flexible algorithm definition grouping.";
    container flex-algo-definitions {
      description
        "Container for flex algo definitions announced in an LSP";

      when "../oc-ni:state/oc-ni:subtlv-type = " +
           "'arc-oc-isis-aug:ROUTER_CAPABILITY_FLEX_ALGO_DEFINITION'" {
        description
           "Only include flex-algo-definitions when the sub-TLV is type 26.";
      }

      list flex-algo-definition {
        description
          "Flex algo definition";
        key "id";
        leaf id {
          type leafref {
            path "../state/id";
          }
        }
        container state {
          uses flexible-algorithm-definition-state-top;
        }
      }
    }
  }

  augment "/oc-ni:network-instances/oc-ni:network-instance" +
          "/oc-ni:protocols/oc-ni:protocol/oc-ni:isis" +
          "/oc-ni:levels/oc-ni:level/oc-ni:link-state-database" +
          "/oc-ni:lsp/oc-ni:tlvs/oc-ni:tlv/oc-ni:router-capabilities" +
          "/oc-ni:capability/oc-ni:subtlvs/oc-ni:subtlvs" {
    uses lsp-ipv6-te-router-id-top;
    uses lsp-node-msd-top;
    uses lsp-srv6-capability-top;
    uses lsp-node-srlb-top;
    uses lsp-flex-algo-definition-top;
  }

  grouping auth-key-top {
    leaf crypto-algorithm {
      type identityref {
        base CRYPTO_TYPE;
      }
      description
        "Authentication key cryptographic algorithm to be used
        for key encryption.";
    }
  }

  grouping instance-authentication-top {
    container hello-authentication {
      description
        "Global IS-IS Hello authentication";

      uses oc-isis:isis-hello-authentication-group;
    }
  }

  augment "/oc-ni:network-instances/oc-ni:network-instance" +
          "/oc-ni:protocols/oc-ni:protocol/oc-ni:isis/oc-ni:global" {
    uses instance-authentication-top;
  }

  augment "/oc-ni:network-instances/oc-ni:network-instance" +
          "/oc-ni:protocols/oc-ni:protocol/oc-ni:isis/oc-ni:global" +
          "/arc-oc-isis-aug:hello-authentication/arc-oc-isis-aug:key" +
          "/arc-oc-isis-aug:config" {
    uses auth-key-top;
  }

  augment "/oc-ni:network-instances/oc-ni:network-instance" +
          "/oc-ni:protocols/oc-ni:protocol/oc-ni:isis/oc-ni:global" +
          "/arc-oc-isis-aug:hello-authentication/arc-oc-isis-aug:key" +
          "/arc-oc-isis-aug:state" {
    uses auth-key-top;
  }

  augment "/oc-ni:network-instances/oc-ni:network-instance" +
          "/oc-ni:protocols/oc-ni:protocol/oc-ni:isis" +
          "/oc-ni:levels/oc-ni:level" +
          "/oc-ni:authentication/oc-ni:key/oc-ni:config" {
    uses auth-key-top;
  }

  augment "/oc-ni:network-instances/oc-ni:network-instance" +
          "/oc-ni:protocols/oc-ni:protocol/oc-ni:isis" +
          "/oc-ni:levels/oc-ni:level" +
          "/oc-ni:authentication/oc-ni:key/oc-ni:state" {
    uses auth-key-top;
  }

  /*
   * Information common for all type of interfaces for both config and oper.
   */
  grouping interface-common-top {
    uses interface-level-admin-tag;
    uses interface-level-srlg;
  }

  /*
   * Information only valid for state but not config for loopback interface.
   */
  grouping interface-no-config-loopback-top {
    leaf network-type {
      type arc-isis-types:network-type;
      description
        "ISIS interface network type.";
    }
  }

  grouping interface-level-srlg {
    leaf-list srlg-membership {
    max-elements 30;
      type leafref {
        path "/oc-ni:network-instances/oc-ni:network-instance" +
             "/arc-te:te/arc-te:srlgs/arc-te:srlg" +
             "/arc-te:config/arc-te:name";
      }
      description
        "list of references to named shared risk link groups that the
        interface belongs to.";
    }
  }

  grouping interface-level-admin-tag {
    leaf-list tag {
      type uint32 {
        range "1..max";
      }
      max-elements 4;
      ordered-by user;
      description
        "ISIS Type-1 32bit TAG.";
      }

    leaf-list tag64 {
      type uint64 {
        range "1..max";
      }
      max-elements 4;
      ordered-by user;
      description
        "ISIS Type-2 64bit TAG.";
    }
  }

  grouping isis-interface-ldp-igp-config {
    description
      "This grouping defines ISIS/LDP Synchronization configuration for
      and IS-IS interface.";

    leaf enabled {
      type boolean;
      default false;
      description
        "When set to true, rely on IGP/LDP synchronization. IGP cost for link
         is maintained at max until LDP sessions are established and label
         bindings complete. When set to false, do not rely on IGP/LDP
         synchronization if also disabled globally. If enabled globally, per
         interface configuration does not apply.";
      reference "RFC5443: LDP IGP Synchronization.";
    }
  }

  grouping interface-mpls {
    container mpls {
      description
        "Configuration and operational state relating to MPLS-related
        features in IS-IS";

      container igp-ldp-sync {
        description
          "Configuration and operational state relating to synchronisation
          between the LDP and IS-IS";
        container config {
          description
            "This container defines ISIS/IGP configuration.";

          uses isis-interface-ldp-igp-config;
        }

        container state {
          config false;
          description
            "This container defines state information for ISIS/LDP Sync.";

          uses isis-interface-ldp-igp-config;
        }
      }
    }
  }


  grouping isis-interface-csnp-config {
    description
      "This grouping defines CSNP configuration IS-IS interface.";

    leaf enabled {
      type boolean;
      default true;
      description
        "When set to false, CSNPs will not be sent out via this interface";
    }
  }

  grouping interface-csnp {
    container csnp {
      description
        "Configuration and operational state relating to interface CSNP
         in IS-IS";


      container config {
        description
          "This container defines ISIS interface CSNP configuration.";

        uses isis-interface-csnp-config;
      }

      container state {
        config false;
        description
          "This container defines state information for interface CSNP.";

        uses isis-interface-csnp-config;
      }
    }
  }

  grouping interface-state-top {
    leaf circuit-id {
      type arc-isis-types:node-name;
      description
        "ISIS interface circuit ID.";
    }

    leaf protocol-up {
      type boolean;
      description
        "ISIS interface protocol up.";
    }

    leaf snpa {
      type oc-isis-types:snpa;
      description
        "ISIS interface SNPA.";
    }

    leaf mtu {
      type uint32;
      description
        "ISIS interface MTU.";
    }

    leaf ifindex {
      type uint32;
      description
        "The ifindex of the interface.";
    }

    leaf update-index {
      type uint16;
      description
        "ISIS interface update index.";
    }

    leaf next-lsp-transmission {
      type uint64;
      units milliseconds;
      description
        "Next LSP transmission due.";
    }

    leaf next-lsp-retransmission {
      type uint64;
      units milliseconds;
      description
        "Next LSP retransmission due.";
    }

    leaf speed {
      type uint32;
      units "Gbps";
      description
        "Speed of the interface in Gbps";
    }
  }

  grouping global-upa-config {
    description
      "IS-IS global AF UPA parameters";
    
    leaf adv-lifetime {
      type uint16 {
        range "30..max";
      }
      units seconds;
      default 180;
      description
        "Number of seconds a UPA should be advertised after the prefix is " +
        "determined unreachable";
    }

    leaf adv-metric {
      type uint32 {
        range "4261412865..4294967294";
      }
      default 4261412865;
      description
        "Metric value used for the UPA prefix";
    }

    leaf adv-maximum {
      type uint16 {
        range "1..max";
      }
      default 32;
      description
        "Max number of UPAs allowed to be generated";
    }

    leaf rx-process {
      type boolean;
      default false;
      description
        "Should received UPAs be processed and sent to global RIB";
    }
  }

  grouping global-af-prefix-unreachable-top {
    container prefix-unreachable {
      description
        "Configuration and operational state for unreachable prefix " +
        "announcement (UPA) advertisement";
      reference "draft-ietf-lsr-igp-ureach-prefix-announce-02";

      container config {
        description
          "Configuration of UPA advertisement parameters";
        uses global-upa-config;
      }

      container state {
        config false;
        description
          "Operational state of UPA advertisement parameters";
        uses global-upa-config;
      }
    }
  }

  grouping summary-pfx-upa-config {
    description
      "IS-IS summary prefix unreachable prefix announcement (UPA) " +
      "advertisement config";
    reference "draft-ietf-lsr-igp-ureach-prefix-announce-02";

    leaf adv-unreachable {
      type boolean;
      default false;
      description
        "Should UPAs be generated for the components of the summary";
    }

    leaf unreachable-component-tag {
      type uint32 {
        range "1..max";
      }
      description
        "Limit UPA generation to components with specified tag value";
    }
  }

  grouping isis-summary-pfx-cfg {
    description
      "ISIS summary prefix configuration";

    leaf prefix {
      type inet:ip-prefix;
      description
        "IP prefix to summarize";
    }

    leaf level {
      type oc-isis-types:level-type;
      default "LEVEL_1_2";
      description
        "ISIS levels (level-1, level-2, level-1-2).";
    }

    leaf metric {
      type uint32;
      description
        "Metric for the summary prefix";
    }

    leaf tag {
      type uint32 {
        range "1..max";
      }
      description
        "Tag for the summary prefix";
    }

    leaf apply-policy {
      type leafref {
        path "/oc-rpol:routing-policy/oc-rpol:policy-definitions/" +
          "oc-rpol:policy-definition/oc-rpol:name";
      }
      description
        "Policy name to be applied for summary prefix on
        candidate prefixes";
    }

    leaf algorithm {
      when "../../../../oc-ni:config/oc-ni:afi-name = 'oc-isis-types:IPV6'" {
        description
          "Flex-algo ID";
      }
      type uint8 {
        range "0 | 128..255";
      }
    }
  }

  grouping isis-summary-pfx-counters {
    container levels {
      list level {
        key "level-number";

        description
          "List of ISIS level specific route information.";

        leaf level-number {
          type oc-isis-types:level-number;
          description
            "ISIS level-number.";
        }

        leaf prefix-contributor-count {
          type uint32;
        }

        leaf locator-contributor-count {
          type uint32;
        }

        leaf prefix-min-metric {
          type uint32;
        }

        leaf locator-min-metric {
          type uint32;
        }
      }
    }
  }

  grouping isis-summary-pfx {
    container summary-prefixes {
      list summary-prefix {
        key "prefix";
        description
          "List of summary prefixes under an ISIS instance af";

        leaf prefix {
          type leafref {
            path "../config/prefix";
          }
          description
            "Network prefix to summarize";
        }

        container config {
          description
            "ISIS instance prefix config";
          uses isis-summary-pfx-cfg;
          uses summary-pfx-upa-config;
        }

        container state {
          config false;
          description
            "ISIS instance prefix state";
          uses isis-summary-pfx-cfg;
          uses summary-pfx-upa-config;
          uses isis-summary-pfx-counters;
        }
      }
    }
  }

  augment "/oc-ni:network-instances/oc-ni:network-instance" +
          "/oc-ni:protocols/oc-ni:protocol/oc-ni:isis/oc-ni:global" +
          "/oc-ni:afi-safi/oc-ni:af" {
    uses isis-summary-pfx;
    uses global-af-prefix-unreachable-top;
  }

  augment "/oc-ni:network-instances/oc-ni:network-instance" +
          "/oc-ni:protocols/oc-ni:protocol/oc-ni:isis/oc-ni:interfaces" +
          "/oc-ni:interface" {
    uses interface-mpls;
    uses interface-csnp;
  }

  augment "/oc-ni:network-instances/oc-ni:network-instance" +
          "/oc-ni:protocols/oc-ni:protocol/oc-ni:isis/oc-ni:interfaces" +
          "/oc-ni:interface/oc-ni:config" {
    uses interface-no-config-loopback-top {
      when "not(starts-with(../oc-ni:interface-id, 'loopback'))";
    }
    uses interface-common-top;
  }

  augment "/oc-ni:network-instances/oc-ni:network-instance" +
          "/oc-ni:protocols/oc-ni:protocol/oc-ni:isis/oc-ni:interfaces" +
          "/oc-ni:interface/oc-ni:state" {
    uses interface-no-config-loopback-top;
    uses interface-common-top;
    uses interface-state-top;
  }

  augment "/oc-ni:network-instances/oc-ni:network-instance" +
          "/oc-ni:protocols/oc-ni:protocol/oc-ni:isis/oc-ni:interfaces" +
          "/oc-ni:interface/oc-ni:timers/oc-ni:config" {
    uses oc-isis:isis-hello-timers-config;
  }

  augment "/oc-ni:network-instances/oc-ni:network-instance" +
          "/oc-ni:protocols/oc-ni:protocol/oc-ni:isis/oc-ni:interfaces" +
          "/oc-ni:interface/oc-ni:timers/oc-ni:state" {
    uses oc-isis:isis-hello-timers-config;
  }

  /*
   * TE delay metric type identity.
   */

  identity DELAY_METRIC_TYPE {
    description
      "Base identity for link delay metric";
  }

  identity DYNAMIC {
    base DELAY_METRIC_TYPE;
    description
      "Delay metric measurement is dynamic.";
  }

  typedef delay-metric-type {
    type union {
      type identityref {
        base DELAY_METRIC_TYPE;
      }
      type oc-isis-types:wide-metric;
    }
    description
      "Type of delay metric used.";
  }

  grouping interface-level-asla-metric-config-top {
    leaf te-metric {
      type oc-isis-types:wide-metric;
      description "ISIS TE metric value";
    }

    leaf delay-metric {
      type delay-metric-type;
      description "ISIS Delay metric type/value in microseconds.";
    }
  }

  grouping interface-level-top {
    container sr-policy {
      container config {
        uses interface-level-asla-metric-config-top;
      }
      container state {
        config false;
        uses interface-level-asla-metric-config-top;
      }
    }
  }

  grouping interface-level-cfg-top {
    leaf metric {
      type oc-isis-types:wide-metric;
      description "ISIS metric value for this interface level.";
    }
    container flexible-algorithm {
      uses interface-level-asla-metric-config-top;
    }
  }

  grouping interface-circuit-counters {
    description
      "Operational state parameters relating to counters specific to one
      interface or circuit.";

    leaf subnet-mismatches {
      type yang:counter32;
      description
        "Number of IIH packets containing an address that does not
         match the subnet of the local interface.";
    }

    leaf duplicate-addresses {
      type yang:counter32;
      description
        "Number of IIH packets containing an address that is the same
         as the address of the local interface.";
    }

    leaf martian-addresses {
      type yang:counter32;
      description
        "Number of IIH packets containing an address that is classified
         as a martian address.";
    }

    leaf missing-addresses {
      type yang:counter32;
      description
        "Number of IIH packets that do not contain any neighbor address
         of the address family type enabled on the local interface.";
    }
  }

  augment "/oc-ni:network-instances/oc-ni:network-instance" +
          "/oc-ni:protocols/oc-ni:protocol/oc-ni:isis/oc-ni:interfaces" +
          "/oc-ni:interface/oc-ni:circuit-counters/oc-ni:state" {
    uses interface-circuit-counters;
  }

  augment "/oc-ni:network-instances/oc-ni:network-instance" +
          "/oc-ni:protocols/oc-ni:protocol/oc-ni:isis/oc-ni:interfaces" +
          "/oc-ni:interface/oc-ni:levels/oc-ni:level" +
          "/circuit-counters/state" {
    uses interface-circuit-counters;
  }

  grouping interface-level-state-top {
    leaf lan-id {
      type arc-isis-types:node-name;
      description
        "ISIS LAN ID for this interface level.";
    }
  }

  grouping interface-level-lsp-counters-state-top {
    leaf no-memory {
      type uint32;
      description
        "The number of the LSP PDU received on the interface " +
        "that cannot be stored.";
    }
  }

  augment "/oc-ni:network-instances/oc-ni:network-instance" +
          "/oc-ni:protocols/oc-ni:protocol/oc-ni:isis/oc-ni:interfaces" +
          "/oc-ni:interface/oc-ni:levels/oc-ni:level" {
    container circuit-counters {
      description
        "This container defines state information for ISIS circuit counters.";

      uses oc-isis:circuit-counters-structural;
    }
  }

  augment "/oc-ni:network-instances/oc-ni:network-instance" +
          "/oc-ni:protocols/oc-ni:protocol/oc-ni:isis/oc-ni:interfaces" +
          "/oc-ni:interface/oc-ni:levels/oc-ni:level/oc-ni:packet-counters" +
          "/oc-ni:lsp/oc-ni:state" {
    uses interface-level-lsp-counters-state-top;
  }

  augment "/oc-ni:network-instances/oc-ni:network-instance" +
          "/oc-ni:protocols/oc-ni:protocol/oc-ni:isis/oc-ni:interfaces" +
          "/oc-ni:interface/oc-ni:levels/oc-ni:level" {
    uses interface-level-top;
  }

  augment "/oc-ni:network-instances/oc-ni:network-instance" +
          "/oc-ni:protocols/oc-ni:protocol/oc-ni:isis/oc-ni:interfaces" +
          "/oc-ni:interface/oc-ni:levels/oc-ni:level/oc-ni:config" {
    uses interface-level-cfg-top;
  }

  augment "/oc-ni:network-instances/oc-ni:network-instance" +
          "/oc-ni:protocols/oc-ni:protocol/oc-ni:isis/oc-ni:interfaces" +
          "/oc-ni:interface/oc-ni:levels/oc-ni:level/oc-ni:state" {
    uses interface-level-cfg-top;
    uses interface-level-state-top;
  }

  augment "/oc-ni:network-instances/oc-ni:network-instance" +
          "/oc-ni:protocols/oc-ni:protocol/oc-ni:isis/oc-ni:interfaces" +
          "/oc-ni:interface/oc-ni:authentication/oc-ni:key/oc-ni:config" {
    uses auth-key-top;
  }

  augment "/oc-ni:network-instances/oc-ni:network-instance" +
          "/oc-ni:protocols/oc-ni:protocol/oc-ni:isis/oc-ni:interfaces" +
          "/oc-ni:interface/oc-ni:authentication/oc-ni:key/oc-ni:state" {
    uses auth-key-top;
  }

  augment "/oc-ni:network-instances/oc-ni:network-instance" +
          "/oc-ni:protocols/oc-ni:protocol/oc-ni:isis/oc-ni:interfaces" +
          "/oc-ni:interface/oc-ni:levels/oc-ni:level" +
          "/oc-ni:hello-authentication/oc-ni:key/oc-ni:config" {
    uses auth-key-top;
  }

  augment "/oc-ni:network-instances/oc-ni:network-instance" +
          "/oc-ni:protocols/oc-ni:protocol/oc-ni:isis/oc-ni:interfaces" +
          "/oc-ni:interface/oc-ni:levels/oc-ni:level" +
          "/oc-ni:hello-authentication/oc-ni:key/oc-ni:state" {
    uses auth-key-top;
  }

  grouping adjacency-state-top {
    leaf neighbor-lan-id {
      type arc-isis-types:node-name;
      description
        "ISIS neighbor LAN ID.";
    }
    leaf usable {
      type boolean;
       description
        "ISIS neighbor usable";
    }
    leaf restarting-neighbor-id {
      type arc-isis-types:system-name;
      description
        "ISIS Restarting Neighbor System ID.
         When an ISIS router that supports graceful restart receives
         the restart TLV in the IIH of a neighbor with the RR flag set
         and the receiving router had an adjacency to this restarting
         neighbor at the same level in UP state before, then the
         receiving router sends IIH to that neighbor containing the
         restart TLV with RA set and places the system-ID of that
         neighbor in the 'Restarting Neighbor ID' field";

    }
    leaf restart-ack {
      type boolean;
      description
        "If TRUE, then we received a restart TLV with the RA
         flag set";
    }
    leaf restart-request {
      type boolean;
      description
        "If TRUE, then we received a restart TLV with the RR
         flag set";
    }
    leaf restart-remaining-time {
      type uint16;
      description
        "The 'remaining time' field value of the restart TLV.";
    }
    leaf adjacency-up-time {
      type string;
      description
        "The time since the adjacency has been established.";
    }

    leaf-list received-multi-topology-ids {
      type isis-multi-topology-id;
      description
        "List of Topology IDs advertised by neighbor.";
    }

    leaf-list active-multi-topology-ids {
      type isis-multi-topology-id;
      description
        "List of Topology IDs active on this adjacency i.e. common
         to both local system and the neighbor.";
    }
    leaf num-state-changes {
      type yang:counter32;
      description "Number of times the adjacency state changed";
    }

    leaf last-state-change-timestamp {
      type yang:date-and-time;
      description "Timestamp of the last state change";
    }

    leaf last-down-reason {
      type enumeration {
        enum NONE {
          value 0;
          description "No specific reason for state change";
        }
        enum AREA_MISMATCH {
          value 1;
          description "Area address mismatch with neighbor";
        }
        enum WRONG_SYS_TYPE {
          value 2;
          description "System type does not match with neighbor";
        }
        enum SYS_ID_CHANGE {
          value 3;
          description "Neighbor system ID changed";
        }
        enum HOLD_TIME_EXPIRED {
          value 4;
          description "Hold timer expired before receiving hello";
        }
        enum NBR_RESTART {
          value 5;
          description "Neighbor is restarting";
        }
        enum BFD_DOWN {
          value 6;
          description "BFD session went down";
        }
        enum NOT_USABLE {
          value 7;
          description "Interface is not usable for IS-IS";
        }
        enum ITF_DOWN {
          value 8;
          description "Interface went down";
        }
        enum RESTART_RR_STATE_NOT_UP {
          value 9;
          description "Received restart TLV with RR set but adjacency state is not UP";
        }
        enum P2P_NBR_NO_GR {
          value 10;
          description "P2P neighbor does not support graceful restart";
        }
        enum CLEAR_INITIATED {
          value 11;
          description "Clear command was initiated by user";
        }
      }
      description "Reason for the last adjacency down (i.e., transition to the DOWN state).";
    }
  }

  augment "/oc-ni:network-instances/oc-ni:network-instance" +
          "/oc-ni:protocols/oc-ni:protocol/oc-ni:isis" +
          "/oc-ni:interfaces/oc-ni:interface" +
          "/oc-ni:levels/oc-ni:level/oc-ni:adjacencies" +
          "/oc-ni:adjacency/oc-ni:state" {
    uses adjacency-state-top;
  }

  grouping isis-bfd-config {
    leaf profile {
      type leafref {
        path "/oc-bfd:bfd/oc-bfd:interfaces/oc-bfd:interface/oc-bfd:config" +
             "/oc-bfd:id";
      }
      description
        "A reference to the BFD profile.";
    }
  }

  grouping isis-bfd-top {
    container config {
      description
      "This container defines BFD configuration parameters.";
      uses isis-bfd-config;
    }
    container state {
      config false;
        description
          "This container defines BFD state information.";
      uses isis-bfd-config;
    }
  }

  augment "/oc-ni:network-instances/oc-ni:network-instance" +
          "/oc-ni:protocols/oc-ni:protocol/oc-ni:isis" +
          "/oc-ni:interfaces/oc-ni:interface" +
          "/oc-ni:bfd" {
    uses isis-bfd-top;
  }

  grouping adjacency-bfd-topo-state {
    leaf mt-id {
      type isis-multi-topology-id;
      description
        "Multitopology Identifier.";
    }
    leaf ipv4-bfd-required {
      type boolean;
      description
        "ISIS neighbor topology IPV4 BFD required";
    }
    leaf ipv6-bfd-required {
      type boolean;
      description
        "ISIS neighbor topology IPV6 BFD required";
    }
    leaf bfd-required {
      type boolean;
      description
        "ISIS neighbor topology BFD required";
    }
    leaf ipv4-bfd-up {
      type boolean;
      description
        "ISIS neighbor topology IPV4 BFD up";
    }
    leaf ipv6-bfd-up {
      type boolean;
      description
        "ISIS neighbor topology IPV6 BFD up";
    }
    leaf ipv4-up {
      type boolean;
      description
        "ISIS neighbor topology IPV4 up";
    }
    leaf ipv6-up {
      type boolean;
      description
        "ISIS neighbor topology IPV6 up";
    }
    leaf usable {
      type boolean;
      description
        "ISIS neighbor topology usable";
    }
  }

  grouping adjacency-bfd-top {
    container bfd {
      container topologies {
        list topology {
          key "mt-id";

          leaf mt-id {
            type leafref {
              path "../state/mt-id";
            }
            description
              "A reference to a MT ID";
          }
          container state {
            uses adjacency-bfd-topo-state;
          }
        }
      }
      container state {
        leaf bfd-required {
          type boolean;
          description
            "ISIS neighbor BFD required";
        }
      }
    }
  }

  grouping adjacency-dynamic-delay-measurement-top {
    container dynamic-delay-measurement {
      container state {
        leaf enabled {
          type boolean;
          description
            "True if dynamic delay measurement is active for this adjacency.";
        }
        leaf num-advertisements-sent {
          type yang:gauge32;
          description
            "Number of advertisements sent for this adjancecy as a result of delay value change";
        }
        leaf last-sampled-avg-delay-value {
          type uint32;
          description
            "Last advertised average delay value for this adjacency";
        }
        leaf last-advertised-min-delay-value {
          type uint32;
          description
            "Last advertised min delay value for this adjacency";
        }
        leaf last-advertised-max-delay-value {
          type uint32;
          description
            "Last advertised max delay value for this adjacency";
        }
        leaf last-advertised-timestamp {
          type yang:date-and-time;
          description
            "Timestamp when the delay value was advertised for this adjacency";
        }
        leaf last-advertisement-reason {
          type string;
          description
            "Reason for advertising the last delay value.";
        }
      }
    }
  }

  augment "/oc-ni:network-instances/oc-ni:network-instance" +
          "/oc-ni:protocols/oc-ni:protocol/oc-ni:isis" +
          "/oc-ni:interfaces/oc-ni:interface" +
          "/oc-ni:levels/oc-ni:level/oc-ni:adjacencies" +
          "/oc-ni:adjacency" {
    uses adjacency-bfd-top;
    uses adjacency-dynamic-delay-measurement-top;
  }

  identity SID_BINDING {
    base "oc-isis-lsdb-types:ISIS_TLV_TYPE";
    description
      "ISIS TLV 149. An SID Label binding is a form of a range, prefix
       and a Prefix SID subtlv";
    reference
      "SID/Label Binding TLV rfc8667.";
  }

  grouping binding-tlv {
    list sid-prefixs {
      key "sid-prefix";
      description
        "SID IP Prefix.";

      leaf sid-prefix {
        type leafref {
          path "../state/sid-prefix";
        }
      }

      container state {
        leaf sid-prefix {
          type inet:ip-prefix;
          description
            "SID IP Prefix.";

        }
        leaf sid-range {
          type uint16;
          description
            "SID Range.";
        }
        uses isis-lsdb-prefix-sid-state;
      }
    }
  }

  grouping binding-tlv-top {
    description
      "This grouping describes the ISIS SID Binding TLV.";

    container sid-binding {
      config false;
      description
        "This container defines a set of ISIS SID Bindings.";

      when "../oc-ni:state/oc-ni:type = 'arc-oc-isis-aug:SID_BINDING'" {
        description
          "Only include SID Binding TLV attributes when the TLV type is 149.";
      }

      uses binding-tlv;
    }
  }

  augment "/oc-ni:network-instances/oc-ni:network-instance" +
          "/oc-ni:protocols/oc-ni:protocol/oc-ni:isis" +
          "/oc-ni:levels/oc-ni:level/oc-ni:link-state-database" +
          "/oc-ni:lsp/oc-ni:tlvs/oc-ni:tlv" {
    uses binding-tlv-top;
  }

  identity SRV6_LOCATOR {
    base "oc-isis-lsdb-types:ISIS_TLV_TYPE";
    description
      "ISIS TLV 27. An SRV6 locator is a form of summary address for the set
      of topology/algorithm specific SIDs instantiated at the node.";
    reference
      "draft-ietf-lsr-isis-srv6-extensions";
  }

  identity SRV6_LOCATOR_SUBTLV_TYPE {
    base "oc-isis-lsdb-types:ISIS_SUBTLV_TYPE";
    description
      "Base identity for an ISIS SRV6 LOCATOR SUB-TLV type.";
  }

  identity SRV6_LOCATOR_END_SID {
    base "SRV6_LOCATOR_SUBTLV_TYPE";
    description
      "Sub-TLV 5. SRv6 End SID.";
    reference
      "draft-ietf-lsr-isis-srv6-extensions";
  }

  identity ISIS_SUBSUBTLV_TYPE {
    description
      "Base identity for an ISIS SUB-SUB-TLV type.";
  }

  identity SRV6_SID_SUBSUBTLV_TYPE {
    base "ISIS_SUBSUBTLV_TYPE";
    description
      "Base identity for an SRV6 END SID SUB-SUB-TLV type.";
  }

  identity SRV6_SID_STRUCTURE {
    base "SRV6_SID_SUBSUBTLV_TYPE";
    description
      "SID sub-sub-TLV 1. SRv6 SID Structure.";
    reference
      "draft-ietf-lsr-isis-srv6-extensions";
  }

  identity EXTENDED_ADMIN_GROUP_TYPE {
    base "ISIS_SUBSUBTLV_TYPE";
    description
      "Extended Admin-group";
    reference
      "Defined in RFC-7308 and used in RFC-8919";
  }

  identity ADMIN_GROUP_TYPE {
    base "ISIS_SUBSUBTLV_TYPE";
    description
      "Extended Admin-group";
    reference
      "Defined in RFC-5305";
  }

  identity TE_DEFAULT_METRIC_TYPE {
    base "ISIS_SUBSUBTLV_TYPE";
    description
      "Default TE Metric";
    reference
      "Defined in RFC-5305 and used in RFC-8919";
  }

  identity MIN_MAX_DELAY_METRIC_TYPE {
    base "ISIS_SUBSUBTLV_TYPE";
    description
      "Min/Max Unidirectional Link Delay Sub-TLV";
    reference
      "Defined in RFC-8570 and used in RFC-8919";
  }

  grouping isis-lsdb-subtlv-type-state {
    description
      "Per-subTLV type operational state parameters for ISIS.";

    leaf type {
      type identityref {
        base oc-isis-lsdb-types:ISIS_SUBTLV_TYPE;
      }
      description
        "The type of subTLV being described. The type of subTLV is
        expressed as a canonical name.";
    }
  }

  grouping isis-lsdb-subsubtlv-type-state {
    description
      "Per-subsubTLV type operational state parameters for ISIS.";

    leaf type {
      type identityref {
        base ISIS_SUBSUBTLV_TYPE;
      }
      description
        "The type of subsubTLV being described. The type of subsubTLV is
        expressed as a canonical name.";
    }
  }

  grouping undefined-subsubtlv-state {
    description
      "Generic grouping defining an unknown sub-sub-TLV.";

    uses oc-isis:isis-lsdb-generic-tlv;
  }

  grouping isis-lsdb-undefined-subsubtlv {
    description
      "Grouping for unknown Sub-sub-TLVs in the IS-IS LSDB.";

    container undefined-subsubtlvs {
      description
        "This container describes undefined ISIS Sub-sub-TLVs.";

      list undefined-subsubtlv {
        key "type";

        description
          "Sub-sub-TLVs that are not defined in the model or not recognised by
          system.";

        leaf type {
          type leafref {
            path "../state/type";
          }
          description
            "A reference to a subsubTLV";
        }

        container state {
          description
            "State parameters of the undefined Sub-sub-TLV.";

          uses undefined-subsubtlv-state;
        }
      }
    }
  }

  identity APP_SPECIFIC_SRLG {
    base "oc-isis-lsdb-types:ISIS_TLV_TYPE";
    description
      "ISIS TLV 238. The Application-Specific SRLG TLV carries a list of
      Shared Risk Link Groups for a link, identified by Link Identifier
      sub-TLVs";
    reference
      "RFC9479: IS-IS Application-Specific Link Attributes";
  }

  identity APP_SPECIFIC_SRLG_SUBTLV_TYPE {
    base "oc-isis-lsdb-types:ISIS_SUBTLV_TYPE";
    description
      "Base identity for an ISIS Application-Specific SRLG SUB-TLV type.";
  }

  identity LINK_LOCAL_REMOTE_IDS {
    base "APP_SPECIFIC_SRLG_SUBTLV_TYPE";
    description
      "Sub-TLV 4. Link Local/Remote Identifiers.";
    reference
      "RFC9479: Section 4.3";
  }

  identity IPV4_INTERFACE_ADDRESS {
    base "APP_SPECIFIC_SRLG_SUBTLV_TYPE";
    description
      "Sub-TLV 6. IPv4 interface address.";
    reference
      "RFC9479: Section 4.3";
  }

  identity IPV4_NEIGHBOR_ADDRESS {
    base "APP_SPECIFIC_SRLG_SUBTLV_TYPE";
    description
      "Sub-TLV 8. IPv4 neighbor address.";
    reference
      "RFC9479: Section 4.3";
  }

  identity IPV6_INTERFACE_ADDRESS {
    base "APP_SPECIFIC_SRLG_SUBTLV_TYPE";
    description
      "Sub-TLV 12. IPv6 interface address.";
    reference
      "RFC9479: Section 4.3";
  }

  identity IPV6_NEIGHBOR_ADDRESS {
    base "APP_SPECIFIC_SRLG_SUBTLV_TYPE";
    description
      "Sub-TLV 13. IPv6 neighbor address.";
    reference
      "RFC9479: Section 4.3";
  }

  grouping as-srlg-link-ids-subtlv {
    container link-local-remote-ids {
      when "../state/type = 'arc-oc-isis-aug:LINK_LOCAL_REMOTE_IDS'";

      description
        "This container defines sub-TLV 4 of ISIS TLVs 238.";
      reference
        "RFC9479: Section 4.3, Table 2";

      container state {
        description
          "State parameters of sub-TLV 4.";

        leaf link-local-id {
          type uint32;
          description
            "Link Local Identifier";
        }

        leaf link-remote-id {
          type uint32;
          description
            "Link Remote Identifier";
        }
      }
    }
  }

  grouping as-srlg-ipv4-interface-subtlv {
    container ipv4-interface-address {
      when "../state/type = 'arc-oc-isis-aug:IPV4_INTERFACE_ADDRESS'";

      description
        "This container defines sub-TLV 6 of ISIS TLVs 238.";
      reference
        "RFC9479: Section 4.3, Table 2";

      container state {
        description
          "State parameters of sub-TLV 6.";

        leaf ipv4-interface-address {
          type inet:ipv4-address-no-zone;
          description
            "Interface IPv4 Address.";
        }
      }
    }
  }

  grouping as-srlg-ipv4-neighbor-subtlv {
    container ipv4-neighbor-address {
      when "../state/type = 'arc-oc-isis-aug:IPV4_NEIGHBOR_ADDRESS'";

      description
        "This container defines sub-TLV 8 of ISIS TLVs 238.";
      reference
        "RFC9479: Section 4.3, Table 2";

      container state {
        description
          "State parameters of sub-TLV 8.";

        leaf ipv4-neighbor-address {
          type inet:ipv4-address-no-zone;
          description
            "Neighbor IPv4 Address.";
        }
      }
    }
  }

  grouping as-srlg-ipv6-interface-subtlv {
    container ipv6-interface-address {
      when "../state/type = 'arc-oc-isis-aug:IPV6_INTERFACE_ADDRESS'";

      description
        "This container defines sub-TLV 12 of ISIS TLVs 238.";
      reference
        "RFC9479: Section 4.3, Table 2";

      container state {
        description
          "State parameters of sub-TLV 12.";

        leaf ipv6-interface-address {
          type inet:ipv6-address;
          description
            "Interface IPv6 Address.";
        }
      }
    }
  }

  grouping as-srlg-ipv6-neighbor-subtlv {
    container ipv6-neighbor-address {
      when "../state/type = 'arc-oc-isis-aug:IPV6_NEIGHBOR_ADDRESS'";

      description
        "This container defines sub-TLV 13 of ISIS TLVs 238.";
      reference
        "RFC9479: Section 4.3, Table 2";

      container state {
        description
          "State parameters of sub-TLV 13.";

        leaf ipv6-neighbor-address {
          type inet:ipv6-address;
          description
            "Neighbor IPv6 Address.";
        }
      }
    }
  }

  grouping as-srlg-subtlv-top {
    container subtlvs {
      description
        "This container describes Application-Specific SRLG sub-TLVs.";

      list subtlv {
        key "type";

        description
          "List of subTLV types in the AS-SRLG TLV.";

        leaf type {
          type leafref {
            path "../state/type";
          }
          description
            "A reference for the subTLV type being described within the LSDB";
        }

        container state {
          uses isis-lsdb-subtlv-type-state;
        }

        uses as-srlg-link-ids-subtlv;
        uses as-srlg-ipv4-interface-subtlv;
        uses as-srlg-ipv4-neighbor-subtlv;
        uses as-srlg-ipv6-interface-subtlv;
        uses as-srlg-ipv6-neighbor-subtlv;
      }
    }
  }

  grouping as-srlg-tlv {
    container state {
      description
        "State parameters of TLV 238.";

      leaf system-id {
        type arc-isis-types:node-name;
        description
          "Neighbor system ID + pseudonode number";
      }

      leaf instance-id {
        type uint64;
        description
          "An arbitrary unsigned unique 64-bit integer used to
          disambiguate the instance of TLV 238. The instance
          identifier is synthesised by the system and may be
          renumberedif the entire LSP contents are replaced in
          subsequent advertisements.";
      }

      leaf legacy-flag {
        type boolean;
        description
          "Legacy Flag";
        reference
          "RFC 9479: Section 4.2";
      }

      leaf standard-applications {
      type isis-sabm;
        description
          "Standard applications bitmask";
        reference
          "RFC 9479: Section 4.1";
      }

      leaf user-defined-applications {
        type uint64;
        description
          "User defined applications bitmask";
        reference
          "RFC 9479: Section 4.1";
      }

      leaf-list srlg-value {
        type uint32;
        description
          "SRLG values.";
      }
    }

    uses as-srlg-subtlv-top;
  }

  grouping as-srlg-tlv-top {
    description
      "This grouping describes the ISIS Application-Specific Shared Risk
      Link Group (SRLG) TLV.";

    container as-srlgs {
      config false;
      description
        "This container defines a set of ISIS AS-SRLG.";

      when "../oc-ni:state/oc-ni:type = 'arc-oc-isis-aug:APP_SPECIFIC_SRLG'" {
        description
          "Only include AS-SRLG TLV attributes when the TLV type is 238.";
      }

      list as-srlg {
        key "system-id instance-id";
        description
          "Instance of the Application-Specific SRLG TLV";

        leaf system-id {
          type leafref {
            path "../state/system-id";
          }
          description
            "Reference to the neighboring system's system ID in TLV 238.";
        }

        leaf instance-id {
          type leafref {
            path "../state/instance-id";
          }
          description
            "Reference to the instance number for the same system-id
            in TLV 238.";
        }
        uses as-srlg-tlv;
      }
    }
  }

  augment "/oc-ni:network-instances/oc-ni:network-instance" +
          "/oc-ni:protocols/oc-ni:protocol/oc-ni:isis" +
          "/oc-ni:levels/oc-ni:level/oc-ni:link-state-database" +
          "/oc-ni:lsp/oc-ni:tlvs/oc-ni:tlv" {
    uses as-srlg-tlv-top;
  }

  grouping srv6-sid-structure-subsubtlv {
    container srv6-sid-structure {
      when "../state/type = " +
           "'arc-oc-isis-aug:SRV6_SID_STRUCTURE'";

      description
        "Sub-sub TLV for End, End.X and LAN End.X SIDs to describe
         the length of each part LB:LN:Func:Arg of the SID.";

      container state {
        description
          "State parameters of SRV6 SID structure sub-sub-TLV.";

        leaf lb-length {
          type uint8;
        }

        leaf ln-length {
          type uint8;
        }

        leaf fun-length {
          type uint8;
        }

        leaf arg-length {
          type uint8;
        }
      }
    }
  }

  grouping locator-subsubtlv-top {
    container subsubtlvs {
      description
        "This container describes SRV6 locator sub-sub-TLVs.";

      list subsubtlv {
        key "type";

        description
          "List of subsubTLV types in the LSDB for the SRV6 Locator TLV.";

        leaf type {
          type leafref {
            path "../state/type";
          }
          description
            "A reference for the TLV type being described within the LSDB";
        }

        container state {
          uses isis-lsdb-subsubtlv-type-state;
        }

        uses srv6-sid-structure-subsubtlv;
      }
    }
  }

  grouping prefix-attributes-subtlv {
    container prefix-attribute-flags {
      when "../state/type = " +
           "'oc-isis-lsdb-types:TLV135_PREFIX_FLAGS'";

      description
        "This container defines sub-TLV 4.";

      container state {
        description
          "State parameters of sub-TLV 4.";

        leaf-list flags {
          type arc-isis-types:isis-prefix-attributes-flags-type;

          description
            "Prefix reachability flags.";

          reference
            "RFC7794: IS-IS Prefix Attributes for Extended IPv4 and IPv6
              Reachability. sub-TLV 4.";
        }
      }
    }
  }

  identity ISIS_SRV6_END_SID_FLAG {
    description
      "Base identity for ISIS End SID sub-TLV 5 flags.";
  }

  typedef isis-srv6-end-sid-flags-type {
    type union {
      type identityref {
        base "ISIS_SRV6_END_SID_FLAG";
      }
      type uint8 {
        range "0..7";
      }
    }
    description
      "Type definition for ISIS End SID sub-TLV 5 flags. Unknown
       flags are represented as an integer describing the bit position
       of the flag.";
    reference
      "draft-ietf-lsr-isis-srv6-extensions";
  }

  grouping end-sid-subtlv {
    container srv6-end-sids {
      when "../state/type = " +
           "'arc-oc-isis-aug:SRV6_LOCATOR_END_SID'";

      description
        "This container defines SRV6 Locator sub-TLV 5.";

      list end-sid {
        key "sid";

        leaf sid {
          type leafref {
            path "../state/sid";
          }
        }

        container state {
          leaf sid {
            type inet:ipv6-address;
          }

          leaf-list flags {
            type isis-srv6-end-sid-flags-type;
          }

          leaf endpoint-func {
            type arc-srv6-types:srv6-endpoint-behavior-type;
          }
        }

        uses locator-subsubtlv-top;

        uses isis-lsdb-undefined-subsubtlv;
      }
    }
  }

  grouping ipv4-source-router-id-subtlv {
    container ipv4-source-router-id {
      when "../state/type = " +
           "'oc-isis-lsdb-types:TLV135_IPV4_ROUTER_ID'";

      description
        "This container defines sub-TLV 11 of
         ISIS TLVs 27, 135, 235, 236, 237.";

      container state {
        description
          "State parameters of sub-TLV 11.";

        leaf ipv4-source-router-id {
          type inet:ipv4-address-no-zone;
          description
            "IPv4 Source router ID address. In cases where the advertisement
                is an identifier for the advertising router (e.g., with the
                N-flag set in the Prefix Attribute Flags sub-TLV), it may be
                useful for other routers to know the source of the
                advertisement. When reachability advertisement is leaked from
                one level to another, Router ID advertised is always the Router
                ID of the IS-IS instance that originated the advertisement.
                This would be true even if the prefix had been learned from
                another protocol.";
          reference
            "RFC7794: IS-IS Prefix Attributes for Extended IPv4 and IPv6
                Reachability. sub-TLV 11";
        }
      }
    }
  }

  grouping ipv6-source-router-id-subtlv {
    container ipv6-source-router-id {
      when "../state/type = " +
           "'oc-isis-lsdb-types:TLV135_IPV6_ROUTER_ID'";

      description
        "This container defines sub-TLV 12 of
         ISIS TLVs 27, 135, 235, 236, 237.";

      container state {
        description
          "State parameters of sub-TLV 12.";

        leaf ipv6-source-router-id {
          type inet:ipv6-address;
          description
            "IPv6 Source router ID address. In cases where the advertisement
                is an identifier for the advertising router (e.g., with the
                N-flag set in the Prefix Attribute Flags sub-TLV), it may be
                useful for other routers to know the source of the
                advertisement. When reachability advertisement is leaked from
                one level to another, Router ID advertised is always the Router
                ID of the IS-IS instance that originated the advertisement.
                This would be true even if the prefix had been learned from
                another protocol.";
          reference
            "RFC7794: IS-IS Prefix Attributes for Extended IPv4 and IPv6
                Reachability. sub-TLV 12.";
        }
      }
    }
  }

  grouping locator-subtlv-top {
    container subtlvs {
      description
        "This container describes SRV6 locator sub-TLVs.";

      list subtlv {
        key "type";

        description
          "List of subTLV types in the LSDB for the SRV6 Locator TLV.";

        leaf type {
          type leafref {
            path "../state/type";
          }
          description
            "A reference for the TLV type being described within the LSDB";
        }

        container state {
          uses isis-lsdb-subtlv-type-state;
        }

        uses prefix-attributes-subtlv;
        uses end-sid-subtlv;
        uses ipv4-source-router-id-subtlv;
        uses ipv6-source-router-id-subtlv;
      }
    }
  }

  identity ISIS_SRV6_LOCATOR_FLAG {
    description
      "Base identity for ISIS SRV6 Locator TLV 27 flags.";
  }

  identity ISIS_SRV6_LOCATOR_DOWN_FLAG {
    base "ISIS_SRV6_LOCATOR_FLAG";
    description
      "When the Locator is leaked from level-2 to level-1, the DOWN
       flag MUST be set. Otherwise, this bit MUST be clear. Locators
       with the DOWN flag set MUST NOT be leaked from level-1 to level-2.
       This is to prevent looping.";
    reference
      "draft-ietf-lsr-isis-srv6-extensions";
  }

  typedef isis-srv6-locator-flags-type {
    type union {
      type identityref {
        base "ISIS_SRV6_LOCATOR_FLAG";
      }
      type uint8 {
        range "0..7";
      }
    }
    description
      "Type definition for ISIS SRV6 Locator TLV 27 flags. Unknown
       flags are represented as an integer describing the bit position
       of the flag.";
    reference
      "draft-ietf-lsr-isis-srv6-extensions";
  }

  grouping locators-tlv {
    list locator {
      key "mt-id locator";

      description
        "The SRV6 Locator is a form of summary address for the set of
         topology/algorithm specific SIDs instantiated at the node.";

      reference
        "draft-ietf-lsr-isis-srv6-extensions";

      leaf mt-id {
        type leafref {
          path "../state/mt-id";
        }
      }

      leaf locator {
        type leafref {
          path "../state/locator";
        }
      }

      container state {
        description
          "State parameters of ISIS Locator TLV 27.";

        leaf mt-id {
          type uint16;
          description
            "Multitopology Identifier.";
          reference
            "RFC5120: Multi Topology (MT) Routing in ISIS.";
        }

        leaf locator {
          type inet:ipv6-prefix;
          description
            "SRv6 Locator Address.";
        }

        leaf metric {
          type uint32;
          description
            "Metric.";
          reference
            "RFC5305: IS-IS Extensions for Traffic Engineering";
        }

        leaf-list flags {
          type isis-srv6-locator-flags-type;
        }

        leaf algorithm {
          type arc-igp-types:igp-algorithm-type;
          description
            "Algorithm associated with this locator.";
        }
      }

      uses locator-subtlv-top;

      uses oc-isis:isis-lsdb-undefined-subtlv;
    }
  }

  grouping locator-tlv-top {
    description
      "This grouping describes the ISIS SRV6 Locators TLV.";

    container srv6-locators {
      config false;
      description
        "This container defines a set of ISIS SRV6 Locators.";

      when "../oc-ni:state/oc-ni:type = 'arc-oc-isis-aug:SRV6_LOCATOR'" {
        description
          "Only include SRV6 Locator TLV attributes when the TLV type is 27.";
      }

      uses locators-tlv;
    }
  }

  augment "/oc-ni:network-instances/oc-ni:network-instance" +
          "/oc-ni:protocols/oc-ni:protocol/oc-ni:isis" +
          "/oc-ni:levels/oc-ni:level/oc-ni:link-state-database" +
          "/oc-ni:lsp/oc-ni:tlvs/oc-ni:tlv" {
    uses locator-tlv-top;
  }

  identity ISIS_SRV6_END_X_SID_FLAG {
    description
      "Base identity for ISIS SRV6 End.X SID flag.";
  }

  identity END_X_SID_B_FLAG {
    base "ISIS_SRV6_END_X_SID_FLAG";
    description
      "Backup flag. If set, the End.X SID is eligible for protection.";
    reference
      "draft-ietf-lsr-isis-srv6-extensions";
  }

  identity END_X_SID_S_FLAG {
    base "ISIS_SRV6_END_X_SID_FLAG";
    description
      "Set flag. When set, the S-Flag indicates that the End.X SID
       refers to a set of adjacencies (and therefore MAY be assigned to
       other adjacencies as well).";
    reference
      "draft-ietf-lsr-isis-srv6-extensions";
  }

  identity END_X_SID_P_FLAG {
    base "ISIS_SRV6_END_X_SID_FLAG";
    description
      "Persistent flag. When set, the P-Flag indicates that the End.X SID
       is persistently allocated, i.e., the End.X SID value remains consistent
       across router restart and/or interface flap.";
    reference
      "draft-ietf-lsr-isis-srv6-extensions";
  }

  typedef isis-srv6-end-x-flags-type {
    type union {
      type identityref {
        base "ISIS_SRV6_END_X_SID_FLAG";
      }
      type uint8 {
        range "0..7";
      }
    }
    description
      "Type definition for ISIS SRV6 End.X SID flags. Unknown
       flags are represented as an integer describing the bit position
       of the flag.";
    reference
      "draft-ietf-lsr-isis-srv6-extensions";
  }

  grouping end-x-sid-subsubtlv-top {
    container subsubtlvs {
      description
        "This container describes SRV6 End.X SID sub-sub-TLVs.";

      list subsubtlv {
        key "type";

        description
          "List of subsubTLV types in the LSDB for the SRV6 End.X SID sub-TLV.";

        leaf type {
          type leafref {
            path "../state/type";
          }
          description
            "A reference for the TLV type being described within the LSDB";
        }

        container state {
          uses isis-lsdb-subsubtlv-type-state;
        }

        uses srv6-sid-structure-subsubtlv;
      }
    }
  }

  identity IP_REACHABILITY_PREFIX_SID_SUBTLV_TYPE {
    base "oc-isis-lsdb-types:ISIS_SUBTLV_TYPE";
    description
      "ISIS IP REACHBILITY PREFIX SID SUBTLV.";
  }

  identity EXTENDED_IS_REACH_ADJACENCY_SID_SUBTLV_TYPE {
    base "oc-isis-lsdb-types:ISIS_SUBTLV_TYPE";
    description
      "ISIS EXTENDED IS REACHBILITY ADJACENCY SID SUBTLV.";
  }

  identity SRV6_END_X_SID {
    base "oc-isis-lsdb-types:ISIS_SUBTLV_TYPE";
    description
      "ISIS SRV6 End.X SID SUB-TLV type.";
  }

  identity SRV6_LAN_END_X_SID {
    base "oc-isis-lsdb-types:ISIS_SUBTLV_TYPE";
    description
      "ISIS SRV6 LAN End.X SID SUB-TLV type.";
  }

  identity SRV6_LINK_MSD {
    base "oc-isis-lsdb-types:ISIS_SUBTLV_TYPE";
    description
      "ISIS SRV6 LINK MSD SUB-TLV type.";
  }

  identity ASLA {
    base "oc-isis-lsdb-types:ISIS_SUBTLV_TYPE";
    description
      "ISIS ASLA SUB-TLV type.";
  }

  grouping end-x-sid-common {
    leaf sid {
      type inet:ipv6-address;
      description "The SRv6 SID address.";
    }

    leaf-list flags {
      type isis-srv6-end-x-flags-type;
      description "Flags associated with this End.X SID.";
    }

    leaf algorithm {
      type arc-igp-types:igp-algorithm-type;
      description "Associated IGP algorithm.";
    }

    leaf weight {
      type uint8;
      description "Load balancing factor for parallel adjacencies.";
    }

    leaf endpoint-func {
      type arc-srv6-types:srv6-endpoint-behavior-type;
      description "Endpoint behavior for End.X SID.";
    }
  }

  grouping end-x-sid-subtlv {
    container end-x-sids {
      when "../oc-ni:state/oc-ni:subtlv-type = " +
           "'arc-oc-isis-aug:SRV6_END_X_SID'";

      description
        "This container describes ISIS SRV6 End.X SID.";

      list end-x-sid {
        key "sid";

        leaf sid {
          type leafref {
            path "../state/sid";
          }
        }

        container state {
          uses end-x-sid-common;
        }

        uses end-x-sid-subsubtlv-top;

        uses isis-lsdb-undefined-subsubtlv;
      }
    }
  }

  grouping lan-end-x-sid-subtlv {
    container lan-end-x-sids {
      when "../oc-ni:state/oc-ni:subtlv-type = " +
           "'arc-oc-isis-aug:SRV6_LAN_END_X_SID'";

      description
        "This container describes ISIS SRV6 LAN End.X SID.";

      list lan-end-x-sid {
        key "sid";

        leaf sid {
          type leafref {
            path "../state/sid";
          }
        }

        container state {
          leaf system-id {
            type arc-isis-types:system-name;
            description "Describes the system ID of the neighbor
                         associated with the SID value.";
          }

          uses end-x-sid-common;
        }

        uses end-x-sid-subsubtlv-top;

        uses isis-lsdb-undefined-subsubtlv;
      }
    }
  }

  grouping link-msd-subtlv {
    description
      "Means to advertise to advertise link specific
       values for Maxium Sid Depths(MSD) of various types";
    container link-msds {
      when "../oc-ni:state/oc-ni:subtlv-type = " +
           "'arc-oc-isis-aug:SRV6_LINK_MSD'" {
        description
           "Only include node MSD when the sub-TLV is type 15.";
      }
      description
        "Maximum SRv6 SID Depths.";
      list msd {
        key "type";
        leaf type {
          type leafref {
            path "../state/type";
          }
          description
            "Reference to the MSD type being described.";
        }
        container state {
          description
            "State parameter of MSD.";
          leaf type {
            description
              "The MSD type.";
            type arc-igp-types:msd-type;
          }
          leaf value {
            description
              "The MSD value.";
            type uint8;
          }
        }
      }
    }
  }

  grouping is-reachability-srv6-subtlv-top {
    uses end-x-sid-subtlv;
    uses lan-end-x-sid-subtlv;
    uses link-msd-subtlv;
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:extended-is-reachability" +
          "/oc-ni:neighbors/oc-ni:neighbor/oc-ni:subTLVs/oc-ni:subTLVs" {
    uses is-reachability-srv6-subtlv-top;
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:mt-isn" +
          "/oc-ni:neighbors/oc-ni:neighbor/oc-ni:instances/oc-ni:instance" +
          "/oc-ni:subTLVs/oc-ni:subTLVs" {
    uses is-reachability-srv6-subtlv-top;
  }

  grouping is-reach-asla-ext-admin-group-subsubtlv-top {
    container extended-admin-groups {
      container state {
        leaf-list extended-admin-group {
          type union {
            type uint32;
            type string;
          }
          description
            "Extended admin-group bit positions";
        }
      }
    }
  }

  grouping is-reach-asla-admin-group-subsubtlv-top {
    container admin-groups {
      container state {
        leaf-list admin-group {
          type union {
            type uint32;
            type string;
          }
          description
            "Admin-group bit positions";
        }
      }
    }
  }

  grouping is-reach-asla-te-metric-subsubtlv-top {
    container te-default-metric {
      container state {
        leaf metric {
          type uint32;
          description
            "Default metric for Traffic-engineering";
        }
      }
    }
  }

  grouping is-reach-asla-min-max-delay-subsubtlv-top {
    container min-max-delay {
      container state {
        leaf min-delay {
          type uint32;
          description
            "Minimum measured link delay value (in microseconds)";
        }
        leaf max-delay {
          type uint32;
          description
            "Maximum measured link delay value (in microseconds)";
        }
      }
    }
  }

  grouping is-reach-asla-subsubtlvs-top {
    container subsubtlvs {
      description
        "This container describes SRV6 End.X SID sub-sub-TLVs.";

      list subsubtlv {
        key "type";

        description
          "List of subsubTLV types in the LSDB for the SRV6 End.X SID sub-TLV.";

        leaf type {
          type leafref {
            path "../state/type";
          }
          description
            "A reference for the TLV type being described within the LSDB";
        }

        container state {
          uses isis-lsdb-subsubtlv-type-state;
        }

        uses is-reach-asla-admin-group-subsubtlv-top {
          when "type = 'arc-oc-isis-aug:ADMIN_GROUP_TYPE'"; 
       }
        uses is-reach-asla-ext-admin-group-subsubtlv-top {
          when "type = 'arc-oc-isis-aug:EXTENDED_ADMIN_GROUP_TYPE'";
        } 
        uses is-reach-asla-te-metric-subsubtlv-top {
          when "type = 'arc-oc-isis-aug:TE_DEFAULT_METRIC_TYPE'";
        }
        uses is-reach-asla-min-max-delay-subsubtlv-top {
          when "type = 'arc-oc-isis-aug:MIN_MAX_DELAY_METRIC_TYPE'";
        }
      }
    }
  }

  grouping is-reachability-asla-subtlv-attr-top {
    leaf instance-id {
      type uint16;
      description
        "The sub-TLV instance identifier. Local identifier
         to identify the ASLA sub-TLV when multiple instances
         of the sub-TLV are received";
    }
    leaf standard-applications {
      type isis-sabm;
      description
        "Standard applications bitmask";
      reference
        "RFC 8918: Section 4.1";
    }
    leaf user-defined-applications {
      type uint64;
      description
        "User defined applications bitmask";
      reference
        "RFC 8918: Section 4.1";
    }
  }

  grouping is-reachability-asla-subtlv-top {
    container aslas {
      when "../oc-ni:state/oc-ni:subtlv-type = " +
           "'arc-oc-isis-aug:ASLA'" {
        description
           "Only include ASLA when the sub-TLV is type 16.";
      }
      list asla {
        key "instance-id";
        leaf instance-id {
          type leafref {
            path "../state/instance-id";
          }
          description
            "ASLA Sub-TLV instance indentifier";
        }
        container state {
          uses is-reachability-asla-subtlv-attr-top;
        }
        uses is-reach-asla-subsubtlvs-top;
        uses isis-lsdb-undefined-subsubtlv;
      }
    }
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:extended-is-reachability" +
          "/oc-ni:neighbors/oc-ni:neighbor/oc-ni:subTLVs/oc-ni:subTLVs" {
    uses is-reachability-asla-subtlv-top;
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:mt-isn" +
          "/oc-ni:neighbors/oc-ni:neighbor/oc-ni:instances/oc-ni:instance" +
          "/oc-ni:subTLVs/oc-ni:subTLVs" {
    uses is-reachability-asla-subtlv-top;
  }

  identity ADJ_NEIGHBOR_TYPE {
    description
     "Identity for base neighbor type";
  }

  identity POINT_TO_POINT {
     base "ADJ_NEIGHBOR_TYPE";
     description
      "POINT TO POINT neighbor type";
  }

  typedef adj-sid-neighbor-type {
    type union {
      type identityref {
        base "ADJ_NEIGHBOR_TYPE";
      }
      type inet:ip-address;
    }
    description
      "Type definition for ADJ SID neighbor type (P2P identity/Neighbor IP)";
  }

  grouping sr-igp-adjacency-sid-config {
    description
      "Configuraton parameters relating to the AdjSID.";

    leaf neighbor {
      type adj-sid-neighbor-type;
        description
          "The remote system on the interface with which the Adj-SID is
          associated.(POINT_TO_POINT identity for p2p)";
    }

    leaf sid-type {
      mandatory true;
      type enumeration {
        enum INDEX {
          description
            "SID is of index type";
        }
        enum ABSOLUTE {
          description
            "SID is of absolute index type";
        }
      }
      description
        "Describes the type of the SID value.
        INDEX type indicates that configured
        SID is index value from the SRLB Block.
        ABSOLUTE type indicates that configured
        value is the actual label value from SRLB block.";
      reference
        "RFC 8667 - Section 2.2.1";
    }

    leaf value {
      type uint32;
      description
        "IGP ADJ-SID value(Index/Value based on SID-TYPE).";
    }
  }

  grouping sr-igp-adjacency-sid-config-top {
    description
      "This grouping defines ISIS Adjacency SID.";
      container adjacency-sids {
        description
          "Configuration relating to the advertisement of a
          segment routing adjacency SID for this interface.";

        list adjacency-sid {
          key "neighbor";

          description
            "An Adjacency SID to be advertised for the specified interface.
            The Adj-SID's identifier (the SID ID) must be unique, with flags
            specified indicating the parameters that should be set for the SID.
            Where a SID value is specified that is allocated from the SRLB, the
            global flag must be set by the system.";

          leaf neighbor {
            type leafref {
              path "../config/neighbor";
            }
            description
              "Reference to the neighbor ip with which the Adjacency SID is
              associated(USE POINT_TO_POINT for P2P link).";
          }
          container config {
            description
              "Configuraton parameters relating to the AdjSID.";

            uses sr-igp-adjacency-sid-config;
         }
       }
     }
  }

  grouping sr-igp-prefix-sid-config {
    description
      "Configuration parameters relating to an IGP prefix SID advertisement";

    leaf algorithm {
      type arc-igp-types:igp-algorithm-type;
      description
        "Prefix-SID algorithm to be used for path computation.";
    }

    leaf sid-type {
      mandatory true;
      type enumeration {
        enum INDEX {
          description
            "SID is of index type";
        }
        enum ABSOLUTE {
          description
            "SID is of absolute index type";
        }
      }
      description
        "Describes the type of the SID value.
        INDEX type indicates that configured
        SID is index value from the SRGB Block.
        ABSOLUTE type indicates that configured
        value is the actual label value from SRGB block.";
      reference
        "RFC 8667 - Section 2.1.1";
    }

    leaf value {
      type uint32;
      description
        "IGP Prefix-SID value(Index/Value based on SID-TYPE).";
    }

    leaf clear-n-flag {
      type boolean;
      description
        "Setting this clear-n-flag clears the NODE flag of the prefix SID.";
    }

    leaf label-option {
      type enumeration {
        enum NO_PHP {
          description
            "When this value is specified, the penultimate hop must not pop
            the Prefix-SID label before forwarding it to the local system.";
        }
        enum EXPLICIT_NULL {
          description
            "When set, the penultimate hop must swap the prefix SID for the
            relevant explicit null label before forwarding the packet.";
        }
      }
        description
          "The options associated with the IGP prefix SID for MPLS. The value
          of this leaf specifies the option that the SID should be advertised
          into the IGP with.";
    }
  }

  grouping sr-igp-prefix-sid-config-top {
    description
      "This grouping defines ISIS Prefix SID.";

    container prefix-sids {
      description
        "This container defines segment routing extensions for
        prefixes.";
      reference
        "draft-ietf-isis-segment-routing-extensions. sub-TLV 3: TLV
        135, 235, 236, 237.";

      list prefix-sid {
        key "algorithm";

        description
          "Prefix Segment-ID list. IGP-Prefix Segment is an IGP segment
          attached to an IGP prefix. An IGP-Prefix Segment is global
          (unless explicitly advertised otherwise) within the SR/IGP
          domain.";

        leaf algorithm {
          type leafref {
            path "../config/algorithm";
          }
          description
            "Reference to the value of the prefix SID algo(SPF/STRICT_SPF/128-255).";
        }

        container config {
          description
            "Config parameters for Prefix-SID.";

          uses sr-igp-prefix-sid-config;
        }
      }
    }
  }

  grouping isis-lsdb-adjacency-sid-state {
    description
      "State parameters of Adjacency-SID.";

    leaf value {
      type uint32;
      description
        "Adjacency-SID value.";
    }

    leaf-list flags {
      type enumeration {
        enum ADDRESS_FAMILY {
          description
            "Address-family flag. When unset, the Adj-SID refers to an
            adjacency with outgoing IPv4 encapsulation. If set then the
            Adj-SID refers to an adjacency with outgoing IPv6
            encapsulation.";
        }
        enum BACKUP {
          description
            "Backup flag. When set, the Adj-SID refers to an adjacency
            being protected (e.g.: using IPFRR or MPLS-FRR).";
        }
        enum SET {
          description
          "Set flag. When set, the S-Flag indicates that the Adj-SID
          refers to a set of adjacencies.";
        }
        enum PERSISTENT {
          description
            "Persistent flag. When set, the P-Flag indicates the ADJ-SID
            is persistent across restarts.";
        }
        enum VALUE {
          description
            "Value flag. When set, the SID carries a value (instead of an
            index). By default the flag is SET.";
        }
        enum LOCAL {
          description
            "Local flag. When set, the value/index carried by the SID has
            local significance. By default the flag is SET.";
        }
      }
      description
        "Flags associated with Adj-Segment-ID.";
    }

    leaf weight {
      type uint8;
      description
        "Value that represents the weight of the Adj-SID for the purpose
        of load balancing.";
    }
  }

  grouping isis-lsdb-adjacency-sid-state-top {
    description
      "This grouping defines ISIS Adjacency SID state.";
    container adjacency-sids {
      when "../oc-ni:state/oc-ni:subtlv-type =" +
           "'arc-oc-isis-aug:EXTENDED_IS_REACH_ADJACENCY_SID_SUBTLV_TYPE'" {
        description
          "Only include the Adjacency SID container when
          the sub-TLV is type 31.";
      }
      list adjacency-sid {
        key "sid";

        description
          "Adjacency Segment-ID list. Adjacency Segment is an IGP segment
          attached to an IGP Adjacency. An IGP-Adjacency Segment is global
          (unless explicitly advertised otherwise) within the SR/IGP
          domain.";

        leaf sid {
          type leafref {
            path "../state/value";
          }
          description
            "Reference to the value of the Adjacency SID.";
        }
        container state {
          description
            "State parameters of Adjacency-SID.";

          uses isis-lsdb-adjacency-sid-state;
        }
      }
    }
  }

  grouping isis-lsdb-prefix-sid-state {
    description
      "State parameters for Prefix-SID.";

    leaf algorithm {
      type arc-igp-types:igp-algorithm-type;
      description
        "Prefix-SID algorithm to be used for path computation.";
    }

    leaf sid {
      type uint32;
      description
        "IGP Prefix-SID value.";
    }

    leaf-list flags {
      type enumeration {
        enum NO_PHP {
          description
            "When this value is specified, the penultimate hop must not pop
            the Prefix-SID label before forwarding it to the local system.";
        }
        enum EXPLICIT_NULL {
          description
            "When set, the penultimate hop must swap the prefix SID for the
            relevant explicit null label before forwarding the packet.";
        }
        enum READVERTISEMENT {
          description
            "Readvertisment flag. When set, the prefix to which this
            Prefix-SID is attached, has been propagated by the router
            either from another level or from redistribution.";
        }
        enum NODE {
          description
            "Node flag. When set, the Prefix-SID refers to the
            router identified by the prefix. Typically, the
            N-Flag is set on Prefix-SIDs attached to a router
            loopback address.";
        }
        enum VALUE {
          description
            "Value flag. When set, the Prefix-SID carries a value (instead
            of an index). By default the flag is UNSET.";
        }
        enum LOCAL {
          description
          "Local flag. When set, the value/index carried by the
          Prefix-SID has local significance. By default the flag is
          UNSET.";
        }
      }
      description
        "The options associated with the IGP prefix SID for MPLS. The value
        of this leaf specifies the option that the SID should be advertised
        into the IGP with.";
    }
  }

  grouping isis-lsdb-prefix-sid-state-top {
    description
      "This grouping defines ISIS Prefix SID.";

    container prefix-sids {
      when "../oc-ni:state/oc-ni:subtlv-type = " +
           "'arc-oc-isis-aug:IP_REACHABILITY_PREFIX_SID_SUBTLV_TYPE'" {
        description
          "Only include the Prefix SID container when
          the sub-TLV is type 3.";
      }
      description
        "This container defines segment routing extensions for
        prefixes.";

      reference
        "draft-ietf-isis-segment-routing-extensions. sub-TLV 3: TLV
        135, 235, 236, 237.";

      list prefix-sid {
        key "algorithm";

        description
          "Prefix Segment-ID list. IGP-Prefix Segment is an IGP segment
          attached to an IGP prefix. An IGP-Prefix Segment is global
          (unless explicitly advertised otherwise) within the SR/IGP
          domain.";

        leaf algorithm {
          type leafref {
            path "../state/algorithm";
          }
          description
            "Reference to the value of the prefix SID Algo(SPF/STRICT_SPF/128-255).";

        }

        container state {
          description
            "State parameters for Prefix-SID.";

          uses isis-lsdb-prefix-sid-state;
        }
      }
    }
  }

  grouping fast-reroute-itf-af-config-top {
    description
      "IS-IS interface AFI/SAFI fast reroute configuration.";

    container fast-reroute {
      description
        "Fast reroute configuration";

      container ip {
        description
          "IP Fast Reroute";

        container config {
          description
            "IP Fast Reroute Configuration";

          leaf enabled {
            description
              "IP FRR Enabled";

            type boolean;

            must "not(../../../../../../../fast-reroute/ti-lfa/config/srv6-enabled) and " +
                 "not(../../../../../../oc-ni:af/oc-ni:config/fast-reroute/ti-lfa/config/srv6/enabled)" {
              error-message "Cannot enable both TI-LFA and IP-FRR on the same interface";
            }
          }
        }
      }

      container ti-lfa {
        description
          "TI-LFA Fast Reroute";

        container config {
          description
            "TI-LFA Fast Reroute Configuration";

          container srv6 {
            description
              "TI-LFA using SRv6";

            leaf enabled {
              description
                "Enables TI-LFA fast reroute over SRv6";

              type boolean;

              must "not(../../../../../../../oc-ni:af/oc-ni:config" +
                        "/fast-reroute/ti-lfa/config/sr-mpls/enabled)" {
                error-message "Cannot enable both TI-LFA SR-MPLS and" + 
                              "SRv6 on the same interface";
              }

              must "not(../../../../../../../oc-ni:af/oc-ni:config" +
                        "/fast-reroute/ip/config/enabled)" {
                error-message "Cannot enable both TI-LFA and" +
                              "IP-FRR on the same interface";
              }

              must "not(../../../../../../../../fast-reroute" +
                        "/ti-lfa/config/srv6-enabled)" {
                error-message "Cannot configure TI-LFA at interface level and AF level";
              }
            }

            when "derived-from-or-self(../../../../oc-ni:afi-name, 'oc-isis-types:IPV6') and " +
                  "derived-from-or-self(../../../../oc-ni:safi-name, 'oc-isis-types:UNICAST')";
          }

          container sr-mpls {
            description
              "TI-LFA using SR MPLS";

            leaf enabled {
              description
                "Enables TI-LFA fast reroute over SRv6";

              type boolean;

              must "not(../../../../../../../oc-ni:af/oc-ni:config" +
                        "/fast-reroute/ti-lfa/config/srv6/enabled)" {
                error-message "Cannot enable both TI-LFA SR-MPLS and SRv6 on the same interface";
              }

              must "not(../../../../../../../oc-ni:af/oc-ni:config" +
                        "/fast-reroute/ip/config/enabled)" {
                error-message "Cannot enable both TI-LFA and IP-FRR on the same interface";
              }

              must "not(../../../../../../../../fast-reroute" +
                        "/ti-lfa/config/srv6-enabled)" {
                error-message "Cannot configure TI-LFA at interface level and AF level";
              }
            }
          }
        }
      }
    }
  }

  grouping interface-af-ipv4-unnumbered-top {
    leaf ipv4-unnumbered {
      type boolean;
      description
        "Indicates if IPV4 interface is unnumbered";
    }
  }

  augment "/oc-ni:network-instances/oc-ni:network-instance" +
          "/oc-ni:protocols/oc-ni:protocol/oc-ni:isis" +
          "/oc-ni:interfaces/oc-ni:interface/oc-ni:afi-safi" +
          "/oc-ni:af/oc-ni:config" {
    uses sr-igp-prefix-sid-config-top;
    uses sr-igp-adjacency-sid-config-top;
    uses fast-reroute-itf-af-config-top;
  }

  augment "/oc-ni:network-instances/oc-ni:network-instance" +
          "/oc-ni:protocols/oc-ni:protocol/oc-ni:isis" +
          "/oc-ni:interfaces/oc-ni:interface/oc-ni:afi-safi" +
          "/oc-ni:af/oc-ni:state" {
    uses fast-reroute-itf-af-config-top;
    uses interface-af-ipv4-unnumbered-top {
      when "derived-from-or-self(../oc-ni:afi-name, 'oc-isis-types:IPV4') and " +
           "derived-from-or-self(../oc-ni:safi-name, 'oc-isis-types:UNICAST')";
    }
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:extended-ipv4-reachability" +
          "/oc-ni:prefixes/oc-ni:prefix/oc-ni:subTLVs/oc-ni:subTLVs" {
    uses isis-lsdb-prefix-sid-state-top;
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:ipv6-reachability" +
          "/oc-ni:prefixes/oc-ni:prefix/oc-ni:subTLVs/oc-ni:subTLVs" {
    uses isis-lsdb-prefix-sid-state-top;
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:mt-ipv6-reachability" +
          "/oc-ni:prefixes/oc-ni:prefix/oc-ni:subTLVs/oc-ni:subTLVs" {
    uses isis-lsdb-prefix-sid-state-top;
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:extended-is-reachability" +
          "/oc-ni:neighbors/oc-ni:neighbor" +
          "/oc-ni:subTLVs/oc-ni:subTLVs" {
    uses isis-lsdb-adjacency-sid-state-top;
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:mt-isn" +
          "/oc-ni:neighbors/oc-ni:neighbor/oc-ni:instances/oc-ni:instance" +
          "/oc-ni:subTLVs/oc-ni:subTLVs" {
    uses isis-lsdb-adjacency-sid-state-top;
  }

  grouping isis-af-mt-config {
    description
      "This grouping defines ISIS address-family level multi-topology
      config.";

    leaf enabled {
      type boolean;
      description
        "Indicates whether multi-topology is enabled for this
        address-family.";
    }
  }

  grouping isis-af-mt {
    description
      "This grouping defines ISIS address-family level multi-topology.";

    container multi-topology {
      description
        "This container defines ISIS address-family multi-topology
        config and state.";


      container config {
        description
          "Address-family multi-topology config.";

        uses isis-af-mt-config;
      }

      container state {
        config false;
        description
          "Address-family multi-topology state.";

        uses isis-af-mt-config;
      }
    }
  }

  grouping micro-loop-af-avoidance {
    description
      "Micro-loop avoidance configuration";
    leaf sr-mpls-enabled {
      type boolean;
      default false;
      description
        "micro-loop-avoidance SR MPLS configuration";
    }
  }

  grouping micro-loop-af-avoidance-top {
    description
      "Micro-loop avoidance configuration per af.";
    container micro-loop-avoidance {
      description
        "Micro-loop avoidance Configuration per address family";
      container config {
        uses micro-loop-af-avoidance;
      }
      container state {
        config false;
        uses micro-loop-af-avoidance;
      }
    }
  }
  augment "/oc-ni:network-instances/oc-ni:network-instance" +
          "/oc-ni:protocols/oc-ni:protocol/oc-ni:isis/oc-ni:global" +
          "/oc-ni:afi-safi/oc-ni:af" {
    uses isis-af-mt {
      when "oc-ni:config/oc-ni:afi-name = 'oc-isis-types:IPV6' and " +
           "oc-ni:config/oc-ni:safi-name = 'oc-isis-types:UNICAST'" {
        description
          "Applicable only for IPV6 UNICAST address-family.";
      }
    }
    uses micro-loop-af-avoidance-top;
    //TBD make this exclusive to global/micro-loop-avoidance/srv6_enabled config
  }

  grouping isis-lsdb-mt-tlv-flags {
    leaf overload-bit {
      type boolean;
      description
        "OVERLOAD bit.";
    }

    leaf attached-bit {
      type boolean;
      description
        "ATTACH bit.";
    }
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:multi-topology" +
          "/oc-ni:topologies/oc-ni:topology" +
          "/oc-ni:state" {
    uses isis-lsdb-mt-tlv-flags;
  }

  grouping isis-max-link-bandwidth-state {
    description
      "This grouping defines augments to max-link-bandwidth
       Sub-TLV state";

    leaf max-link-bandwidth-value {
      type uint64;
      units "bytes per second";
      description
        "The maximum bandwidth that can be used on this link in this
        direction (from the system originating the LSP to its
        neighbors).  It is encoded in 32 bits in IEEE floating point
        format.  The units are bytes (not bits!) per second.";
      reference
        "RFC5305: IS-IS Extensions for Traffic Engineering. sub-TLV 9:
        TLV 22,23,141,222,223.";
    }
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:extended-is-reachability" +
          "/oc-ni:neighbors/oc-ni:neighbor/oc-ni:subTLVs/oc-ni:subTLVs" +
          "/oc-ni:max-link-bandwidth/oc-ni:state" {
    uses isis-max-link-bandwidth-state;
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:mt-isn" +
          "/oc-ni:neighbors/oc-ni:neighbor/oc-ni:instances/oc-ni:instance" +
          "/oc-ni:subTLVs/oc-ni:subTLVs" +
          "/oc-ni:max-link-bandwidth/oc-ni:state" {
    uses isis-max-link-bandwidth-state;
  }

  grouping isis-max-reservable-link-bandwidth-state {
    description
      "This grouping defines augments to max-reservable-link-bandwidth
       Sub-TLV state";

    leaf max-reservable-link-bandwidth-value {
      type uint64;
      units "bytes per second";
      description
        "The maximum amount of bandwidth that can be reserved in this
        direction on this link.  Note that for oversubscription
        purposes,  this can be greater than the bandwidth of the link.
        It is encoded  in 32 bits in IEEE floating point format.  The
        units are bytes  (not bits!) per second.";
      reference
        "RFC5305: IS-IS Extensions for Traffic Engineering. Sub-TLV 10:
        TLV 22,23,141,222,223.";
    }
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:extended-is-reachability" +
          "/oc-ni:neighbors/oc-ni:neighbor/oc-ni:subTLVs/oc-ni:subTLVs" +
          "/oc-ni:max-reservable-link-bandwidth/oc-ni:state" {
    uses isis-max-reservable-link-bandwidth-state;
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:mt-isn" +
          "/oc-ni:neighbors/oc-ni:neighbor/oc-ni:instances/oc-ni:instance" +
          "/oc-ni:subTLVs/oc-ni:subTLVs" +
          "/oc-ni:max-reservable-link-bandwidth/oc-ni:state" {
    uses isis-max-reservable-link-bandwidth-state;
  }

  grouping isis-unreserved-bandwidth-state {
    description
      "This grouping defines augments to unreserved-bandwidth
       Sub-TLV state";

    leaf bandwidth-value {
      type uint64;
      units "bytes per second";
      description
        "The amount of bandwidth reservable in this
        direction on this link. Note that for
        oversubscription purposes, this can be greater than
        the bandwidth of the link. It contains eight 32-bit
        IEEE floating point numbers(one for each priority).
        The units are bytes (not bits!) per second. The
        values correspond to the bandwidth that can be
        reserved with a setup priority of 0 through 7,
        arranged in increasing order with priority 0
        occurring at the start of the sub-TLV, and priority
        7 at the end of the sub-TLV.";
    }
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:extended-is-reachability" +
          "/oc-ni:neighbors/oc-ni:neighbor/oc-ni:subTLVs/oc-ni:subTLVs" +
          "/oc-ni:unreserved-bandwidth/oc-ni:setup-priority/oc-ni:state" {
    uses isis-unreserved-bandwidth-state;
  }

  augment "/oc-ni:network-instances/oc-ni:network-instance" +
          "/oc-ni:protocols/oc-ni:protocol/oc-ni:isis/oc-ni:levels" +
          "/oc-ni:level/oc-ni:link-state-database/oc-ni:lsp" +
          "/oc-ni:tlvs/oc-ni:tlv/oc-ni:mt-isn" +
          "/oc-ni:neighbors/oc-ni:neighbor/oc-ni:instances/oc-ni:instance" +
          "/oc-ni:subTLVs/oc-ni:subTLVs" +
          "/oc-ni:unreserved-bandwidth/oc-ni:setup-priority/oc-ni:state" {
    uses isis-unreserved-bandwidth-state;
  }

  grouping isis-bandwidth-constraints-state {
    description
      "This grouping defines augments to bandwidth-constraints
       Sub-TLV state";

    leaf bandwidth-constraints-value {
      type uint64;
      units "bytes per second";
      description
        "Contains BC0, BC1,... BC(N-1).  Each BC is encoded on 32 bits
        in IEEE floating point format.  The units are bytes (not bits!)
        per secondy.";
    }
  }

  grouping isis-residual-bandwidth-state {
    description
      "This grouping defines augments to residual-bandwidth
       Sub-TLV state";

    leaf residual-bandwidth-value {
      type uint64;
      units "bytes per second";
      description
        "Residual bandwidth on a link,forwarding adjacency [RFC4206], or
        bundled link in IEEE floating-point format with units of bytes
        per second. For a link or forwarding adjacency, residual
        bandwidth is defined to be the Maximum Bandwidth [RFC5305] minus
        the bandwidth currently allocated to RSVP-TE label switched
        paths. For a bundled link, residual bandwidth is defined to be
        the sum of the component link residual bandwidths.";
    }
  }

  grouping isis-available-bandwidth-state {
    description
      "This grouping defines augments to available-bandwidth
       Sub-TLV state";

    leaf available-bandwidth-value {
      type uint64;
      units "bytes per second";
      description
        "The available bandwidth on a link, forwarding adjacency, or
        bundled link in IEEE floating-point format with units of bytes
        per second. For a link or forwarding adjacency, available
        bandwidth is defined to be residual bandwidth minus the measured
        bandwidth used for the actual forwarding of non-RSVP-TE label
        switched path packets.  For a bundled link, available bandwidth
        is defined to be the sum of the component link available
        bandwidths minus the measured bandwidth used for the actual
        forwarding of non-RSVP-TE label switched path packets.  For a
        bundled link, available bandwidth is defined to be the sum of
        the component link available bandwidths.";
    }
  }

  grouping isis-utilized-bandwidth-state {
    description
      "This grouping defines augments to utilized-bandwidth
       Sub-TLV state";

    leaf utilized-bandwidth-value {
      type uint64;
      units "bytes per second";
      description
        "The bandwidth utilization on a link, forwarding adjacency, or
        bundled link in IEEE floating-point format with units of bytes
        per second.  For a link or forwarding adjacency, bandwidth
        utilization represents the actual utilization of the link (i.e.,
        as measured by the advertising node).  For a bundled link,
        bandwidth utilization is defined to be the sum of the component
        link bandwidth utilizations.";
    }
  }

  grouping isis-global-area-system-id {
    leaf-list area-address {
      type string;
      description
        "This type defines IS-IS Area address. An area address should be in
        the form xx.yyyy.";
     }

    leaf system-id {
      type string;
      description
        "This type defines IS-IS System ID. A System ID should  be in
        the form yyyy.yyyy.yyyy.00 ";
     }
  }

  augment "/oc-ni:network-instances/oc-ni:network-instance" +
          "/oc-ni:protocols/oc-ni:protocol/oc-ni:isis/oc-ni:global" +
          "/oc-ni:state" {
    uses isis-global-area-system-id;
  }

  grouping isis-frr-timers {
    description
      "This grouping defines ISIS FRR/TI-LFA timers";

    leaf fast-reroute-interval {
      type uint16;
      units milliseconds;
      default 500;
      description
        "Specifies the time interval in milliseconds before Fast Reroute
         and TI-LFA computations begin after the primary SPF completes.
         The default is 500 milliseconds.";
    }
  }

  augment "/oc-ni:network-instances/oc-ni:network-instance" +
          "/oc-ni:protocols/oc-ni:protocol/oc-ni:isis/oc-ni:global" +
          "/oc-ni:timers/oc-ni:config" {
    uses isis-frr-timers;
  }

  augment "/oc-ni:network-instances/oc-ni:network-instance" +
          "/oc-ni:protocols/oc-ni:protocol/oc-ni:isis/oc-ni:global" +
          "/oc-ni:timers/oc-ni:state" {
    uses isis-frr-timers;
  }

    grouping isis-spf-timers {
    description
      "This grouping defines additional ISIS SPF timers";

    leaf spf-mla-interval {
      type uint64 {
        range "1..120000";
      }
      units milliseconds;
      default 25;
      description
        "Time interval in milliseconds between the detection of topology change
         and when the SPF algorithm runs, if the topology change is such that
         Segment Routing microloop avoidance becomes active.";
    }
  }

  augment "/oc-ni:network-instances/oc-ni:network-instance" +
          "/oc-ni:protocols/oc-ni:protocol/oc-ni:isis/oc-ni:global" +
          "/oc-ni:timers/oc-ni:spf/oc-ni:config" {
    uses isis-spf-timers;
  }

  augment "/oc-ni:network-instances/oc-ni:network-instance" +
          "/oc-ni:protocols/oc-ni:protocol/oc-ni:isis/oc-ni:global" +
          "/oc-ni:timers/oc-ni:spf/oc-ni:state" {
    uses isis-spf-timers;
  }
}
