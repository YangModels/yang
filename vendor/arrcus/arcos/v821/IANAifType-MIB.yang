/*
 * Generated by confdc --mib2yang
 * Source: IANAifType-MIB.mib
 */
module IANAifType-MIB {
  namespace "http://tail-f.com/ns/mibs/IANAifType-MIB/201703300000Z";
  prefix IANAifType_MIB;
  tailf:id "";
  tailf:snmp-mib-module-name "IANAifType-MIB";
  import tailf-common {
    prefix tailf;
  }

  revision 2017-03-30 {
    description
      "";
  }

  typedef IANAifType {
    type enumeration {
      enum "other" {
        value 1;
      }
      enum "regular1822" {
        value 2;
      }
      enum "hdh1822" {
        value 3;
      }
      enum "ddnX25" {
        value 4;
      }
      enum "rfc877x25" {
        value 5;
      }
      enum "ethernetCsmacd" {
        value 6;
      }
      enum "iso88023Csmacd" {
        value 7;
      }
      enum "iso88024TokenBus" {
        value 8;
      }
      enum "iso88025TokenRing" {
        value 9;
      }
      enum "iso88026Man" {
        value 10;
      }
      enum "starLan" {
        value 11;
      }
      enum "proteon10Mbit" {
        value 12;
      }
      enum "proteon80Mbit" {
        value 13;
      }
      enum "hyperchannel" {
        value 14;
      }
      enum "fddi" {
        value 15;
      }
      enum "lapb" {
        value 16;
      }
      enum "sdlc" {
        value 17;
      }
      enum "ds1" {
        value 18;
      }
      enum "e1" {
        value 19;
      }
      enum "basicISDN" {
        value 20;
      }
      enum "primaryISDN" {
        value 21;
      }
      enum "propPointToPointSerial" {
        value 22;
      }
      enum "ppp" {
        value 23;
      }
      enum "softwareLoopback" {
        value 24;
      }
      enum "eon" {
        value 25;
      }
      enum "ethernet3Mbit" {
        value 26;
      }
      enum "nsip" {
        value 27;
      }
      enum "slip" {
        value 28;
      }
      enum "ultra" {
        value 29;
      }
      enum "ds3" {
        value 30;
      }
      enum "sip" {
        value 31;
      }
      enum "frameRelay" {
        value 32;
      }
      enum "rs232" {
        value 33;
      }
      enum "para" {
        value 34;
      }
      enum "arcnet" {
        value 35;
      }
      enum "arcnetPlus" {
        value 36;
      }
      enum "atm" {
        value 37;
      }
      enum "miox25" {
        value 38;
      }
      enum "sonet" {
        value 39;
      }
      enum "x25ple" {
        value 40;
      }
      enum "iso88022llc" {
        value 41;
      }
      enum "localTalk" {
        value 42;
      }
      enum "smdsDxi" {
        value 43;
      }
      enum "frameRelayService" {
        value 44;
      }
      enum "v35" {
        value 45;
      }
      enum "hssi" {
        value 46;
      }
      enum "hippi" {
        value 47;
      }
      enum "modem" {
        value 48;
      }
      enum "aal5" {
        value 49;
      }
      enum "sonetPath" {
        value 50;
      }
      enum "sonetVT" {
        value 51;
      }
      enum "smdsIcip" {
        value 52;
      }
      enum "propVirtual" {
        value 53;
      }
      enum "propMultiplexor" {
        value 54;
      }
      enum "ieee80212" {
        value 55;
      }
      enum "fibreChannel" {
        value 56;
      }
      enum "hippiInterface" {
        value 57;
      }
      enum "frameRelayInterconnect" {
        value 58;
      }
      enum "aflane8023" {
        value 59;
      }
      enum "aflane8025" {
        value 60;
      }
      enum "cctEmul" {
        value 61;
      }
      enum "fastEther" {
        value 62;
      }
      enum "isdn" {
        value 63;
      }
      enum "v11" {
        value 64;
      }
      enum "v36" {
        value 65;
      }
      enum "g703at64k" {
        value 66;
      }
      enum "g703at2mb" {
        value 67;
      }
      enum "qllc" {
        value 68;
      }
      enum "fastEtherFX" {
        value 69;
      }
      enum "channel" {
        value 70;
      }
      enum "ieee80211" {
        value 71;
      }
      enum "ibm370parChan" {
        value 72;
      }
      enum "escon" {
        value 73;
      }
      enum "dlsw" {
        value 74;
      }
      enum "isdns" {
        value 75;
      }
      enum "isdnu" {
        value 76;
      }
      enum "lapd" {
        value 77;
      }
      enum "ipSwitch" {
        value 78;
      }
      enum "rsrb" {
        value 79;
      }
      enum "atmLogical" {
        value 80;
      }
      enum "ds0" {
        value 81;
      }
      enum "ds0Bundle" {
        value 82;
      }
      enum "bsc" {
        value 83;
      }
      enum "async" {
        value 84;
      }
      enum "cnr" {
        value 85;
      }
      enum "iso88025Dtr" {
        value 86;
      }
      enum "eplrs" {
        value 87;
      }
      enum "arap" {
        value 88;
      }
      enum "propCnls" {
        value 89;
      }
      enum "hostPad" {
        value 90;
      }
      enum "termPad" {
        value 91;
      }
      enum "frameRelayMPI" {
        value 92;
      }
      enum "x213" {
        value 93;
      }
      enum "adsl" {
        value 94;
      }
      enum "radsl" {
        value 95;
      }
      enum "sdsl" {
        value 96;
      }
      enum "vdsl" {
        value 97;
      }
      enum "iso88025CRFPInt" {
        value 98;
      }
      enum "myrinet" {
        value 99;
      }
      enum "voiceEM" {
        value 100;
      }
      enum "voiceFXO" {
        value 101;
      }
      enum "voiceFXS" {
        value 102;
      }
      enum "voiceEncap" {
        value 103;
      }
      enum "voiceOverIp" {
        value 104;
      }
      enum "atmDxi" {
        value 105;
      }
      enum "atmFuni" {
        value 106;
      }
      enum "atmIma" {
        value 107;
      }
      enum "pppMultilinkBundle" {
        value 108;
      }
      enum "ipOverCdlc" {
        value 109;
      }
      enum "ipOverClaw" {
        value 110;
      }
      enum "stackToStack" {
        value 111;
      }
      enum "virtualIpAddress" {
        value 112;
      }
      enum "mpc" {
        value 113;
      }
      enum "ipOverAtm" {
        value 114;
      }
      enum "iso88025Fiber" {
        value 115;
      }
      enum "tdlc" {
        value 116;
      }
      enum "gigabitEthernet" {
        value 117;
      }
      enum "hdlc" {
        value 118;
      }
      enum "lapf" {
        value 119;
      }
      enum "v37" {
        value 120;
      }
      enum "x25mlp" {
        value 121;
      }
      enum "x25huntGroup" {
        value 122;
      }
      enum "transpHdlc" {
        value 123;
      }
      enum "interleave" {
        value 124;
      }
      enum "fast" {
        value 125;
      }
      enum "ip" {
        value 126;
      }
      enum "docsCableMaclayer" {
        value 127;
      }
      enum "docsCableDownstream" {
        value 128;
      }
      enum "docsCableUpstream" {
        value 129;
      }
      enum "a12MppSwitch" {
        value 130;
      }
      enum "tunnel" {
        value 131;
      }
      enum "coffee" {
        value 132;
      }
      enum "ces" {
        value 133;
      }
      enum "atmSubInterface" {
        value 134;
      }
      enum "l2vlan" {
        value 135;
      }
      enum "l3ipvlan" {
        value 136;
      }
      enum "l3ipxvlan" {
        value 137;
      }
      enum "digitalPowerline" {
        value 138;
      }
      enum "mediaMailOverIp" {
        value 139;
      }
      enum "dtm" {
        value 140;
      }
      enum "dcn" {
        value 141;
      }
      enum "ipForward" {
        value 142;
      }
      enum "msdsl" {
        value 143;
      }
      enum "ieee1394" {
        value 144;
      }
      enum "if-gsn" {
        value 145;
      }
      enum "dvbRccMacLayer" {
        value 146;
      }
      enum "dvbRccDownstream" {
        value 147;
      }
      enum "dvbRccUpstream" {
        value 148;
      }
      enum "atmVirtual" {
        value 149;
      }
      enum "mplsTunnel" {
        value 150;
      }
      enum "srp" {
        value 151;
      }
      enum "voiceOverAtm" {
        value 152;
      }
      enum "voiceOverFrameRelay" {
        value 153;
      }
      enum "idsl" {
        value 154;
      }
      enum "compositeLink" {
        value 155;
      }
      enum "ss7SigLink" {
        value 156;
      }
      enum "propWirelessP2P" {
        value 157;
      }
      enum "frForward" {
        value 158;
      }
      enum "rfc1483" {
        value 159;
      }
      enum "usb" {
        value 160;
      }
      enum "ieee8023adLag" {
        value 161;
      }
      enum "bgppolicyaccounting" {
        value 162;
      }
      enum "frf16MfrBundle" {
        value 163;
      }
      enum "h323Gatekeeper" {
        value 164;
      }
      enum "h323Proxy" {
        value 165;
      }
      enum "mpls" {
        value 166;
      }
      enum "mfSigLink" {
        value 167;
      }
      enum "hdsl2" {
        value 168;
      }
      enum "shdsl" {
        value 169;
      }
      enum "ds1FDL" {
        value 170;
      }
      enum "pos" {
        value 171;
      }
      enum "dvbAsiIn" {
        value 172;
      }
      enum "dvbAsiOut" {
        value 173;
      }
      enum "plc" {
        value 174;
      }
      enum "nfas" {
        value 175;
      }
      enum "tr008" {
        value 176;
      }
      enum "gr303RDT" {
        value 177;
      }
      enum "gr303IDT" {
        value 178;
      }
      enum "isup" {
        value 179;
      }
      enum "propDocsWirelessMaclayer" {
        value 180;
      }
      enum "propDocsWirelessDownstream" {
        value 181;
      }
      enum "propDocsWirelessUpstream" {
        value 182;
      }
      enum "hiperlan2" {
        value 183;
      }
      enum "propBWAp2Mp" {
        value 184;
      }
      enum "sonetOverheadChannel" {
        value 185;
      }
      enum "digitalWrapperOverheadChannel" {
        value 186;
      }
      enum "aal2" {
        value 187;
      }
      enum "radioMAC" {
        value 188;
      }
      enum "atmRadio" {
        value 189;
      }
      enum "imt" {
        value 190;
      }
      enum "mvl" {
        value 191;
      }
      enum "reachDSL" {
        value 192;
      }
      enum "frDlciEndPt" {
        value 193;
      }
      enum "atmVciEndPt" {
        value 194;
      }
      enum "opticalChannel" {
        value 195;
      }
      enum "opticalTransport" {
        value 196;
      }
      enum "propAtm" {
        value 197;
      }
      enum "voiceOverCable" {
        value 198;
      }
      enum "infiniband" {
        value 199;
      }
      enum "teLink" {
        value 200;
      }
      enum "q2931" {
        value 201;
      }
      enum "virtualTg" {
        value 202;
      }
      enum "sipTg" {
        value 203;
      }
      enum "sipSig" {
        value 204;
      }
      enum "docsCableUpstreamChannel" {
        value 205;
      }
      enum "econet" {
        value 206;
      }
      enum "pon155" {
        value 207;
      }
      enum "pon622" {
        value 208;
      }
      enum "bridge" {
        value 209;
      }
      enum "linegroup" {
        value 210;
      }
      enum "voiceEMFGD" {
        value 211;
      }
      enum "voiceFGDEANA" {
        value 212;
      }
      enum "voiceDID" {
        value 213;
      }
      enum "mpegTransport" {
        value 214;
      }
      enum "sixToFour" {
        value 215;
        tailf:code-name "IF_TYPE_sixToFour";        
      }
      enum "gtp" {
        value 216;
      }
      enum "pdnEtherLoop1" {
        value 217;
      }
      enum "pdnEtherLoop2" {
        value 218;
      }
      enum "opticalChannelGroup" {
        value 219;
      }
      enum "homepna" {
        value 220;
      }
      enum "gfp" {
        value 221;
      }
      enum "ciscoISLvlan" {
        value 222;
      }
      enum "actelisMetaLOOP" {
        value 223;
      }
      enum "fcipLink" {
        value 224;
      }
      enum "rpr" {
        value 225;
      }
      enum "qam" {
        value 226;
      }
      enum "lmp" {
        value 227;
      }
      enum "cblVectaStar" {
        value 228;
      }
      enum "docsCableMCmtsDownstream" {
        value 229;
      }
      enum "adsl2" {
        value 230;
      }
      enum "macSecControlledIF" {
        value 231;
      }
      enum "macSecUncontrolledIF" {
        value 232;
      }
      enum "aviciOpticalEther" {
        value 233;
      }
      enum "atmbond" {
        value 234;
      }
      enum "voiceFGDOS" {
        value 235;
      }
      enum "mocaVersion1" {
        value 236;
      }
      enum "ieee80216WMAN" {
        value 237;
      }
      enum "adsl2plus" {
        value 238;
      }
      enum "dvbRcsMacLayer" {
        value 239;
      }
      enum "dvbTdm" {
        value 240;
      }
      enum "dvbRcsTdma" {
        value 241;
      }
      enum "x86Laps" {
        value 242;
      }
      enum "wwanPP" {
        value 243;
      }
      enum "wwanPP2" {
        value 244;
      }
      enum "voiceEBS" {
        value 245;
      }
      enum "ifPwType" {
        value 246;
      }
      enum "ilan" {
        value 247;
      }
      enum "pip" {
        value 248;
      }
      enum "aluELP" {
        value 249;
      }
      enum "gpon" {
        value 250;
      }
      enum "vdsl2" {
        value 251;
      }
      enum "capwapDot11Profile" {
        value 252;
      }
      enum "capwapDot11Bss" {
        value 253;
      }
      enum "capwapWtpVirtualRadio" {
        value 254;
      }
      enum "bits" {
        value 255;
      }
      enum "docsCableUpstreamRfPort" {
        value 256;
      }
      enum "cableDownstreamRfPort" {
        value 257;
      }
      enum "vmwareVirtualNic" {
        value 258;
      }
      enum "ieee802154" {
        value 259;
      }
      enum "otnOdu" {
        value 260;
      }
      enum "otnOtu" {
        value 261;
      }
      enum "ifVfiType" {
        value 262;
      }
      enum "g9981" {
        value 263;
      }
      enum "g9982" {
        value 264;
      }
      enum "g9983" {
        value 265;
      }
      enum "aluEpon" {
        value 266;
      }
      enum "aluEponOnu" {
        value 267;
      }
      enum "aluEponPhysicalUni" {
        value 268;
      }
      enum "aluEponLogicalLink" {
        value 269;
      }
      enum "aluGponOnu" {
        value 270;
      }
      enum "aluGponPhysicalUni" {
        value 271;
      }
      enum "vmwareNicTeam" {
        value 272;
      }
      enum "docsOfdmDownstream" {
        value 277;
      }
      enum "docsOfdmaUpstream" {
        value 278;
      }
      enum "gfast" {
        value 279;
      }
      enum "sdci" {
        value 280;
      }
      enum "xboxWireless" {
        value 281;
      }
      enum "fastdsl" {
        value 282;
      }
      enum "docsCableScte55d1FwdOob" {
        value 283;
      }
      enum "docsCableScte55d1RetOob" {
        value 284;
      }
      enum "docsCableScte55d2DsOob" {
        value 285;
      }
      enum "docsCableScte55d2UsOob" {
        value 286;
      }
      enum "docsCableNdf" {
        value 287;
      }
      enum "docsCableNdr" {
        value 288;
      }
      enum "ptm" {
        value 289;
      }
      enum "ghn" {
        value 290;
      }
    }
  }

  typedef IANAtunnelType {
    type enumeration {
      enum "other" {
        value 1;
      }
      enum "direct" {
        value 2;
      }
      enum "gre" {
        value 3;
      }
      enum "minimal" {
        value 4;
      }
      enum "l2tp" {
        value 5;
      }
      enum "pptp" {
        value 6;
      }
      enum "l2f" {
        value 7;
      }
      enum "udp" {
        value 8;
      }
      enum "atmp" {
        value 9;
      }
      enum "msdp" {
        value 10;
      }
      enum "sixToFour" {
        value 11;
        tailf:code-name "TUNNEL_TYPE_sixToFour";
      }
      enum "sixOverFour" {
        value 12;
      }
      enum "isatap" {
        value 13;
      }
      enum "teredo" {
        value 14;
      }
      enum "ipHttps" {
        value 15;
      }
      enum "softwireMesh" {
        value 16;
      }
      enum "dsLite" {
        value 17;
      }
    }
  }
}
