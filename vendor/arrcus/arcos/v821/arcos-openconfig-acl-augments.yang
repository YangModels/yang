module arcos-openconfig-acl-augments {
  yang-version 1.1;
  namespace "http://yang.arrcus.com/arcos/openconfig/acl/augments";
  prefix arc-oc-acl-aug;

  import openconfig-acl {
    prefix oc-acl;
  }

  import iana-if-type {
    prefix ianaift;
  }

  import openconfig-yang-types {
    prefix oc-yang;
  }

  import ietf-inet-types {
    prefix ietf-inet;
  }

  import openconfig-interfaces {
    prefix oc-if;
  }

  import openconfig-if-ethernet {
    prefix oc-eth;
  }

  import openconfig-if-aggregate {
    prefix oc-lag;
  }

  import openconfig-network-instance {
    prefix oc-ni;
  }

  import openconfig-packet-match {
    prefix oc-match;
  }

  import arcos-copp-service-policy {
    prefix arc-copp-svc-pol;
  }

  import ietf-yang-types {
    prefix ietf-yang;
  }

  import arcos-apply-path {
    prefix arc-app-path;
  }

  organization
    "Arrcus, Inc.";

  contact
    "Arrcus, Inc.
     2077 Gateway Place
     Suite 400
     San Jose, CA 95110

     E-mail: yang-support@arrcus.com";

  description
    "This module contains augments for the ACL feature in ArcOS

     Copyright (c) 2016-2023 by Arrcus, Inc.
     All rights reserved.";

  revision 2025-10-02 {
    description
      "added network-instance leaf for bgp v6 flowspec acls";
  }

  revision 2024-04-11 {
    description
      "Added new destination-address-apply-path and source-address-apply-path leaf
       for acl-entry configuration";
  }

  revision 2024-02-01 {
    description
      "Added new target attribute for acl target configuration";
  }

  revision 2023-09-29 {
    description "Created a group for acl-interface-state";
  }

  revision 2023-09-12 {
    description "Display acl-service-policies node based on interface name";
  }

  revision 2023-05-31 {
    description
      "Changed stats leaf from counter64 to zero-based-counter64";
  }

  revision 2023-05-31 {
    description 
      "Added new acl-counter feature for stats aggregation of different ACEs";
  }

  identity REDIRECT {
    base oc-acl:FORWARDING_ACTION;
    description
      "Redirect the packet";
  }

  identity ACL_VPNV4 {
    base oc-acl:ACL_TYPE;
    description
      "IP-layer ACLs with non default VRF/VPN IPv4 addresses";
  }

  identity ACL_VPNV6 {
    base oc-acl:ACL_TYPE;
    description
      "IP-layer ACLs with non default VRF/VPN IPv6 addresses";
  }

  identity ACL_TARGET_ATTRIBUTE {
    description
      "Base identity for ACL target attributes";
  }

  identity ACL_INTF {
    base ACL_TARGET_ATTRIBUTE;
    description
      "Default target attribute";
  }

  identity ACL_PRE_FS {
    base ACL_TARGET_ATTRIBUTE;
    description
      "Pre flowsepc target attribute";
  }

  grouping ipv4-redirect-config {
    description
      "Config of IPv4 redirect action";

    leaf network-instance {
      type oc-ni:network-instance-ref;
      must "not(../cpu)";
      description
        "redirect packet to specified network-instance";
    }

    leaf next-hop {
      type ietf-inet:ipv4-address-no-zone;
      must "not(../cpu)";
      description
        "redirect packet to specified ipv4 nexthop address";
    }

    leaf cpu {
      type empty;
      must "not(../next-hop) or not(../network-instance)";
      description
          "Punt to CPU";

    }
  }

  grouping ipv4-redirect-state {
    description
      "State information of IPv4 redirect action";
  }

  grouping ipv4-redirect-action-top {
    description
      "Grouping for parameters related to ipv4 redirect forwarding action";

    container ipv4-redirect {
      description
        "Container holding parameters related to ipv4 redirect forwarding action";

      container config {
        description
          "Config data";
        uses ipv4-redirect-config;
      }

      container state {
        config false;
        description
          "State information";
        uses ipv4-redirect-config;
        uses ipv4-redirect-state;
      }
    }
  }


  grouping ipv6-redirect-config {
    description
      "Config of IPv6 redirect action";

    leaf network-instance {
      type oc-ni:network-instance-ref;
      must "not(../cpu)";
      description
        "redirect packet to specified network-instance";
    }

    leaf next-hop {
      type ietf-inet:ipv6-address-no-zone;
      must "not(../cpu)";
      description
        "redirect packet to specified ipv6 nexthop address";
    }

    leaf cpu {
      type empty;
      must "not(../next-hop) or not(../network-instance)";
      description
          "Punt to CPU";

    }
  }

  grouping ipv6-redirect-state {
    description
      "State information of IPv6 redirect action";
  }


  grouping ipv6-redirect-action-top {
    description
      "Grouping for parameters related to ipv6 redirect forwarding action";

    container ipv6-redirect {
      description
        "Container holding parameters related to ipv6 redirect forwarding action";

      container config {
        description
          "Config data";
        uses ipv6-redirect-config;
      }

      container state {
        config false;
        description
          "State information";
        uses ipv6-redirect-config;
        uses ipv6-redirect-state;
      }
    }
  }


  grouping interface-acl-sets-top {
    description
      "Top-level grouping for per-interface per-direction ACL data";

    list acl-set {
      key "type";
      description
        "List of per-direction ACLs on the interface";

      leaf type {
        type identityref {
          base oc-acl:ACL_TYPE;
        }
        description
          "Reference to the ACL set type (ACL_IPV4, ACL_IPV6 or ACL_L2)
          applied on the interface direction.";
      }

      leaf set-name {
        type leafref {
          path "/oc-acl:acl/oc-acl:acl-sets" +
               "/oc-acl:acl-set[oc-acl:type=current()/../type]/oc-acl:config" +
               "/oc-acl:name";
        }
        mandatory true;
        description
          "Reference to the ACL set name applied on interface direction";
      }
    }
  }

  grouping acl-service-policies-top {
    description
      "Top-level grouping for per-interface ACL data";

    list acl-service-policies {
      key "direction target-attribute";
      description
        "Direction of traffic the ACL polices take effect on";

      leaf direction {
        type enumeration {
          enum ingress-acl-sets {
            description
              "ACL per-interface policies for incoming traffic";
          }
          enum egress-acl-sets {
            description
              "ACL per-interface policies for outgoing traffic";
          }
        }
      }

      leaf target-attribute {
        type identityref {
          base arc-oc-acl-aug:ACL_TARGET_ATTRIBUTE;
        }
        description
          "Reference to the ACL target attribute (ACL_PRE_FS or ACL_INTF)
          applied on the interface direction.";

        must "derived-from-or-self(current(), 'arc-oc-acl-aug:ACL_INTF') or " + 
             "(derived-from-or-self(current(), 'arc-oc-acl-aug:ACL_PRE_FS') and " + 
             " current()/../direction = 'ingress-acl-sets')" {
          error-message "Pre-flowspec target attribute only allowed on ingress direction";
        }
      }
      uses interface-acl-sets-top;

      container state {
        config false;
        uses interface-acl-sets-top;
      }
    }
  }

  grouping acl-interface-state {
    description
      "State of acl interfaces";
    leaf id {
      type string;
      description 
        "User defined identifier for interface and subinterface";
    }
    
    leaf direction {
      type enumeration {
        enum ingress-acl {
          description
            "ACL per-interface policies for incoming traffic";
        }
        enum egress-acl {
          description
            "ACL per-interface policies for outgoing traffic";
        }
      }
    }

    leaf target-attribute {
      type identityref {
        base arc-oc-acl-aug:ACL_TARGET_ATTRIBUTE;
      }
      description
        "Target specific attribute";
    }
  }

  grouping access-list-entries-top {
    description
      "Access list entries to level container";

    container acl-entries {
      description
        "Access list entries container";

      list acl-entry {
        key "sequence-id";
        description
          "List of ACL entries comprising an ACL set";

        leaf sequence-id {
          type leafref {
            path "../config/sequence-id";
          }
          description
            "references the list key";
        }

        container config {
          description
            "Access list entries config";
          uses oc-acl:access-list-entries-config;
        }

        container state {
          config false;
          description
            "State information for ACL entries";
          uses oc-acl:access-list-entries-config;
          uses oc-acl:access-list-entries-state;
        }

        uses oc-match:ipv4-protocol-fields-top;
        uses oc-match:ipv6-protocol-fields-top;
        uses oc-match:transport-fields-top;
        uses oc-acl:action-top;
      }
    }
  }

  augment "/oc-acl:acl/oc-acl:acl-sets/oc-acl:acl-set" {
    container interfaces {
      config false;
      list interface {
        key "id direction target-attribute";
        description 
          "Interfaces on which a given ACL is applied";
        uses acl-interface-state;

        container state {
          uses acl-interface-state;
        }
      }
    }
  }

  augment "/oc-if:interfaces/oc-if:interface" {
    uses acl-service-policies-top {
      when "((starts-with(current()/oc-if:name, 'loopback')) or " +
           " (starts-with(current()/oc-if:name, 'vlan')) or " +
           " (starts-with(current()/oc-if:name, 'bond')) or " +
           " ((starts-with(current()/oc-if:name, 'swp')) and (boolean(current()/oc-eth:ethernet/oc-eth:config/oc-lag:aggregate-id) != 'true')))";
    }
  }

  augment "/oc-if:interfaces/oc-if:interface/oc-if:subinterfaces/oc-if:subinterface" {
    uses acl-service-policies-top {
      when "((starts-with(current()/../../oc-if:name, 'bond')) or " +
           " ((starts-with(current()/../../oc-if:name, 'swp')) and (boolean(current()/../../oc-eth:ethernet/oc-eth:config/oc-lag:aggregate-id) != 'true')))";
      refine "acl-service-policies/direction" {
        must "current() = 'ingress-acl-sets'" {
          error-message "Egress ACL not supported under subinterfaces";
        }
      }
    }
  }

  augment "/arc-copp-svc-pol:control-plane" {
    uses acl-service-policies-top {
      refine "acl-service-policies/direction" {
        must "current() = 'ingress-acl-sets'" {
          error-message "Egress ACL not supported under control-plane";
        }
      }
      refine "acl-service-policies/target-attribute" {
        must "derived-from-or-self(current(), 'arc-oc-acl-aug:ACL_INTF')" {
          error-message "Only ACL_INTF attribute allowed on control-plane";
        }
      }
    }
  }

  augment "/oc-acl:acl/oc-acl:acl-sets/oc-acl:acl-set/oc-acl:acl-entries" +
          "/oc-acl:acl-entry/oc-acl:state" {
    leaf matched-ingress-packets {
      type ietf-yang:zero-based-counter64;
      description
        "Aggregate count of the number of packets matching the current ACL
        entry on ingress direction accross all interfaces.";
    }
    leaf matched-egress-packets {
      type ietf-yang:zero-based-counter64;
      description
        "Aggregate count of the number of packets matching the current ACL
        entry on egress direction accross all interfaces.";
    }
    leaf matched-ingress-octets {
      type ietf-yang:zero-based-counter64;
      description
        "Aggregate count of the number of octets (bytes) matching the current
        ACL entry on ingress direction accross all interfaces.";
    }
    leaf matched-egress-octets {
      type ietf-yang:zero-based-counter64;
      description
        "Aggregate count of the number of octets (bytes) matching the current
        ACL entry on ingress direction accross all interfaces.";
    }
  }

  augment "/oc-acl:acl/arc-oc-acl-aug:bgp/arc-oc-acl-aug:acl-set" +
          "/arc-oc-acl-aug:acl-entries/arc-oc-acl-aug:acl-entry/arc-oc-acl-aug:state" {
    leaf matched-ingress-packets {
      type ietf-yang:zero-based-counter64;
      description
        "Aggregate count of the number of packets matching the current ACL
        entry on ingress direction accross all interfaces.";
    }
    leaf matched-egress-packets {
      type ietf-yang:zero-based-counter64;
      description
        "Aggregate count of the number of packets matching the current ACL
        entry on egress direction accross all interfaces.";
    }
    leaf matched-ingress-octets {
      type ietf-yang:zero-based-counter64;
      description
        "Aggregate count of the number of octets (bytes) matching the current
        ACL entry on ingress direction accross all interfaces.";
    }
    leaf matched-egress-octets {
      type ietf-yang:zero-based-counter64;
      description
        "Aggregate count of the number of octets (bytes) matching the current
        ACL entry on ingress direction accross all interfaces.";
    }
  }

  augment "/oc-acl:acl" {
    container system-defined {
      config false;
      description
        "Display system defined ACLs.These ACLs can not be re-used or modified";
      list acl-set {
        key "name type";
        description
          "List of ACL sets, each comprising of a list of ACL
          entries";

        uses oc-acl:acl-set-config;
        uses oc-acl:access-list-entries-top;
      }
    }
  }

  augment "/oc-acl:acl" {
    container bgp {
      config false;
      description
        "Display bgp flowspec defined ACLs.These ACLs can not be re-used or modified";
      list acl-set {
        key "name type";
        description
          "List of ACL sets, each comprising of a list of ACL
          entries";

        uses oc-acl:acl-set-config;
        uses access-list-entries-top;
      }
    }
  }

  augment "/oc-acl:acl" {
    container acl-counters {
      description
        "ACL counters container";
      list acl-counter {
        key "name";
        description
          "List of ACL counters";

        leaf name {
          type string;
          description
            "Name of the acl-counter";
        }
        
        container state {
          config false;
          leaf matched-ingress-packets {
            type ietf-yang:zero-based-counter64;
            description
              "Aggregate count of the number of packets matching the current ACL
              entry on ingress direction accross all interfaces.";
          }
          leaf matched-egress-packets {
            type ietf-yang:zero-based-counter64;
            description
              "Aggregate count of the number of packets matching the current ACL
              entry on egress direction accross all interfaces.";
          }
          leaf matched-ingress-octets {
            type ietf-yang:zero-based-counter64;
            description
              "Aggregate count of the number of octets (bytes) matching the current
              ACL entry on ingress direction accross all interfaces.";
          }
          leaf matched-egress-octets {
            type ietf-yang:zero-based-counter64;
            description
              "Aggregate count of the number of octets (bytes) matching the current
              ACL entry on ingress direction accross all interfaces.";
          }
        }
      }
    }
  }

  augment "/oc-acl:acl/oc-acl:acl-sets/oc-acl:acl-set/oc-acl:acl-entries" +
          "/oc-acl:acl-entry/oc-acl:actions" {
    uses ipv4-redirect-action-top {
      when "((current()/oc-acl:config/oc-acl:forwarding-action='arc-oc-acl-aug:REDIRECT')" +
           " and (current()/../../../oc-acl:type = 'oc-acl:ACL_IPV4'))";
    }
  }

  augment "/oc-acl:acl/oc-acl:acl-sets/oc-acl:acl-set/oc-acl:acl-entries" +
          "/oc-acl:acl-entry/oc-acl:actions" {
    uses ipv6-redirect-action-top {
      when "((current()/oc-acl:config/oc-acl:forwarding-action='arc-oc-acl-aug:REDIRECT')" +
           " and (current()/../../../oc-acl:type = 'oc-acl:ACL_IPV6'))";
    }
  }


  augment "/oc-acl:acl/arc-oc-acl-aug:bgp/arc-oc-acl-aug:acl-set" +
          "/arc-oc-acl-aug:acl-entries/arc-oc-acl-aug:acl-entry/arc-oc-acl-aug:actions" {
    uses ipv4-redirect-action-top;
  }

  augment "/oc-acl:acl/arc-oc-acl-aug:bgp/arc-oc-acl-aug:acl-set" +
          "/arc-oc-acl-aug:acl-entries/arc-oc-acl-aug:acl-entry/arc-oc-acl-aug:actions" {
    uses ipv6-redirect-action-top;
  }

  augment "/oc-acl:acl/oc-acl:acl-sets/oc-acl:acl-set" +
          "/oc-acl:acl-entries/oc-acl:acl-entry/oc-acl:state" {
    leaf priority {
      type uint32;
    }
    description "Add priority field for configured aces";
  }

  augment "/oc-acl:acl/oc-acl:acl-sets/oc-acl:acl-set" +
          "/oc-acl:acl-entries/oc-acl:acl-entry/oc-acl:ipv4" +
          "/oc-acl:config" {
    leaf destination-address-apply-path {
      type leafref {
        path "/arc-app-path:apply-paths/arc-app-path:apply-path" +
             "/arc-app-path:config/arc-app-path:name";
      }
    }
    description
      "The name of the apply-path prefix-list learnt by
       apply-path.";
  }

  augment "/oc-acl:acl/oc-acl:acl-sets/oc-acl:acl-set" +
            "/oc-acl:acl-entries/oc-acl:acl-entry/oc-acl:ipv4" +
            "/oc-acl:config" {
    leaf source-address-apply-path {
      type leafref {
        path "/arc-app-path:apply-paths/arc-app-path:apply-path" +
             "/arc-app-path:config/arc-app-path:name";
      }
    }
    description
      "The name of the apply-path prefix-list learnt by
       apply-path.";
  }

  augment "/oc-acl:acl/oc-acl:acl-sets/oc-acl:acl-set" +
          "/oc-acl:acl-entries/oc-acl:acl-entry/oc-acl:ipv4" +
          "/oc-acl:state" {
    leaf destination-address-apply-path {
      type string;
    }
    description
      "The name of the apply-path prefix-list learnt by
       apply-path.";
  }

  augment "/oc-acl:acl/oc-acl:acl-sets/oc-acl:acl-set" +
          "/oc-acl:acl-entries/oc-acl:acl-entry/oc-acl:ipv4" +
          "/oc-acl:state" {
    leaf source-address-apply-path {
      type string;
    }
    description
      "The name of the apply-path prefix-list learnt by
       apply-path.";
  }

  augment "/oc-acl:acl/oc-acl:acl-sets/oc-acl:acl-set" +
          "/oc-acl:acl-entries/oc-acl:acl-entry/oc-acl:ipv6" +
          "/oc-acl:config" {
    leaf destination-address-apply-path {
      type leafref {
        path "/arc-app-path:apply-paths/arc-app-path:apply-path" +
             "/arc-app-path:config/arc-app-path:name";
      }
    }
    description
      "The name of the apply-path prefix-list learnt by
       apply-path.";
  }

  augment "/oc-acl:acl/oc-acl:acl-sets/oc-acl:acl-set" +
          "/oc-acl:acl-entries/oc-acl:acl-entry/oc-acl:ipv6" +
          "/oc-acl:config" {
    leaf source-address-apply-path {
      type leafref {
        path "/arc-app-path:apply-paths/arc-app-path:apply-path" +
             "/arc-app-path:config/arc-app-path:name";
      }
    }
    description
      "The name of the apply-path prefix-list learnt by
       apply-path.";
  }

  augment "/oc-acl:acl/oc-acl:acl-sets/oc-acl:acl-set" +
          "/oc-acl:acl-entries/oc-acl:acl-entry/oc-acl:ipv6" +
          "/oc-acl:state" {
    leaf destination-address-apply-path {
      type string;
    }
    description
      "The name of the apply-path prefix-list learnt by
       apply-path.";
  }

  augment "/oc-acl:acl/oc-acl:acl-sets/oc-acl:acl-set" +
          "/oc-acl:acl-entries/oc-acl:acl-entry/oc-acl:ipv6" +
          "/oc-acl:state" {
    leaf source-address-apply-path {
      type string;
    }
    description
      "The name of the apply-path prefix-list learnt by
       apply-path.";
  }

  augment "/oc-acl:acl/arc-oc-acl-aug:system-defined/arc-oc-acl-aug:acl-set" +
          "/arc-oc-acl-aug:acl-entries/arc-oc-acl-aug:acl-entry/arc-oc-acl-aug:state" {
    leaf priority {
      type uint32;
    }
    description "Add priority field for system-defined aces";
  }

  augment "/oc-acl:acl/arc-oc-acl-aug:bgp/arc-oc-acl-aug:acl-set" +
          "/arc-oc-acl-aug:acl-entries/arc-oc-acl-aug:acl-entry/arc-oc-acl-aug:state" {
    leaf priority {
      type uint32;
    }
    description "Add priority field for bgp aces";
  }

  augment "/oc-acl:acl/oc-acl:acl-sets/oc-acl:acl-set" +
          "/oc-acl:acl-entries/oc-acl:acl-entry/oc-acl:config" {
    leaf acl-counter {
      type leafref {
        path "/oc-acl:acl/arc-oc-acl-aug:acl-counters/arc-oc-acl-aug:acl-counter/arc-oc-acl-aug:name";
      } 
    }
    description "Add acl-counter for configured aces";
  }

  augment "/oc-acl:acl/oc-acl:acl-sets/oc-acl:acl-set" +
          "/oc-acl:acl-entries/oc-acl:acl-entry/oc-acl:state" {
    leaf acl-counter {
      type leafref{
        path "/oc-acl:acl/arc-oc-acl-aug:acl-counters/arc-oc-acl-aug:acl-counter/arc-oc-acl-aug:name";
      }
    }
    description "Add acl-counter for configured aces";
  }

  
  augment "/oc-acl:acl/arc-oc-acl-aug:bgp/arc-oc-acl-aug:acl-set" +
            "/arc-oc-acl-aug:acl-entries/arc-oc-acl-aug:acl-entry" +
            "/arc-oc-acl-aug:ipv4/arc-oc-acl-aug:state" {
    leaf network-instance {
      type oc-ni:network-instance-ref;
      description
        "Match packet from specified network-instance";
    }
  }
  augment "/oc-acl:acl/arc-oc-acl-aug:bgp/arc-oc-acl-aug:acl-set" +
            "/arc-oc-acl-aug:acl-entries/arc-oc-acl-aug:acl-entry" +
            "/arc-oc-acl-aug:ipv6/arc-oc-acl-aug:state" {
    leaf network-instance {
      type oc-ni:network-instance-ref;
      description
        "Match packet from specified network-instance";
    }
  }
}
