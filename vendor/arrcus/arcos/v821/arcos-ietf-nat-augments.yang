module arcos-ietf-nat-augments {
  yang-version 1.1;
  namespace "http://yang.arrcus.com/arcos/ietf/nat/augments";
  prefix arc-ietf-nat-aug;

  import ietf-nat{
    prefix nat;
  }

  import ietf-interfaces {
    prefix if;
    reference
      "RFC 8343: A YANG Data Model for Interface Management";
  }

  import ietf-yang-types {
    prefix yang;
    reference
     "Section 3 of RFC 6991";
  }

  import ietf-inet-types {
    prefix inet;
    reference
      "Section 4 of RFC 6991";
  }

  organization
    "Arrcus, Inc.";

  contact
    "Arrcus, Inc.
     2077 Gateway Place
     Suite 400
     San Jose, CA 95110

     E-mail: yang-support@arrcus.com";

  description
    "This module defines ArcOS deviations to the
     IETF NAT  module.

     Copyright (c) 2016-2021  by Arrcus, Inc.
     All rights reserved.";

  revision 2021-09-24 {
    description "Initial revision";
  }

  grouping nat-state {
    container state {
       config false;

       leaf name {
         type string;
         description "NAT instance name";
       }

       leaf enable {
         type boolean;
         description "NAT instance enable status";
       }

       leaf type {
         type identityref {
           base nat:nat-type;
         }
         description "NAT instance type";
       }

       leaf source-prefixes {
         type string;
         description "NAT instance internal source prefixes";
       }

       leaf external-interfaces {
         type string;
         description "NAT instance external interfaces";
       }

       container mapping-table {
         description
           "NAT mapping table.  Applicable for functions that maintain
            static and/or dynamic mappings, such as NAT44, Destination
            NAT, NAT64, or CLAT.";
         list mapping-entry {
           key "index";
           description
             "NAT mapping entry.";
           uses nat:mapping-entry;
         }
       }

       list policy {

         key "id";
         description
           "NAT parameters for a given instance";

         leaf id {
           type uint32;
           description
             "An identifier of the NAT policy.  It must be unique
              within the NAT instance.";
         }

         leaf external-interface {
           type if:interface-ref;
           description
             "Name of the external interface.";
         }
       }
    }
  }

  augment "/nat:nat/nat:instances/nat:instance" {
     uses nat-state;
  }

  augment "/nat:nat/nat:instances/nat:instance/nat:statistics/nat:traffic-statistics" {
          list mapping-rule {
            config false;
            key "source-prefix external-interface";
            leaf source-prefix {
              type string;
              description "internal source prefixe";
            }
            leaf external-interface {
              type string;
              description "external interface";
            }
            leaf total-packets {
              type yang:zero-based-counter64;
              description "Total number of packets send and recv";
            }
            leaf total-bytes {
              type yang:zero-based-counter64;
              units "bytes";
              description "Total numbe of bytes send and recv";
            }
          }
  }
}
