module arcos-openconfig-packet-match-augments {
  yang-version 1.1;
  namespace "http://yang.arrcus.com/arcos/openconfig/packet-match/augments";
  prefix arc-oc-pkt-match-aug;

  import openconfig-acl {
    prefix oc-acl;
  }

  import arcos-openconfig-acl-augments {
    prefix arc-oc-acl-aug;
  }

  import openconfig-packet-match-types {
    prefix oc-pkt-match-types;
  }

  import arcos-icmp-types {
    prefix arc-icmp-types;
  }

  import arcos-icmpv6-types {
    prefix arc-icmpv6-types;
  }

  import openconfig-vlan-types {
    prefix oc-vlan-types;
  }

  import openconfig-defined-sets {
    prefix oc-sets;
  }

  organization
    "Arrcus, Inc.";

    contact
        "Email: eng@arrcus.com";

  description
    "This module defines augment statements for Arrcus
     implemention of the openconfig-packet-match module.";

  revision 2023-07-28 {
    description
      "Added connection-tracking match for IPv4/IPv6 control plane ACLs";
  }

  revision 2023-05-24 {
    description
      "Extended the IP_PROTOCOL identity to cover additional protocol numbers";
  }

  revision 2023-03-15 {
    description
      "Ability to specify packet-length as a single value or as a range";
  }

  revision 2023-03-02 {
    description
      "Added more-frag and frag-offset-nonzero options for IPv4 match criteria";
  }

  revision 2018-08-14 {
      description "ArcOS release 2.2.1";
  }

  revision 2017-07-10 {
    description
      "Initial Revision
       * Add ICMP type under ipv4 and ipv6 match nodes.
       ";

    reference
      "RFC 6020: YANG - A Data Modeling Language for the
      Network Configuration Protocol (NETCONF)";
  }

  identity IPV6_HOP_HDR {
    base oc-pkt-match-types:IP_PROTOCOL;
    description
      "IPv6 Hop by Hop Header (0)";
  }

  identity IP_EGP {
    base oc-pkt-match-types:IP_PROTOCOL;
    description
      "Exterior Gateway Protocol (8)";
  }

  identity IPV6_ROUTING_HDR {
    base oc-pkt-match-types:IP_PROTOCOL;
    description
      "IPv6 Routing Header (43)";
  }

  identity IPV6_FRAG_HDR {
    base oc-pkt-match-types:IP_PROTOCOL;
    description
      "IPv6 Fragment Header (44)";
  }

  identity IP_ESP {
    base oc-pkt-match-types:IP_PROTOCOL;
    description
      "Encap Security Payload (50)";
  }

  identity IPV6_NONEXT_HDR {
    base oc-pkt-match-types:IP_PROTOCOL;
    description
      "IPv6 No Next Header (59)";
  }

  identity IPV6_DOPTS_HDR {
    base oc-pkt-match-types:IP_PROTOCOL;
    description
      "IPv6 Destination Options Header (60)";
  }

  identity IP_OSPF {
    base oc-pkt-match-types:IP_PROTOCOL;
    description
      "OSPF Protocol (89)";
  }

  identity IP_VRRP  {
    base oc-pkt-match-types:IP_PROTOCOL;
    description
      "VRRP Protocol (112)";
  }

  // ICMP and ICMPv6 fields
  grouping icmp-dst-unreach-code-field-top {
    description
      "Configuration data of ICMP code field when ICMP type is
      Destnation Unreachable.";

    leaf icmp-dst-unreach-code {
      type arc-icmp-types:icmp-dst-unreach-code;

      description
        "ICMP code can be specified when the protocol is IP_ICMP and
        ICMP type is ICMP_DST_UNREACH.";
    }
  }

  grouping icmp-redirect-code-field-top {
    description
      "Configuration data of ICMP code field when ICMP type is Redirect.";

    leaf icmp-redirect-code {
      type arc-icmp-types:icmp-redirect-code;

      description
        "ICMP code can be specified when the protocol is IP_ICMP and
        ICMP type is ICMP_REDIRECT.";
    }
  }

  grouping icmp-router-advert-code-field-top {
    description
      "Configuration data of ICMP code field when ICMP type is
      Router Advertisement.";

    leaf icmp-router-advert-code {
      type arc-icmp-types:icmp-router-advert-code;

      description
        "ICMP code can be specified  when the protocol is IP_ICMP and
        ICMP type is ICMP_ROUTER_ADVERT.";
    }
  }

  grouping icmp-time-exceeded-code-field-top {
    description
      "Configuration data of ICMP code field when ICMP type is
      Time Exceeded.";

    leaf icmp-time-exceeded-code {
      type arc-icmp-types:icmp-time-exceeded-code;

      description
        "ICMP code can be specified when the protocol is IP_ICMP and
        ICMP type is ICMP_TIME_EXCEEDED.";
    }
  }

  grouping icmp-param-problem-code-field-top {
    description
      "Configuration data of ICMP code field when ICMP type is
      Parameter Problem.";

    leaf icmp-param-problem-code {
      type arc-icmp-types:icmp-param-problem-code;

      description
        "ICMP code can be specified when the protocol is IP_ICMP and
        ICMP type is ICMP_PARAM_PROBLEM.";
    }
  }

  grouping icmpv6-dst-unreach-code-field-top {
    description
      "Configuration data of ICMPv6 code field when ICMPv6 type is
      Destnation Unreachable.";

    leaf icmpv6-dst-unreach-code {
      type arc-icmpv6-types:icmpv6-dst-unreach-code;

      description
        "ICMPv6 code can be specified when the protocol is IP_ICMPV6 and
        ICMPv6 type is ICMPV6_DST_UNREACH.";
    }
  }

  grouping icmpv6-time-exceeded-code-field-top {
    description
      "Configuration data of ICMPv6 code field when ICMPv6 type is
      Time Exceeded.";

    leaf icmpv6-time-exceeded-code {
      type arc-icmpv6-types:icmpv6-time-exceeded-code;

      description
        "ICMPv6 code can be specified when the protocol is IP_ICMPV6 and
        ICMPv6 type is ICMPV6_TIME_EXCEEDED.";
    }
  }

  grouping icmpv6-param-problem-code-field-top {
    description
      "Configuration data of ICMPv6 code field when ICMPv6 type is
      Parameter Problem.";

    leaf icmpv6-param-problem-code {
      type arc-icmpv6-types:icmpv6-param-problem-code;

      description
        "ICMPv6 code can be specified when the protocol is IP_ICMPV6 and
        ICMPv6 type is ICMPV6_PARAM_PROBLEM.";
    }
  }

  grouping icmpv6-router-renumber-code-field-top {
    description
      "Configuration data of ICMPv6 code field when ICMPv6 type is
      Router Renumbering.";

    leaf icmpv6-router-renumber-code {
      type arc-icmpv6-types:icmpv6-router-renumber-code;

      description
        "ICMPv6 code can be specified when the protocol is IP_ICMPV6 and
        ICMPv6 type is ICMPV6_ROUTER_RENUMBER.";
    }
  }

  grouping icmpv6-node-info-query-code-field-top {
    description
      "Configuration data of ICMPv6 code field when ICMPv6 type is
      ICMP Node Information Query.";

    leaf icmpv6-node-info-query-code {
      type arc-icmpv6-types:icmpv6-node-info-query-code;

      description
        "ICMPv6 code can be specified when the protocol is IP_ICMPV6 and
        ICMPv6 type is ICMPV6_NODE_INFO_QUERY.";
    }
  }

  grouping icmpv6-node-info-response-code-field-top {
    description
      "Configuration data of ICMPv6 code field when ICMPv6 type is
      ICMP Node Information Response.";

    leaf icmpv6-node-info-response-code {
      type arc-icmpv6-types:icmpv6-node-info-response-code;

      description
        "ICMPv6 code can be specified when the protocol is IP_ICMPV6 and
        ICMPv6 type is ICMPV6_NODE_INFO_RESPONSE.";
    }
  }

  grouping icmp-type-field-top {
    description
      "Configuration data of ICMP type field.";

    leaf icmp-type {
      type arc-icmp-types:icmp-type;

      description
        "ICMP type can be specified when protocol typep is IP_ICMP.";
    }
  }

  grouping icmpv6-type-field-top {
    description
      "Configuration data of ICMPv6 type field.";

    leaf icmpv6-type {
      type arc-icmpv6-types:icmpv6-type;

      description
        "ICMPv6 type can be specified when protocol typep is IP_ICMPV6.";
    }
  }

  grouping icmp-type-code-fields-top {
    uses icmp-type-field-top {
      when "oc-acl:protocol = 'oc-pkt-match-types:IP_ICMP'" {
        description
          "Only allow ICMP type to be configured when the protocol is ICMP.";
      }
    }

    uses icmp-dst-unreach-code-field-top {
      when "oc-acl:protocol = 'oc-pkt-match-types:IP_ICMP' and " +
        "icmp-type = 'arc-icmp-types:ICMP_DST_UNREACH'" {
        description
          "Only allow ICMP Destination Unreachable code to be configured
          when the ICMP type is ICMP_DST_UNREACH.";
      }
    }

    uses icmp-redirect-code-field-top {
      when "oc-acl:protocol = 'oc-pkt-match-types:IP_ICMP' and " +
        "icmp-type = 'arc-icmp-types:ICMP_REDIRECT'" {
        description
          "Only allow ICMP Redirect code to be configured when the
          ICMP type is ICMP_REDIRECT.";
      }
    }

    uses icmp-router-advert-code-field-top {
      when "oc-acl:protocol = 'oc-pkt-match-types:IP_ICMP' and " +
        "icmp-type = 'arc-icmp-types:ICMP_ROUTER_ADVERT'" {
        description
          "Only allow ICMP Router Advertisement code to be configured
          when the ICMP type is ICMP_ROUTER_ADVERT.";
      }
    }

    uses icmp-time-exceeded-code-field-top {
      when "oc-acl:protocol = 'oc-pkt-match-types:IP_ICMP' and " +
        "icmp-type = 'arc-icmp-types:ICMP_TIME_EXCEEDED'" {
        description
          "Only allow ICMP Time Exceeded code to be configured when the
          ICMP type is ICMP_TIME_EXCEEDED.";
      }
    }

    uses icmp-param-problem-code-field-top {
      when "oc-acl:protocol = 'oc-pkt-match-types:IP_ICMP' and " +
        "icmp-type = 'arc-icmp-types:ICMP_PARAM_PROBLEM'" {
        description
          "Only allow ICMP Parameter Problem code to be configured
          when the ICMP type is ICMP_PARAM_PROBLEM.";
      }
    }
  }

  grouping icmpv6-type-code-fields-top {
    uses icmpv6-type-field-top {
      when "oc-acl:protocol = 'oc-pkt-match-types:IP_ICMPV6'" {
        description
          "Only allow ICMPv6 type to be configured when the protocol
          is ICMPv6.";
      }
    }

    uses icmpv6-dst-unreach-code-field-top {
      when "oc-acl:protocol = 'oc-pkt-match-types:IP_ICMPV6' and " +
        "icmpv6-type = 'arc-icmpv6-types:ICMPV6_DST_UNREACH'" {
        description
          "Only allow ICMPv6 Destination Unreachable code to be configured
          when the ICMPv6 type is ICMPV6_DST_UNREACH.";
      }
    }

    uses icmpv6-time-exceeded-code-field-top {
      when "oc-acl:protocol = 'oc-pkt-match-types:IP_ICMPV6' and " +
        "icmpv6-type = 'arc-icmpv6-types:ICMPV6_TIME_EXCEEDED'" {
        description
          "Only allow ICMPv6 Time Exceeded code to be configured when the
          ICMPv6 type is ICMPV6_TIME_EXCEEDED.";
      }
    }

    uses icmpv6-param-problem-code-field-top {
      when "oc-acl:protocol = 'oc-pkt-match-types:IP_ICMPV6' and " +
        "icmpv6-type = 'arc-icmpv6-types:ICMPV6_PARAM_PROBLEM'" {
        description
          "Only allow ICMPv6 Parameter Problem code to be configured
          when the ICMPv6 type is ICMPV6_PARAM_PROBLEM.";
      }
    }

    uses icmpv6-router-renumber-code-field-top {
      when "oc-acl:protocol = 'oc-pkt-match-types:IP_ICMPV6' and " +
        "icmpv6-type = 'arc-icmpv6-types:ICMPV6_ROUTER_RENUMBER'" {
        description
          "Only allow ICMPv6 Router Renumbering code to be configured
          when the ICMPv6 type is ICMPV6_ROUTER_RENUMBER.";
      }
    }

   uses icmpv6-node-info-query-code-field-top {
      when "oc-acl:protocol = 'oc-pkt-match-types:IP_ICMPV6' and " +
        "icmpv6-type = 'arc-icmpv6-types:ICMPV6_NODE_INFO_QUERY'" {
        description
          "Only allow ICMPv6 Node Information Query code to be configured
          when the ICMPv6 type is ICMPV6_NODE_INFO_QUERY.";
      }
    }

   uses icmpv6-node-info-response-code-field-top {
      when "oc-acl:protocol = 'oc-pkt-match-types:IP_ICMPV6' and " +
        "icmpv6-type = 'arc-icmpv6-types:ICMPV6_NODE_INFO_RESPONSE'" {
        description
          "Only allow ICMPv6 Node Information Response code to be configured
          when the ICMPv6 type is ICMPV6_NODE_INFO_RESPONSE.";
      }
    }
  }


  grouping ip-packet-length {
    description "Match attribute for ip packet length";

    leaf packet-length {
      type union {
        type uint16;
        type string {
          pattern '(6[0-5][0-5][0-3][0-5]|[0-5]?[0-9]?[0-9]?[0-9]?' +
            '[0-9]?)\.\.(6[0-5][0-5][0-3][0-5]|[0-5]?[0-9]?[0-9]?' +
            '[0-9]?[0-9]?)';
        }
      }
      description "IP packet length (single value or as a range)";
    }
  }

  grouping eth-vlan-id {
    description "Match attribute for vlan id";

    leaf vlan-id {
      type union {
        type oc-vlan-types:vlan-id;
        type oc-vlan-types:vlan-range;
      }
      description "Vlan id (single value or a range) used as a ethernet qualifier";
    }
  }

  augment "/oc-acl:acl/oc-acl:acl-sets/oc-acl:acl-set/oc-acl:acl-entries" +
          "/oc-acl:acl-entry/oc-acl:ipv4/oc-acl:config" {
    uses ip-packet-length;
  }

  augment "/oc-acl:acl/oc-acl:acl-sets/oc-acl:acl-set/oc-acl:acl-entries" +
          "/oc-acl:acl-entry/oc-acl:ipv4/oc-acl:config" {
    uses icmp-type-code-fields-top;
  }

  augment "/oc-acl:acl/oc-acl:acl-sets/oc-acl:acl-set/oc-acl:acl-entries" +
          "/oc-acl:acl-entry/oc-acl:ipv6/oc-acl:config" {
    uses ip-packet-length;
  }

  augment "/oc-acl:acl/oc-acl:acl-sets/oc-acl:acl-set/oc-acl:acl-entries" +
          "/oc-acl:acl-entry/oc-acl:ipv6/oc-acl:config" {
    uses icmpv6-type-code-fields-top;
  }

  augment "/oc-acl:acl/oc-acl:acl-sets/oc-acl:acl-set/oc-acl:acl-entries" +
          "/oc-acl:acl-entry/oc-acl:ipv4/oc-acl:state" {
    uses ip-packet-length;
  }

  augment "/oc-acl:acl/oc-acl:acl-sets/oc-acl:acl-set/oc-acl:acl-entries" +
          "/oc-acl:acl-entry/oc-acl:ipv4/oc-acl:state" {
    uses icmp-type-code-fields-top;
  }

  augment "/oc-acl:acl/oc-acl:acl-sets/oc-acl:acl-set/oc-acl:acl-entries" +
          "/oc-acl:acl-entry/oc-acl:ipv6/oc-acl:state" {
    uses ip-packet-length;
  }

  augment "/oc-acl:acl/oc-acl:acl-sets/oc-acl:acl-set/oc-acl:acl-entries" +
          "/oc-acl:acl-entry/oc-acl:ipv6/oc-acl:state" {
    uses icmpv6-type-code-fields-top;
  }

  augment "/oc-acl:acl/arc-oc-acl-aug:system-defined/arc-oc-acl-aug:acl-set" +
          "/arc-oc-acl-aug:acl-entries/arc-oc-acl-aug:acl-entry/arc-oc-acl-aug:ipv4/arc-oc-acl-aug:state" {
    uses icmp-type-field-top;
    uses icmp-dst-unreach-code-field-top;
    uses icmp-redirect-code-field-top;
    uses icmp-router-advert-code-field-top;
    uses icmp-time-exceeded-code-field-top;
    uses icmp-param-problem-code-field-top;
  }

  augment "/oc-acl:acl/arc-oc-acl-aug:system-defined/arc-oc-acl-aug:acl-set" +
          "/arc-oc-acl-aug:acl-entries/arc-oc-acl-aug:acl-entry/arc-oc-acl-aug:ipv6/arc-oc-acl-aug:state" {
    uses icmpv6-type-field-top;
    uses icmpv6-dst-unreach-code-field-top;
    uses icmpv6-time-exceeded-code-field-top;
    uses icmpv6-param-problem-code-field-top;
    uses icmpv6-router-renumber-code-field-top;
    uses icmpv6-node-info-query-code-field-top;
    uses icmpv6-node-info-response-code-field-top;
  }

  augment "/oc-acl:acl/arc-oc-acl-aug:bgp/arc-oc-acl-aug:acl-set" +
          "/arc-oc-acl-aug:acl-entries/arc-oc-acl-aug:acl-entry/arc-oc-acl-aug:ipv4/arc-oc-acl-aug:state" {
    uses ip-packet-length;
    uses icmp-type-field-top;
    uses icmp-dst-unreach-code-field-top;
    uses icmp-redirect-code-field-top;
    uses icmp-router-advert-code-field-top;
    uses icmp-time-exceeded-code-field-top;
    uses icmp-param-problem-code-field-top;
  }

  augment "/oc-acl:acl/arc-oc-acl-aug:bgp/arc-oc-acl-aug:acl-set" +
          "/arc-oc-acl-aug:acl-entries/arc-oc-acl-aug:acl-entry/arc-oc-acl-aug:ipv6/arc-oc-acl-aug:state" {
    uses ip-packet-length;
    uses icmpv6-type-field-top;
    uses icmpv6-dst-unreach-code-field-top;
    uses icmpv6-time-exceeded-code-field-top;
    uses icmpv6-param-problem-code-field-top;
    uses icmpv6-router-renumber-code-field-top;
    uses icmpv6-node-info-query-code-field-top;
    uses icmpv6-node-info-response-code-field-top;
  }

  augment "/oc-acl:acl/oc-acl:acl-sets/oc-acl:acl-set/oc-acl:acl-entries" +
          "/oc-acl:acl-entry/oc-acl:l2/oc-acl:config" {
    uses eth-vlan-id;
  }

  augment "/oc-acl:acl/oc-acl:acl-sets/oc-acl:acl-set/oc-acl:acl-entries" +
          "/oc-acl:acl-entry/oc-acl:l2/oc-acl:state" {
    uses eth-vlan-id;
  }

  // IP Prefix list support
  grouping ipv4-prefix-list-field-top {
    leaf source-address-prefix-set {
      description
        "Reference to a IPv4 address prefix Set to match the source address";

      type leafref {
        path "/oc-sets:defined-sets/oc-sets:ipv4-prefix-sets/oc-sets:ipv4-prefix-set/oc-sets:name";
      }
    }

    leaf destination-address-prefix-set {
      description
        "Reference to a IPv4 address prefix Set to match the destination address";

      type leafref {
        path "/oc-sets:defined-sets/oc-sets:ipv4-prefix-sets/oc-sets:ipv4-prefix-set/oc-sets:name";
      }
    }
  }

  grouping ipv6-prefix-list-field-top {
    leaf source-address-prefix-set {
      description
        "Reference to a IPv6 address prefix Set to match the source address";

      type leafref {
        path "/oc-sets:defined-sets/oc-sets:ipv6-prefix-sets/oc-sets:ipv6-prefix-set/oc-sets:name";
      }
    }

    leaf destination-address-prefix-set { 
      description
        "Reference to a IPv6 address prefix Set to match the destination address";

      type leafref {
        path "/oc-sets:defined-sets/oc-sets:ipv6-prefix-sets/oc-sets:ipv6-prefix-set/oc-sets:name";
      }
    }
  }
  
  grouping ipv4-frag-top {
    description "Match attribute for ipv4 fragmentation";

    leaf more-frag {
      type boolean;
      description 
        "Matches when more-frag flag is set (first and intermediate pkts) in the IPv4 header";
    }

    leaf frag-offset-nonzero {
      type boolean;
      description 
        "Matches when frag-offset field is non-zero (intermediate and last pkt) in the IPv4 header";
    }
  }

  grouping conn-track-top {
    description "Match attribute for connection tracking (applicable for linux acls)";

    leaf connection-tracking {
      type empty;
      description
        "When set, this leaf enables the matching of packets received in response to connections initiated by the switch";
    }
  }

  augment "/oc-acl:acl/oc-acl:acl-sets/oc-acl:acl-set/oc-acl:acl-entries" +
          "/oc-acl:acl-entry/oc-acl:ipv4/oc-acl:config" {
    uses ipv4-prefix-list-field-top;
  }

  augment "/oc-acl:acl/oc-acl:acl-sets/oc-acl:acl-set/oc-acl:acl-entries" +
          "/oc-acl:acl-entry/oc-acl:ipv4/oc-acl:state" {
    uses ipv4-prefix-list-field-top;
  }
  augment "/oc-acl:acl/oc-acl:acl-sets/oc-acl:acl-set/oc-acl:acl-entries" +
          "/oc-acl:acl-entry/oc-acl:ipv6/oc-acl:config" {
    uses ipv6-prefix-list-field-top;
  }

  augment "/oc-acl:acl/oc-acl:acl-sets/oc-acl:acl-set/oc-acl:acl-entries" +
          "/oc-acl:acl-entry/oc-acl:ipv6/oc-acl:state" {
    uses ipv6-prefix-list-field-top;
  }

  augment "/oc-acl:acl/arc-oc-acl-aug:system-defined/arc-oc-acl-aug:acl-set" +
          "/arc-oc-acl-aug:acl-entries/arc-oc-acl-aug:acl-entry/arc-oc-acl-aug:ipv4/arc-oc-acl-aug:state" {
    uses ipv4-prefix-list-field-top;
  }

  augment "/oc-acl:acl/arc-oc-acl-aug:system-defined/arc-oc-acl-aug:acl-set" +
          "/arc-oc-acl-aug:acl-entries/arc-oc-acl-aug:acl-entry/arc-oc-acl-aug:ipv6/arc-oc-acl-aug:state" {
    uses ipv6-prefix-list-field-top;
  }

  augment "/oc-acl:acl/arc-oc-acl-aug:bgp/arc-oc-acl-aug:acl-set" +
          "/arc-oc-acl-aug:acl-entries/arc-oc-acl-aug:acl-entry/arc-oc-acl-aug:ipv4/arc-oc-acl-aug:state" {
    uses ipv4-prefix-list-field-top;
  }

  augment "/oc-acl:acl/arc-oc-acl-aug:bgp/arc-oc-acl-aug:acl-set" +
          "/arc-oc-acl-aug:acl-entries/arc-oc-acl-aug:acl-entry/arc-oc-acl-aug:ipv6/arc-oc-acl-aug:state" {
    uses ipv6-prefix-list-field-top;
  }

  augment "/oc-acl:acl/oc-acl:acl-sets/oc-acl:acl-set/oc-acl:acl-entries" +
          "/oc-acl:acl-entry/oc-acl:ipv4/oc-acl:config" {
    uses ipv4-frag-top;
  }

  augment "/oc-acl:acl/oc-acl:acl-sets/oc-acl:acl-set/oc-acl:acl-entries" +
          "/oc-acl:acl-entry/oc-acl:ipv4/oc-acl:state" {
    uses ipv4-frag-top;
  }

  augment "/oc-acl:acl/oc-acl:acl-sets/oc-acl:acl-set/oc-acl:acl-entries" +
          "/oc-acl:acl-entry/oc-acl:ipv4/oc-acl:config" {
    uses conn-track-top;
  }

  augment "/oc-acl:acl/oc-acl:acl-sets/oc-acl:acl-set/oc-acl:acl-entries" +
          "/oc-acl:acl-entry/oc-acl:ipv4/oc-acl:state" {
    uses conn-track-top;
  }
  augment "/oc-acl:acl/oc-acl:acl-sets/oc-acl:acl-set/oc-acl:acl-entries" +
          "/oc-acl:acl-entry/oc-acl:ipv6/oc-acl:config" {
    uses conn-track-top;
  }

  augment "/oc-acl:acl/oc-acl:acl-sets/oc-acl:acl-set/oc-acl:acl-entries" +
          "/oc-acl:acl-entry/oc-acl:ipv6/oc-acl:state" {
    uses conn-track-top;
  }
}
