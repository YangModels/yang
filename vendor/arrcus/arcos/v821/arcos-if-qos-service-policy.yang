module arcos-if-qos-service-policy {
  yang-version 1.1;
  namespace "http://yang.arrcus.com/arcos/interface/qos/service-policy";
  prefix arc-if-qos-svc-pol;

  import ietf-yang-types {
    prefix yang;
  }

  import arcos-policy {
    prefix arc-pol;
  }
  import arcos-policy-action {
    prefix arc-pol-actn;
  }
  import arcos-service-policy {
    prefix arc-svc-pol;
  }
  import arcos-qos {
    prefix arc-qos;
  }
  import arcos-qos-policy {
    prefix arc-qos-pol;
  }
  import arcos-qos-random-detect {
    prefix arc-qos-red;
  }
  import arcos-if-qos {
    prefix arc-if-qos;
  }
  import iana-if-type {
    prefix ianaift;
  }
  import openconfig-interfaces {
    prefix oc-if;
  }
  import openconfig-if-ethernet {
    prefix oc-eth;
  }
  import openconfig-if-aggregate {
    prefix oc-lag;
  }
  import arcos-platform {
    prefix arc-platform;
  }
  import openconfig-system {
    prefix oc-sys;
  }
  import arcos-openconfig-system-augments {
    prefix arc-oc-sys-aug;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for qos specific policy instance on interfaces;
     Copyright (c) 2016-2023 by Arrcus, Inc.
     All rights reserved.";
     
  revision 2025-09-25 {
    description "Added compensation support if spolicy";
  }

  revision 2024-11-07 {
    description "Modified the 'when' clause to ensure that the condition considers additional cases";
  }

  revision 2024-03-22 {
    description "added queue-stats-top grouping under subinterface policy classifier state";
  }

  revision 2024-03-04 {
    description "added match-packets, match-bytes, offered-rate, dropped-rate to queue-stats-top grouping. Modified offered-rate, dropped-rate type to uint32";
  }

  revision 2024-02-28 {
    description "moved the leafs in queue-stats-top grouping inside the counters container and added queue-sizebytes and queue-sizecount";
  }
  
  revision 2023-09-12 {
    description "Display qos service policy based on interface name";
  }

  revision 2023-05-05 {
    description
      "Enabled service policies to be attached on egress of subinterfaces for DNX";
  }
  grouping queue-stats-top {
    container counters{

      leaf match-packets {
        type yang:zero-based-counter64;
        description "Number of packets matched";
      }

      leaf match-bytes {
        type yang:zero-based-counter64;
        description "Number of bytes matched";
      }

      leaf offered-rate {
        type uint32;
        units "bps";
        description
          "Total offered rate ; calculated from matched byte counts from the classifier";
      }

      leaf dropped-rate {
        type uint32;
        units "bps";
        description
          "Total dropped rate ; calculated from queue-dropcount";
      }

      leaf queue-txcount {
        type yang:zero-based-counter64;
        description
          "Number of packets successfully transmitted out of a queue";
      }

      leaf queue-txbytes {
        type yang:zero-based-counter64;
        description
          "Number of bytes successfully transmitted out of a queue";
      }

      leaf queue-dropcount {
        type yang:zero-based-counter64;
        description
          "Number of packets dropped from a queue.
          Drops could be as a result of dropping discipline or
          could be as a result of unavailabilty of buffers";
      }

      leaf queue-dropbytes {
        type yang:zero-based-counter64;
        description
          "Number of bytes dropped from a queue.
          Drops could be as a result of dropping discipline or
          could be as a result of unavailabilty of buffers";
      }

      leaf queue-sizebytes {
        type yang:gauge64;
        description
          "Number of bytes in the queue.";
      }

      leaf queue-sizecount {
        type yang:gauge64;
        description
          "Number of packets in the queue.";
      }

      leaf egress-policer-match-packets {
        type yang:zero-based-counter64;
        description "Number of packets matched by egress policer if any";
      }

      leaf egress-policer-match-bytes {
        type yang:zero-based-counter64;
        description "Number of bytes matched by egress policer if any";
      }

      leaf egress-policer-offered-rate {
        type uint32;
        units "bps";
        description
          "Total egress policer offered rate ; calculated from egress policer matched byte counts from the classifier";
      }

      leaf egress-policer-dropped-rate {
        type uint32;
        units "bps";
        description
          "Total egress policer dropped rate ; caclulated from egress-dropqueue-dropcount";
      }

    }
  }


  augment "/oc-if:interfaces/oc-if:interface"
        + "/arc-if-qos:qos/service-policies/service-policy" {
    uses arc-pol:policy-classifiers-state-top;
  }
  augment "/oc-if:interfaces/oc-if:interface/oc-if:subinterfaces/oc-if:subinterface"
        + "/arc-if-qos:qos/service-policies/service-policy" {
    uses arc-pol:policy-classifiers-state-top;
  }

  augment "/oc-if:interfaces/oc-if:interface"
        + "/arc-if-qos:qos/service-policies/service-policy/classifiers/classifier"
        + "/actions/action" {
    uses arc-qos-pol:rate-min-top;
  }

  augment "/oc-if:interfaces/oc-if:interface"
        + "/arc-if-qos:qos/service-policies/service-policy/classifiers/classifier"
        + "/actions/action" {
    uses arc-qos-pol:rate-max-top;
  }

  augment "/oc-if:interfaces/oc-if:interface"
        + "/arc-if-qos:qos/service-policies/service-policy/classifiers/classifier"
        + "/actions/action" {
    uses arc-qos-pol:rate-excess-top;
  }

  augment "/oc-if:interfaces/oc-if:interface"
        + "/arc-if-qos:qos/service-policies/service-policy/classifiers/classifier"
        + "/actions/action" {
    uses arc-qos-pol:priority-top;
  }

  augment "/oc-if:interfaces/oc-if:interface"
        + "/arc-if-qos:qos/service-policies/service-policy/classifiers/classifier"
        + "/state" {
    uses queue-stats-top;
  }

  augment "/oc-if:interfaces/oc-if:interface/oc-if:subinterfaces/oc-if:subinterface"
        + "/arc-if-qos:qos/service-policies/service-policy/classifiers/classifier"
        + "/state" {
    uses queue-stats-top;
  }


  augment "/oc-if:interfaces/oc-if:interface"
        + "/arc-if-qos:qos/service-policies/service-policy/classifiers/classifier"
        + "/actions/action" {
    uses arc-pol-actn:mark-top;
  }
  augment "/oc-if:interfaces/oc-if:interface/oc-if:subinterfaces/oc-if:subinterface"
        + "/arc-if-qos:qos/service-policies/service-policy/classifiers/classifier"
        + "/actions/action" {
    uses arc-pol-actn:mark-top;
  }

  augment "/oc-if:interfaces/oc-if:interface"
        + "/arc-if-qos:qos/service-policies/service-policy/classifiers/classifier"
        + "/actions/action/mark/state" {
    uses arc-pol-actn:mark-local-tc-top;
  }
  augment "/oc-if:interfaces/oc-if:interface/oc-if:subinterfaces/oc-if:subinterface"
        + "/arc-if-qos:qos/service-policies/service-policy/classifiers/classifier"
        + "/actions/action/mark/state" {
    uses arc-pol-actn:mark-local-tc-top;
  }

  augment "/oc-if:interfaces/oc-if:interface"
        + "/arc-if-qos:qos/service-policies/service-policy/classifiers/classifier"
        + "/actions/action/mark/state" {
    uses arc-pol-actn:mark-local-tc-drop-precedence-top;
  }
  augment "/oc-if:interfaces/oc-if:interface/oc-if:subinterfaces/oc-if:subinterface"
        + "/arc-if-qos:qos/service-policies/service-policy/classifiers/classifier"
        + "/actions/action/mark/state" {
    uses arc-pol-actn:mark-local-tc-drop-precedence-top;
  }

  augment "/oc-if:interfaces/oc-if:interface"
        + "/arc-if-qos:qos/service-policies/service-policy/classifiers/classifier"
        + "/actions/action" {
    uses arc-pol-actn:police-top;
  }
  augment "/oc-if:interfaces/oc-if:interface/oc-if:subinterfaces/oc-if:subinterface"
        + "/arc-if-qos:qos/service-policies/service-policy/classifiers/classifier"
        + "/actions/action" {
    uses arc-pol-actn:police-top;
  }

  augment "/oc-if:interfaces/oc-if:interface"
        + "/arc-if-qos:qos/service-policies/service-policy/classifiers/classifier"
        + "/actions/action/police/state" {
    uses arc-pol-actn:police-stats-top;
  }
  augment "/oc-if:interfaces/oc-if:interface/oc-if:subinterfaces/oc-if:subinterface"
        + "/arc-if-qos:qos/service-policies/service-policy/classifiers/classifier"
        + "/actions/action/police/state" {
    uses arc-pol-actn:police-stats-top;
  }

  augment "/oc-if:interfaces/oc-if:interface"
        + "/arc-if-qos:qos/service-policies/service-policy/classifiers/classifier"
        + "/actions/action" {
    uses arc-qos-red:random-detect-instance-top;
  }

  augment "/oc-if:interfaces/oc-if:interface/arc-if-qos:qos" {
    uses arc-svc-pol:service-policies-top {
      when "((current()/../oc-if:name != 'ma1') and "
         + "((starts-with(current()/../oc-if:name, 'bond')) or "
         + " ((starts-with(current()/../oc-if:name, 'vlan') and "
         + " (/arc-platform:platform/arc-platform:family = 'arc-platform:BROADCOM_DNX'))) or "
         + "((starts-with(current()/../oc-if:name, 'swp')) and "
         + "(boolean(current()/../oc-eth:ethernet/oc-eth:config/oc-lag:aggregate-id) != 'true'))))";

      refine "service-policies/service-policy/direction" {
        must "(current() = 'EGRESS') or "
           + "(/arc-platform:platform/arc-platform:family = 'arc-platform:BROADCOM_DNX') or "
           + "(/arc-platform:platform/arc-platform:family = 'arc-platform:BROADCOM_XGS') or "
           + "(/arc-platform:platform/arc-platform:deployment-type = 'arc-platform:DISTRIBUTED') or "
           + "(/oc-sys:system/arc-oc-sys-aug:cli/arc-oc-sys-aug:config/arc-oc-sys-aug:unhide-unsupported-cli = 'true')" {
          error-message "Ingress qos policies not supported";
        }
      }
    }

    description
      "Augmenting policy service instance list under an interface";
  }

  augment "/oc-if:interfaces/oc-if:interface/oc-if:subinterfaces/oc-if:subinterface/arc-if-qos:qos" {
    uses arc-svc-pol:service-policies-top {
      when "((starts-with(current()/../../../oc-if:name, 'bond')) or "
         + " (starts-with(current()/../../../oc-if:name, 'vlan')) or "
         + " ((starts-with(current()/../../../oc-if:name, 'swp')) and (boolean(current()/../../../oc-eth:ethernet/oc-eth:config/oc-lag:aggregate-id) != 'true'))) and "
         + "((/arc-platform:platform/arc-platform:family = 'arc-platform:BROADCOM_DNX') or "
         + " (/arc-platform:platform/arc-platform:deployment-type = 'arc-platform:DISTRIBUTED') or "
         + " (/oc-sys:system/arc-oc-sys-aug:cli/arc-oc-sys-aug:config/arc-oc-sys-aug:unhide-unsupported-cli = 'true'))" {
      }
    }
  }

  augment "/oc-if:interfaces/oc-if:interface"
        + "/arc-if-qos:qos/service-policies/service-policy/classifiers/classifier"
        + "/actions/action" {
    uses arc-qos-pol:compensation-top;
  }
}
