module arcos-bgp-types {
  yang-version 1.1;
  namespace "http://yang.arrcus.com/arcos/bgp/types";
  prefix arc-bgp-types;

  import ietf-inet-types {
    prefix inet;
  }

  import openconfig-interfaces {
    prefix oc-if;
  }

  organization
    "Arrcus, Inc.";

  contact
    "Arrcus, Inc.
     2077 Gateway Place
     Suite 400
     San Jose, CA 95110
     E-mail: yang-support@arrcus.com";

  description
    "This module defines Arrcus additions
     to the BGP data types.

     Copyright (c) 2016-2023 by Arrcus, Inc.
     All rights reserved.";

  revision 2024-02-15 {
    description
      "EVPN-VPWS Interface State-Machine States and Events";
  }

  revision 2023-09-29 {
    description "Add route-type defintions for MUP";
  }

  revision 2019-08-20 {
    description "ArcOS 3.3.1";
  }

  typedef bgp-route-refresh-type {
    type enumeration {
      enum in {
        description
          "BGP neighbor inbound route refresh";
      }
      enum out {
        description
          "BGP neighbor outbound route refresh";
      }
    }
  }

  typedef bgp-next-hop-type {
    type union {
      type enumeration {
        enum SELF {
          description
            "Special designation for local router's own address,
             i.e next-hop-self";
        }
        enum UNCHANGED {
          description
            "Special designation to not change the next-hop when
             advertising to the remote-peer i.e next-hop-unchanged";
        }
      }
    }
    description
      "Type definition for specifying next-hop";
  }

  typedef bgp-mup-known-route-type {
    type enumeration {
      enum MUP_ISD {
        value 1;
        description
          "MUP Interwork Segment Discovery route type";
      }
      enum MUP_DSD {
        value 2;
        description
          "MUP Direct Segment Discovery route type";
      }
      enum MUP_ST1 {
        value 3;
        description
          "MUP Type-1 Session Transformed route type";
      }
      enum MUP_ST2 {
        value 4;
        description
          "MUP Type-2 Session Transformed route type";
      }
    }
  }

  typedef bgp-mup-route-type {
    type union {
      type bgp-mup-known-route-type;
      type uint16;
    }
    description
      "BGP MUP route types";
  }

  typedef bgp-capability-state {
    type enumeration {
      enum UNNEGOTIABLE {
        description
          "Capability sent but not received OR not sent but received";
      }
      enum NEGOTIATED {
        description
          "Capability sent and received";
      }
    }
  }

  typedef srv6-tunnel-endpoint-type {
    type enumeration {
      enum INGRESS {
        description
          "SRv6 ingress tunnel endpoint";
      }
      enum EGRESS {
        description
          "SRv6 egress tunnel endpoint";
      }
      enum NONE {
        description
          "Neither an SRv6 ingress nor egress tunnel endpoint";
      }
    }
  }

  typedef srv6-checksum-type {
    type enumeration {
      enum NO_CHECKSUM {
        description
          "No checksum calculation";
      }
      enum SOFTWARE_CHECKSUM {
        description
          "Softbank based checksum calculation";
      }
      enum HARDWARE_CHECKSUM {
        description
          "Hardware checksum offload";
      }
    }
  }

  typedef bgp-as-type {
    type enumeration {
      enum ASN16 {
        description
          "2-byte (16-bit) AS number";
      }
      enum ASN32 {
        description
          "4-byte (32-bit) AS number";
      }
    }
  }

  typedef bgp-interface-state {
    type enumeration {
      enum UP {
        value 1;
        description
          "Ready to pass packets.";
      }
      enum DOWN {
        value 2;
        description
          "The interface does not pass any packets.";
      }
    }
  }

  typedef bgp-rib-origin-type {
    type union {
      type inet:ip-address-no-zone;
      type leafref {
        path "/oc-if:interfaces/oc-if:interface/oc-if:name";
      }
    }
    description
      "The origin type represents either a no zone IP address,
      or an interface name";
  }

  /*
   * EVPN-VPWS Interface State-Machine States
   */
  identity EVPN_VPWS_INTERFACE_FSM_STATE {
    description
      "EVPN-VPWS Interface State-Machine State";
  }

  identity STATE_NONE {
    base EVPN_VPWS_INTERFACE_FSM_STATE;
    description
      "None/Invalid state";
  }

  identity STATE_INIT {
    base EVPN_VPWS_INTERFACE_FSM_STATE;
    description
      "Initial state";
  }

  identity STATE_IFUP {
    base EVPN_VPWS_INTERFACE_FSM_STATE;
    description
      "Interface-UP state";
  }

  identity STATE_IFDOWN {
    base EVPN_VPWS_INTERFACE_FSM_STATE;
    description
      "Interface-DOWN state";
  }

  identity STATE_LOS_RESTORED {
    base EVPN_VPWS_INTERFACE_FSM_STATE;
    description
      "LOS-Restored state";
  }

  identity STATE_LOS {
    base EVPN_VPWS_INTERFACE_FSM_STATE;
    description
      "LOS state";
  }

  identity STATE_LOS_IFDOWN {
    base EVPN_VPWS_INTERFACE_FSM_STATE;
    description
      "LOS-Interface-DOWN state";
  }

  identity STATE_CONNECTED {
    base EVPN_VPWS_INTERFACE_FSM_STATE;
    description
      "CONNECTED state";
  }

  identity STATE_CONNECTED_LOS {
    base EVPN_VPWS_INTERFACE_FSM_STATE;
    description
      "CONNECTED-LOS state";
  }

  identity STATE_CONNECTED_IFDOWN {
    base EVPN_VPWS_INTERFACE_FSM_STATE;
    description
      "CONNECTED-Interface-DOWN state";
  }

  identity STATE_UNKNOWN {
    base EVPN_VPWS_INTERFACE_FSM_STATE;
    description
      "Unknown state";
  }

  /*
   * EVPN-VPWS Interface State-Machine Events
   */
  identity EVPN_VPWS_INTERFACE_FSM_EVENT {
    description
      "EVPN-VPWS Interface State-Machine Event";
  }

  identity EVENT_NONE {
    base EVPN_VPWS_INTERFACE_FSM_EVENT;
    description
      "None/Invalid event";
  }

  identity EVENT_OPER_UP {
    base EVPN_VPWS_INTERFACE_FSM_EVENT;
    description
      "Oper-UP event";
  }

  identity EVENT_OPER_DOWN {
    base EVPN_VPWS_INTERFACE_FSM_EVENT;
    description
      "Oper-DOWN event";
  }

  identity EVENT_SVC_SETUP {
    base EVPN_VPWS_INTERFACE_FSM_EVENT;
    description
      "Service-Setup event";
  }

  identity EVENT_SVC_TEARDOWN {
    base EVPN_VPWS_INTERFACE_FSM_EVENT;
    description
      "Service-Teardown event";
  }

  identity EVENT_RESTORE_LOS {
    base EVPN_VPWS_INTERFACE_FSM_EVENT;
    description
      "Restore-LOS event";
  }

  identity EVENT_SVC_WAIT_TIMER_EXPIRY {
    base EVPN_VPWS_INTERFACE_FSM_EVENT;
    description
      "Service-Wait-Timer-Expiry event";
  }

  identity EVENT_OPER_WAIT_TIMER_EXPIRY {
    base EVPN_VPWS_INTERFACE_FSM_EVENT;
    description
      "Oper-Wait-Timer-Expiry event";
  }

  identity EVENT_CONFIG_CHANGE {
    base EVPN_VPWS_INTERFACE_FSM_EVENT;
    description
      "Configuration-Change event";
  }

  identity EVENT_RESET {
    base EVPN_VPWS_INTERFACE_FSM_EVENT;
    description
      "Reset event";
  }

  identity EVENT_UNKNOWN {
    base EVPN_VPWS_INTERFACE_FSM_EVENT;
    description
      "Unknown event";
  }

  grouping bgp-adj-rib-attr-state {
    description
      "Path attributes that are not expected to be shared across
      route entries, specific to Adj-RIB";

    leaf path-id {
      type uint64;
      description
        "When the BGP speaker supports advertisement of multiple
        paths for a prefix, the path identifier is used to
        uniquely identify a route based on the combination of the
        prefix and path id.";
    }
  }

  grouping bgp-loc-rib-common-keys {
    description
      "Common references used in keys for IPv4 and IPv6
      LOC-RIB entries";

    leaf origin {
      type union {
        type inet:ip-address;
        type leafref {
          path "/oc-if:interfaces/oc-if:interface/oc-if:name";
        }
      }
      description
        "Indicates the origin of the route.";
    }

    leaf path-id {
      type uint64;
      description
        "When the BGP speaker supports advertisement of multiple
        paths for a prefix, the path identifier is used to
        uniquely identify a route based on the combination of the
        prefix and path id.";
    }
  }
}
