submodule arcos-datapath-aft-gtp-ip-term {
  yang-version "1.1";

  belongs-to "arcos-datapath-aft" {
    prefix "arcos-dp-aft";
  }

  import ietf-inet-types { prefix "inet"; }
  import arcos-aft-types { prefix "arc-aft-types"; }

  // Include common cross-AFT groupings from the common submodule.
  include arcos-datapath-aft-common;

  organization
    "Arrcus, Inc.";

  contact
    "Arrcus, Inc.
     2077 Gateway Place
     Suite 400
     San Jose, CA 95110

     E-mail: yang-support@arrcus.com";

  description
    "Submodule containing definitions of groupings for the abstract
     forwarding table for GTP IP Termination Objects.

     Copyright (c) 2024 by Arrcus, Inc.
     All rights reserved.";

  revision "2024-05-02" {
    description
      "Initial Version";
  }

  grouping aft-gtp-ip-term-structural {
    description
      "Structural grouping defining the schema for the GTP IP Term
      table.";

    list gtp-ip-term-entry {
      key "outer-vrf-id dst-prefix";

      description
        "List of the GTP IP Term entries within the abstract
        forwarding table. This list is keyed by the outer vrf id.";

      leaf outer-vrf-id {
        type uint32;
        description
          "Outer vrf id matched by the entry.";
      }

      leaf dst-prefix {
        type inet:ipv6-prefix;
        description
          "Destination prefix matched by the entry.";
      }

      container state {
        config false;
        description
          "Operational state parameters for the GTP IP Term AFT
          entry.";
        uses aft-gtp-ip-term-entry-state;
      }

    }
  }

  grouping aft-gtp-ip-term-entry-state {
    description
      "Operational state parameters for the GTP IP Term entry.";
    leaf outer-vrf-id {
      type uint32;
      description
        "VRF in use for the entry";
    }

    leaf dst-prefix {
      type inet:ipv6-prefix;
      description
        "IPv6 Destination Prefix of the GTP IP term obj";
    }

    leaf src-prefix {
      type inet:ipv4-prefix;
      description
        "Src IPv4 Prefix GTP IP term obj";
    }

    leaf hw-obj-id {
      type uint64;
      description
        "HW Obj id of GTP IP term obj";
    }
  }
}
