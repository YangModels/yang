/*
 * Generated by confdc --mib2yang
 * Source: RMON-MIB.mib
 */
module RMON-MIB {
  namespace "http://tail-f.com/ns/mibs/RMON-MIB/200005110000Z";
  prefix RMON_MIB;
  tailf:id "";
  tailf:snmp-mib-module-name "RMON-MIB";

  import ietf-yang-types {
    prefix yang;
  }
  import tailf-common {
    prefix tailf;
  }

  revision 2000-05-11 {
    description
      "";
  }

  container RMON-MIB {
    config false;
    container etherStatsTable {
      list etherStatsEntry {
        key "etherStatsIndex";
        tailf:sort-order "snmp";
        tailf:snmp-name "etherStatsTable";
        leaf etherStatsIndex {
          type etherStatsIndexType;
          tailf:snmp-name "etherStatsIndex";
        }
        leaf etherStatsDataSource {
          type yang:object-identifier;
          tailf:snmp-name "etherStatsDataSource";
        }
        leaf etherStatsDropEvents {
          type yang:counter32;
          tailf:snmp-name "etherStatsDropEvents";
        }
        leaf etherStatsOctets {
          type yang:counter32;
          tailf:snmp-name "etherStatsOctets";
        }
        leaf etherStatsPkts {
          type yang:counter32;
          tailf:snmp-name "etherStatsPkts";
        }
        leaf etherStatsBroadcastPkts {
          type yang:counter32;
          tailf:snmp-name "etherStatsBroadcastPkts";
        }
        leaf etherStatsMulticastPkts {
          type yang:counter32;
          tailf:snmp-name "etherStatsMulticastPkts";
        }
        leaf etherStatsCRCAlignErrors {
          type yang:counter32;
          tailf:snmp-name "etherStatsCRCAlignErrors";
        }
        leaf etherStatsUndersizePkts {
          type yang:counter32;
          tailf:snmp-name "etherStatsUndersizePkts";
        }
        leaf etherStatsOversizePkts {
          type yang:counter32;
          tailf:snmp-name "etherStatsOversizePkts";
        }
        leaf etherStatsFragments {
          type yang:counter32;
          tailf:snmp-name "etherStatsFragments";
        }
        leaf etherStatsJabbers {
          type yang:counter32;
          tailf:snmp-name "etherStatsJabbers";
        }
        leaf etherStatsCollisions {
          type yang:counter32;
          tailf:snmp-name "etherStatsCollisions";
        }
        leaf etherStatsPkts64Octets {
          type yang:counter32;
          tailf:snmp-name "etherStatsPkts64Octets";
        }
        leaf etherStatsPkts65to127Octets {
          type yang:counter32;
          tailf:snmp-name "etherStatsPkts65to127Octets";
        }
        leaf etherStatsPkts128to255Octets {
          type yang:counter32;
          tailf:snmp-name "etherStatsPkts128to255Octets";
        }
        leaf etherStatsPkts256to511Octets {
          type yang:counter32;
          tailf:snmp-name "etherStatsPkts256to511Octets";
        }
        leaf etherStatsPkts512to1023Octets {
          type yang:counter32;
          tailf:snmp-name "etherStatsPkts512to1023Octets";
        }
        leaf etherStatsPkts1024to1518Octets {
          type yang:counter32;
          tailf:snmp-name "etherStatsPkts1024to1518Octets";
        }
        leaf etherStatsOwner {
          type OwnerString;
          tailf:snmp-name "etherStatsOwner";
        }
        leaf etherStatsStatus {
          type EntryStatus;
          tailf:snmp-name "etherStatsStatus";
        }
      }
    }
    container historyControlTable {
      list historyControlEntry {
        key "historyControlIndex";
        tailf:sort-order "snmp";
        tailf:snmp-name "historyControlTable";
        leaf historyControlIndex {
          type historyControlIndexType;
          tailf:snmp-name "historyControlIndex";
        }
        leaf historyControlDataSource {
          type yang:object-identifier;
          tailf:snmp-name "historyControlDataSource";
        }
        leaf historyControlBucketsRequested {
          type historyControlBucketsRequestedType;
          tailf:snmp-name "historyControlBucketsRequested";
        }
        leaf historyControlBucketsGranted {
          type historyControlBucketsGrantedType;
          tailf:snmp-name "historyControlBucketsGranted";
        }
        leaf historyControlInterval {
          type historyControlIntervalType;
          tailf:snmp-name "historyControlInterval";
        }
        leaf historyControlOwner {
          type OwnerString;
          tailf:snmp-name "historyControlOwner";
        }
        leaf historyControlStatus {
          type EntryStatus;
          tailf:snmp-name "historyControlStatus";
        }
      }
    }
    container etherHistoryTable {
      list etherHistoryEntry {
        key "etherHistoryIndex etherHistorySampleIndex";
        tailf:sort-order "snmp";
        tailf:snmp-name "etherHistoryTable";
        leaf etherHistoryIndex {
          type etherHistoryIndexType;
          tailf:snmp-name "etherHistoryIndex";
        }
        leaf etherHistorySampleIndex {
          type etherHistorySampleIndexType;
          tailf:snmp-name "etherHistorySampleIndex";
        }
        leaf etherHistoryIntervalStart {
          type yang:timeticks;
          tailf:snmp-name "etherHistoryIntervalStart";
        }
        leaf etherHistoryDropEvents {
          type yang:counter32;
          tailf:snmp-name "etherHistoryDropEvents";
        }
        leaf etherHistoryOctets {
          type yang:counter32;
          tailf:snmp-name "etherHistoryOctets";
        }
        leaf etherHistoryPkts {
          type yang:counter32;
          tailf:snmp-name "etherHistoryPkts";
        }
        leaf etherHistoryBroadcastPkts {
          type yang:counter32;
          tailf:snmp-name "etherHistoryBroadcastPkts";
        }
        leaf etherHistoryMulticastPkts {
          type yang:counter32;
          tailf:snmp-name "etherHistoryMulticastPkts";
        }
        leaf etherHistoryCRCAlignErrors {
          type yang:counter32;
          tailf:snmp-name "etherHistoryCRCAlignErrors";
        }
        leaf etherHistoryUndersizePkts {
          type yang:counter32;
          tailf:snmp-name "etherHistoryUndersizePkts";
        }
        leaf etherHistoryOversizePkts {
          type yang:counter32;
          tailf:snmp-name "etherHistoryOversizePkts";
        }
        leaf etherHistoryFragments {
          type yang:counter32;
          tailf:snmp-name "etherHistoryFragments";
        }
        leaf etherHistoryJabbers {
          type yang:counter32;
          tailf:snmp-name "etherHistoryJabbers";
        }
        leaf etherHistoryCollisions {
          type yang:counter32;
          tailf:snmp-name "etherHistoryCollisions";
        }
        leaf etherHistoryUtilization {
          type etherHistoryUtilizationType;
          tailf:snmp-name "etherHistoryUtilization";
        }
      }
    }
    container alarmTable {
      list alarmEntry {
        key "alarmIndex";
        tailf:sort-order "snmp";
        tailf:snmp-name "alarmTable";
        leaf alarmIndex {
          type alarmIndexType;
          tailf:snmp-name "alarmIndex";
        }
        leaf alarmInterval {
          type int32;
          tailf:snmp-name "alarmInterval";
        }
        leaf alarmVariable {
          type yang:object-identifier;
          tailf:snmp-name "alarmVariable";
        }
        leaf alarmSampleType {
          type alarmSampleTypeType;
          tailf:snmp-name "alarmSampleType";
        }
        leaf alarmValue {
          type int32;
          tailf:snmp-name "alarmValue";
        }
        leaf alarmStartupAlarm {
          type alarmStartupAlarmType;
          tailf:snmp-name "alarmStartupAlarm";
        }
        leaf alarmRisingThreshold {
          type int32;
          tailf:snmp-name "alarmRisingThreshold";
        }
        leaf alarmFallingThreshold {
          type int32;
          tailf:snmp-name "alarmFallingThreshold";
        }
        leaf alarmRisingEventIndex {
          type alarmRisingEventIndexType;
          tailf:snmp-name "alarmRisingEventIndex";
        }
        leaf alarmFallingEventIndex {
          type alarmFallingEventIndexType;
          tailf:snmp-name "alarmFallingEventIndex";
        }
        leaf alarmOwner {
          type OwnerString;
          tailf:snmp-name "alarmOwner";
        }
        leaf alarmStatus {
          type EntryStatus;
          tailf:snmp-name "alarmStatus";
        }
      }
    }
    container hostControlTable {
      list hostControlEntry {
        key "hostControlIndex";
        tailf:sort-order "snmp";
        tailf:snmp-name "hostControlTable";
        leaf hostControlIndex {
          type hostControlIndexType;
          tailf:snmp-name "hostControlIndex";
        }
        leaf hostControlDataSource {
          type yang:object-identifier;
          tailf:snmp-name "hostControlDataSource";
        }
        leaf hostControlTableSize {
          type int32;
          tailf:snmp-name "hostControlTableSize";
        }
        leaf hostControlLastDeleteTime {
          type yang:timeticks;
          tailf:snmp-name "hostControlLastDeleteTime";
        }
        leaf hostControlOwner {
          type OwnerString;
          tailf:snmp-name "hostControlOwner";
        }
        leaf hostControlStatus {
          type EntryStatus;
          tailf:snmp-name "hostControlStatus";
        }
      }
    }
    container hostTable {
      list hostEntry {
        key "hostIndex hostAddress";
        tailf:sort-order "snmp";
        tailf:snmp-name "hostTable";
        leaf hostIndex {
          type hostIndexType;
          tailf:snmp-name "hostIndex";
        }
        leaf hostAddress {
          type tailf:hex-list;
          tailf:snmp-name "hostAddress";
        }
        leaf hostCreationOrder {
          type hostCreationOrderType;
          tailf:snmp-name "hostCreationOrder";
        }
        leaf hostInPkts {
          type yang:counter32;
          tailf:snmp-name "hostInPkts";
        }
        leaf hostOutPkts {
          type yang:counter32;
          tailf:snmp-name "hostOutPkts";
        }
        leaf hostInOctets {
          type yang:counter32;
          tailf:snmp-name "hostInOctets";
        }
        leaf hostOutOctets {
          type yang:counter32;
          tailf:snmp-name "hostOutOctets";
        }
        leaf hostOutErrors {
          type yang:counter32;
          tailf:snmp-name "hostOutErrors";
        }
        leaf hostOutBroadcastPkts {
          type yang:counter32;
          tailf:snmp-name "hostOutBroadcastPkts";
        }
        leaf hostOutMulticastPkts {
          type yang:counter32;
          tailf:snmp-name "hostOutMulticastPkts";
        }
      }
    }
    container hostTimeTable {
      list hostTimeEntry {
        key "hostTimeIndex hostTimeCreationOrder";
        tailf:sort-order "snmp";
        tailf:snmp-name "hostTimeTable";
        leaf hostTimeIndex {
          type hostTimeIndexType;
          tailf:snmp-name "hostTimeIndex";
        }
        leaf hostTimeCreationOrder {
          type hostTimeCreationOrderType;
          tailf:snmp-name "hostTimeCreationOrder";
        }
        leaf hostTimeAddress {
          type tailf:hex-list;
          tailf:snmp-name "hostTimeAddress";
        }
        leaf hostTimeInPkts {
          type yang:counter32;
          tailf:snmp-name "hostTimeInPkts";
        }
        leaf hostTimeOutPkts {
          type yang:counter32;
          tailf:snmp-name "hostTimeOutPkts";
        }
        leaf hostTimeInOctets {
          type yang:counter32;
          tailf:snmp-name "hostTimeInOctets";
        }
        leaf hostTimeOutOctets {
          type yang:counter32;
          tailf:snmp-name "hostTimeOutOctets";
        }
        leaf hostTimeOutErrors {
          type yang:counter32;
          tailf:snmp-name "hostTimeOutErrors";
        }
        leaf hostTimeOutBroadcastPkts {
          type yang:counter32;
          tailf:snmp-name "hostTimeOutBroadcastPkts";
        }
        leaf hostTimeOutMulticastPkts {
          type yang:counter32;
          tailf:snmp-name "hostTimeOutMulticastPkts";
        }
      }
    }
    container hostTopNControlTable {
      list hostTopNControlEntry {
        key "hostTopNControlIndex";
        tailf:sort-order "snmp";
        tailf:snmp-name "hostTopNControlTable";
        leaf hostTopNControlIndex {
          type hostTopNControlIndexType;
          tailf:snmp-name "hostTopNControlIndex";
        }
        leaf hostTopNHostIndex {
          type hostTopNHostIndexType;
          tailf:snmp-name "hostTopNHostIndex";
        }
        leaf hostTopNRateBase {
          type hostTopNRateBaseType;
          tailf:snmp-name "hostTopNRateBase";
        }
        leaf hostTopNTimeRemaining {
          type int32;
          tailf:snmp-name "hostTopNTimeRemaining";
        }
        leaf hostTopNDuration {
          type int32;
          tailf:snmp-name "hostTopNDuration";
        }
        leaf hostTopNRequestedSize {
          type int32;
          tailf:snmp-name "hostTopNRequestedSize";
        }
        leaf hostTopNGrantedSize {
          type int32;
          tailf:snmp-name "hostTopNGrantedSize";
        }
        leaf hostTopNStartTime {
          type yang:timeticks;
          tailf:snmp-name "hostTopNStartTime";
        }
        leaf hostTopNOwner {
          type OwnerString;
          tailf:snmp-name "hostTopNOwner";
        }
        leaf hostTopNStatus {
          type EntryStatus;
          tailf:snmp-name "hostTopNStatus";
        }
      }
    }
    container hostTopNTable {
      list hostTopNEntry {
        key "hostTopNReport hostTopNIndex";
        tailf:sort-order "snmp";
        tailf:snmp-name "hostTopNTable";
        leaf hostTopNReport {
          type hostTopNReportType;
          tailf:snmp-name "hostTopNReport";
        }
        leaf hostTopNIndex {
          type hostTopNIndexType;
          tailf:snmp-name "hostTopNIndex";
        }
        leaf hostTopNAddress {
          type tailf:hex-list;
          tailf:snmp-name "hostTopNAddress";
        }
        leaf hostTopNRate {
          type int32;
          tailf:snmp-name "hostTopNRate";
        }
      }
    }
    container matrixControlTable {
      list matrixControlEntry {
        key "matrixControlIndex";
        tailf:sort-order "snmp";
        tailf:snmp-name "matrixControlTable";
        leaf matrixControlIndex {
          type matrixControlIndexType;
          tailf:snmp-name "matrixControlIndex";
        }
        leaf matrixControlDataSource {
          type yang:object-identifier;
          tailf:snmp-name "matrixControlDataSource";
        }
        leaf matrixControlTableSize {
          type int32;
          tailf:snmp-name "matrixControlTableSize";
        }
        leaf matrixControlLastDeleteTime {
          type yang:timeticks;
          tailf:snmp-name "matrixControlLastDeleteTime";
        }
        leaf matrixControlOwner {
          type OwnerString;
          tailf:snmp-name "matrixControlOwner";
        }
        leaf matrixControlStatus {
          type EntryStatus;
          tailf:snmp-name "matrixControlStatus";
        }
      }
    }
    container matrixSDTable {
      list matrixSDEntry {
        key "matrixSDIndex matrixSDSourceAddress matrixSDDestAddress";
        tailf:sort-order "snmp";
        tailf:snmp-name "matrixSDTable";
        leaf matrixSDIndex {
          type matrixSDIndexType;
          tailf:snmp-name "matrixSDIndex";
        }
        leaf matrixSDSourceAddress {
          type tailf:hex-list;
          tailf:snmp-name "matrixSDSourceAddress";
        }
        leaf matrixSDDestAddress {
          type tailf:hex-list;
          tailf:snmp-name "matrixSDDestAddress";
        }
        leaf matrixSDPkts {
          type yang:counter32;
          tailf:snmp-name "matrixSDPkts";
        }
        leaf matrixSDOctets {
          type yang:counter32;
          tailf:snmp-name "matrixSDOctets";
        }
        leaf matrixSDErrors {
          type yang:counter32;
          tailf:snmp-name "matrixSDErrors";
        }
      }
    }
    container matrixDSTable {
      list matrixDSEntry {
        key "matrixDSIndex matrixDSDestAddress matrixDSSourceAddress";
        tailf:sort-order "snmp";
        tailf:snmp-name "matrixDSTable";
        leaf matrixDSIndex {
          type matrixDSIndexType;
          tailf:snmp-name "matrixDSIndex";
        }
        leaf matrixDSDestAddress {
          type tailf:hex-list;
          tailf:snmp-name "matrixDSDestAddress";
        }
        leaf matrixDSSourceAddress {
          type tailf:hex-list;
          tailf:snmp-name "matrixDSSourceAddress";
        }
        leaf matrixDSPkts {
          type yang:counter32;
          tailf:snmp-name "matrixDSPkts";
        }
        leaf matrixDSOctets {
          type yang:counter32;
          tailf:snmp-name "matrixDSOctets";
        }
        leaf matrixDSErrors {
          type yang:counter32;
          tailf:snmp-name "matrixDSErrors";
        }
      }
    }
    container filterTable {
      list filterEntry {
        key "filterIndex";
        tailf:sort-order "snmp";
        tailf:snmp-name "filterTable";
        leaf filterIndex {
          type filterIndexType;
          tailf:snmp-name "filterIndex";
        }
        leaf filterChannelIndex {
          type filterChannelIndexType;
          tailf:snmp-name "filterChannelIndex";
        }
        leaf filterPktDataOffset {
          type int32;
          tailf:snmp-name "filterPktDataOffset";
        }
        leaf filterPktData {
          type tailf:hex-list;
          tailf:snmp-name "filterPktData";
        }
        leaf filterPktDataMask {
          type tailf:hex-list;
          tailf:snmp-name "filterPktDataMask";
        }
        leaf filterPktDataNotMask {
          type tailf:hex-list;
          tailf:snmp-name "filterPktDataNotMask";
        }
        leaf filterPktStatus {
          type int32;
          tailf:snmp-name "filterPktStatus";
        }
        leaf filterPktStatusMask {
          type int32;
          tailf:snmp-name "filterPktStatusMask";
        }
        leaf filterPktStatusNotMask {
          type int32;
          tailf:snmp-name "filterPktStatusNotMask";
        }
        leaf filterOwner {
          type OwnerString;
          tailf:snmp-name "filterOwner";
        }
        leaf filterStatus {
          type EntryStatus;
          tailf:snmp-name "filterStatus";
        }
      }
    }
    container channelTable {
      list channelEntry {
        key "channelIndex";
        tailf:sort-order "snmp";
        tailf:snmp-name "channelTable";
        leaf channelIndex {
          type channelIndexType;
          tailf:snmp-name "channelIndex";
        }
        leaf channelIfIndex {
          type channelIfIndexType;
          tailf:snmp-name "channelIfIndex";
        }
        leaf channelAcceptType {
          type channelAcceptTypeType;
          tailf:snmp-name "channelAcceptType";
        }
        leaf channelDataControl {
          type channelDataControlType;
          tailf:snmp-name "channelDataControl";
        }
        leaf channelTurnOnEventIndex {
          type channelTurnOnEventIndexType;
          tailf:snmp-name "channelTurnOnEventIndex";
        }
        leaf channelTurnOffEventIndex {
          type channelTurnOffEventIndexType;
          tailf:snmp-name "channelTurnOffEventIndex";
        }
        leaf channelEventIndex {
          type channelEventIndexType;
          tailf:snmp-name "channelEventIndex";
        }
        leaf channelEventStatus {
          type channelEventStatusType;
          tailf:snmp-name "channelEventStatus";
        }
        leaf channelMatches {
          type yang:counter32;
          tailf:snmp-name "channelMatches";
        }
        leaf channelDescription {
          type channelDescriptionType;
          tailf:snmp-name "channelDescription";
        }
        leaf channelOwner {
          type OwnerString;
          tailf:snmp-name "channelOwner";
        }
        leaf channelStatus {
          type EntryStatus;
          tailf:snmp-name "channelStatus";
        }
      }
    }
    container bufferControlTable {
      list bufferControlEntry {
        key "bufferControlIndex";
        tailf:sort-order "snmp";
        tailf:snmp-name "bufferControlTable";
        leaf bufferControlIndex {
          type bufferControlIndexType;
          tailf:snmp-name "bufferControlIndex";
        }
        leaf bufferControlChannelIndex {
          type bufferControlChannelIndexType;
          tailf:snmp-name "bufferControlChannelIndex";
        }
        leaf bufferControlFullStatus {
          type bufferControlFullStatusType;
          tailf:snmp-name "bufferControlFullStatus";
        }
        leaf bufferControlFullAction {
          type bufferControlFullActionType;
          tailf:snmp-name "bufferControlFullAction";
        }
        leaf bufferControlCaptureSliceSize {
          type int32;
          tailf:snmp-name "bufferControlCaptureSliceSize";
        }
        leaf bufferControlDownloadSliceSize {
          type int32;
          tailf:snmp-name "bufferControlDownloadSliceSize";
        }
        leaf bufferControlDownloadOffset {
          type int32;
          tailf:snmp-name "bufferControlDownloadOffset";
        }
        leaf bufferControlMaxOctetsRequested {
          type int32;
          tailf:snmp-name "bufferControlMaxOctetsRequested";
        }
        leaf bufferControlMaxOctetsGranted {
          type int32;
          tailf:snmp-name "bufferControlMaxOctetsGranted";
        }
        leaf bufferControlCapturedPackets {
          type int32;
          tailf:snmp-name "bufferControlCapturedPackets";
        }
        leaf bufferControlTurnOnTime {
          type yang:timeticks;
          tailf:snmp-name "bufferControlTurnOnTime";
        }
        leaf bufferControlOwner {
          type OwnerString;
          tailf:snmp-name "bufferControlOwner";
        }
        leaf bufferControlStatus {
          type EntryStatus;
          tailf:snmp-name "bufferControlStatus";
        }
      }
    }
    container captureBufferTable {
      list captureBufferEntry {
        key "captureBufferControlIndex captureBufferIndex";
        tailf:sort-order "snmp";
        tailf:snmp-name "captureBufferTable";
        leaf captureBufferControlIndex {
          type captureBufferControlIndexType;
          tailf:snmp-name "captureBufferControlIndex";
        }
        leaf captureBufferIndex {
          type captureBufferIndexType;
          tailf:snmp-name "captureBufferIndex";
        }
        leaf captureBufferPacketID {
          type int32;
          tailf:snmp-name "captureBufferPacketID";
        }
        leaf captureBufferPacketData {
          type tailf:hex-list;
          tailf:snmp-name "captureBufferPacketData";
        }
        leaf captureBufferPacketLength {
          type int32;
          tailf:snmp-name "captureBufferPacketLength";
        }
        leaf captureBufferPacketTime {
          type int32;
          tailf:snmp-name "captureBufferPacketTime";
        }
        leaf captureBufferPacketStatus {
          type int32;
          tailf:snmp-name "captureBufferPacketStatus";
        }
      }
    }
    container eventTable {
      list eventEntry {
        key "eventIndex";
        tailf:sort-order "snmp";
        tailf:snmp-name "eventTable";
        leaf eventIndex {
          type eventIndexType;
          tailf:snmp-name "eventIndex";
        }
        leaf eventDescription {
          type eventDescriptionType;
          tailf:snmp-name "eventDescription";
        }
        leaf eventType {
          type eventTypeType;
          tailf:snmp-name "eventType";
        }
        leaf eventCommunity {
          type eventCommunityType;
          tailf:snmp-name "eventCommunity";
        }
        leaf eventLastTimeSent {
          type yang:timeticks;
          tailf:snmp-name "eventLastTimeSent";
        }
        leaf eventOwner {
          type OwnerString;
          tailf:snmp-name "eventOwner";
        }
        leaf eventStatus {
          type EntryStatus;
          tailf:snmp-name "eventStatus";
        }
      }
    }
    container logTable {
      list logEntry {
        key "logEventIndex logIndex";
        tailf:sort-order "snmp";
        tailf:snmp-name "logTable";
        leaf logEventIndex {
          type logEventIndexType;
          tailf:snmp-name "logEventIndex";
        }
        leaf logIndex {
          type logIndexType;
          tailf:snmp-name "logIndex";
        }
        leaf logTime {
          type yang:timeticks;
          tailf:snmp-name "logTime";
        }
        leaf logDescription {
          type logDescriptionType;
          tailf:snmp-name "logDescription";
        }
      }
    }
  }

  typedef OwnerString {
    type tailf:hex-list {
      tailf:value-length "min .. 127";
    }
  }

  typedef EntryStatus {
    type enumeration {
      enum "valid" {
        value 1;
      }
      enum "createRequest" {
        value 2;
      }
      enum "underCreation" {
        value 3;
      }
      enum "invalid" {
        value 4;
      }
    }
  }

  typedef etherStatsIndexType {
    type int32 {
      range "1 .. 65535";
    }
  }

  typedef historyControlIndexType {
    type int32 {
      range "1 .. 65535";
    }
  }

  typedef historyControlBucketsRequestedType {
    type int32 {
      range "1 .. 65535";
    }
  }

  typedef historyControlBucketsGrantedType {
    type int32 {
      range "1 .. 65535";
    }
  }

  typedef historyControlIntervalType {
    type int32 {
      range "1 .. 3600";
    }
  }

  typedef etherHistoryIndexType {
    type int32 {
      range "1 .. 65535";
    }
  }

  typedef etherHistorySampleIndexType {
    type int32 {
      range "1 .. 2147483647";
    }
  }

  typedef etherHistoryUtilizationType {
    type int32 {
      range "0 .. 10000";
    }
  }

  typedef alarmIndexType {
    type int32 {
      range "1 .. 65535";
    }
  }

  typedef alarmSampleTypeType {
    type enumeration {
      enum "absoluteValue" {
        value 1;
      }
      enum "deltaValue" {
        value 2;
      }
    }
  }

  typedef alarmStartupAlarmType {
    type enumeration {
      enum "risingAlarm" {
        value 1;
      }
      enum "fallingAlarm" {
        value 2;
      }
      enum "risingOrFallingAlarm" {
        value 3;
      }
    }
  }

  typedef alarmRisingEventIndexType {
    type int32 {
      range "0 .. 65535";
    }
  }

  typedef alarmFallingEventIndexType {
    type int32 {
      range "0 .. 65535";
    }
  }

  typedef hostControlIndexType {
    type int32 {
      range "1 .. 65535";
    }
  }

  typedef hostIndexType {
    type int32 {
      range "1 .. 65535";
    }
  }

  typedef hostCreationOrderType {
    type int32 {
      range "1 .. 65535";
    }
  }

  typedef hostTimeIndexType {
    type int32 {
      range "1 .. 65535";
    }
  }

  typedef hostTimeCreationOrderType {
    type int32 {
      range "1 .. 65535";
    }
  }

  typedef hostTopNControlIndexType {
    type int32 {
      range "1 .. 65535";
    }
  }

  typedef hostTopNHostIndexType {
    type int32 {
      range "1 .. 65535";
    }
  }

  typedef hostTopNRateBaseType {
    type enumeration {
      enum "hostTopNInPkts" {
        value 1;
      }
      enum "hostTopNOutPkts" {
        value 2;
      }
      enum "hostTopNInOctets" {
        value 3;
      }
      enum "hostTopNOutOctets" {
        value 4;
      }
      enum "hostTopNOutErrors" {
        value 5;
      }
      enum "hostTopNOutBroadcastPkts" {
        value 6;
      }
      enum "hostTopNOutMulticastPkts" {
        value 7;
      }
    }
  }

  typedef hostTopNReportType {
    type int32 {
      range "1 .. 65535";
    }
  }

  typedef hostTopNIndexType {
    type int32 {
      range "1 .. 65535";
    }
  }

  typedef matrixControlIndexType {
    type int32 {
      range "1 .. 65535";
    }
  }

  typedef matrixSDIndexType {
    type int32 {
      range "1 .. 65535";
    }
  }

  typedef matrixDSIndexType {
    type int32 {
      range "1 .. 65535";
    }
  }

  typedef filterIndexType {
    type int32 {
      range "1 .. 65535";
    }
  }

  typedef filterChannelIndexType {
    type int32 {
      range "1 .. 65535";
    }
  }

  typedef channelIndexType {
    type int32 {
      range "1 .. 65535";
    }
  }

  typedef channelIfIndexType {
    type int32 {
      range "1 .. 65535";
    }
  }

  typedef channelAcceptTypeType {
    type enumeration {
      enum "acceptMatched" {
        value 1;
      }
      enum "acceptFailed" {
        value 2;
      }
    }
  }

  typedef channelDataControlType {
    type enumeration {
      enum "on" {
        value 1;
      }
      enum "off" {
        value 2;
      }
    }
  }

  typedef channelTurnOnEventIndexType {
    type int32 {
      range "0 .. 65535";
    }
  }

  typedef channelTurnOffEventIndexType {
    type int32 {
      range "0 .. 65535";
    }
  }

  typedef channelEventIndexType {
    type int32 {
      range "0 .. 65535";
    }
  }

  typedef channelEventStatusType {
    type enumeration {
      enum "eventReady" {
        value 1;
      }
      enum "eventFired" {
        value 2;
      }
      enum "eventAlwaysReady" {
        value 3;
      }
    }
  }

  typedef channelDescriptionType {
    type string {
      length "min .. 127";
    }
  }

  typedef bufferControlIndexType {
    type int32 {
      range "1 .. 65535";
    }
  }

  typedef bufferControlChannelIndexType {
    type int32 {
      range "1 .. 65535";
    }
  }

  typedef bufferControlFullStatusType {
    type enumeration {
      enum "spaceAvailable" {
        value 1;
      }
      enum "full" {
        value 2;
      }
    }
  }

  typedef bufferControlFullActionType {
    type enumeration {
      enum "lockWhenFull" {
        value 1;
      }
      enum "wrapWhenFull" {
        value 2;
      }
    }
  }

  typedef captureBufferControlIndexType {
    type int32 {
      range "1 .. 65535";
    }
  }

  typedef captureBufferIndexType {
    type int32 {
      range "1 .. 2147483647";
    }
  }

  typedef eventIndexType {
    type int32 {
      range "1 .. 65535";
    }
  }

  typedef eventDescriptionType {
    type string {
      length "min .. 127";
    }
  }

  typedef eventTypeType {
    type enumeration {
      enum "none" {
        value 1;
      }
      enum "log" {
        value 2;
      }
      enum "snmptrap" {
        value 3;
      }
      enum "logandtrap" {
        value 4;
      }
    }
  }

  typedef eventCommunityType {
    type tailf:hex-list {
      tailf:value-length "min .. 127";
    }
  }

  typedef logEventIndexType {
    type int32 {
      range "1 .. 65535";
    }
  }

  typedef logIndexType {
    type int32 {
      range "1 .. 2147483647";
    }
  }

  typedef logDescriptionType {
    type string {
      length "min .. 255";
    }
  }
}
