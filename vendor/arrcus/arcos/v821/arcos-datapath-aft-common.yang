submodule arcos-datapath-aft-common {
  yang-version "1.1";

  belongs-to "arcos-datapath-aft" {
    prefix "arcos-dp-aft";
  }

  import ietf-inet-types { prefix "inet"; }
  import ietf-yang-types { prefix "yang"; }
  import openconfig-interfaces { prefix "oc-if"; }
  import openconfig-mpls-types { prefix "oc-mplst"; }
  import openconfig-policy-types { prefix "oc-pol-types"; }
  import arcos-datapath-aft-types { prefix "arcos-dp-aft-types"; }
  import arcos-datapath-nexthop { prefix "arcos-dp-nh"; }
  import arcos-datapath-tunnel { prefix "arcos-dp-tnl"; }

  organization
    "XXXX";

  contact
    "XXXX";

  description
    "Submodule containing definitions of groupings that are re-used
    across multiple contexts within the AFT model.";


 grouping aft-common-entry-state {
    description
      "Operational state parameters relating to a forwarding entry";

    leaf packets-forwarded {
      type yang:counter64;
      description
        "The number of packets which have matched, and been forwarded,
         based on the AFT entry.";
    }

    leaf octets-forwarded {
      type yang:counter64;
      description
        "The number of octets which have matched, and been forwarded,
         based on the AFT entry";
    }

    leaf next-hop-index {
      type uint64;
      description
        "A reference to the next-hop-index that is in use for the entry";
    }

    leaf next-hop-type {
      type arcos-dp-aft-types:dpal-nexthop-type;
      description
        "Forwarding type.";
    }

    leaf srv6-locator-arg {
      type inet:ip-address;
      description
        "Locator argument";
    }
  }

  grouping aft-common-entry-flat-state {
    description
      "Operational state parameters relating to a forwarding entry";

    uses aft-common-entry-state;
    container next-hops {
      description
        "The abstract forwarding table flattened for next-hops.";
      uses arcos-dp-nh:nexthop-state;
      uses arcos-dp-nh:parent-nexthop-flat-state;
      uses arcos-dp-tnl:tunnel-state-flat;
    }
  }
}
