module arcos-openconfig-interfaces-augments {
  yang-version 1.1;
  namespace "http://yang.arrcus.com/arcos/openconfig/interfaces/augments";
  prefix arc-oc-if-aug;

  import openconfig-interfaces {
    prefix oc-if;
  }

  import openconfig-yang-types {
    prefix oc-yang;
  }

  import openconfig-network-instance {
    prefix oc-ni;
  }

  import openconfig-if-ethernet {
    prefix oc-eth;
  }

  import openconfig-vlan {
    prefix oc-vlan;
  }

  import openconfig-if-aggregate {
    prefix oc-lag;
  }

  import ietf-yang-types {
    prefix yang;
  }

  import ietf-inet-types {
    prefix inet;
  }

  import iana-if-type {
    prefix ianaift;
  }

  import tailf-common {
    prefix tailf;
  }

  import arcos-features {
    prefix arc-features;
  }

  import arcos-platform {
    prefix arc-platform;
  }
  import arcos-portsec {
    prefix arc-portsec;
  }
  import openconfig-system {
    prefix oc-sys;
  }
  import arcos-openconfig-system-augments {
    prefix arc-oc-sys-aug;
  }

  organization
    "Arrcus, Inc.";

  contact
    "Arrcus, Inc.
     2077 Gateway Place
     Suite 400
     San Jose, CA 95110

     E-mail: yang-support@arrcus.com";

  description
    "This module contains definitions for the
     native ArcOS Port Sec feature.

     Copyright (c) 2016-2023 by Arrcus, Inc.
     All rights reserved.";

  revision 2025-05-30 {
    description
      "Adding e-tree leaf AC config for sub-interfaces";
  }

  revision 2025-05-05 {
    description
      "Adding input and output counters for various packet size range";
  }

  revision 2024-12-09 {
    description
      "Adding priority-vlan config for subif0";
  }
  revision 2024-11-25 {
    description
      "Remove Restriction for Strict URPF for urpf-mode-config";
  }

  revision 2024-10-14 {
    description
      "Add leaf link training under interfaces";
  }
      
  revision 2024-09-23 {
    description
      "Circular reference error seen because of when statement, changed it
      to must";
  }

  revision 2024-09-11 {
    description
      "Add leaf custom mac under interfaces";
  }

  revision 2024-04-03 {
    description
      "Add penalty_count and suppress_state for damping-info state";
  }

  revision 2024-03-28 {
    description
      "Add default values and range for damping-info leafs";
  }

  revision 2023-12-20 {
    description
      "Remove derived-from-or-self() for a non-identityref node.";
  }

  revision 2023-12-16 {
    description
      "Interface damping support";
  }

  revision 2023-09-20 {
    description
      "Restrict L2CP-Tunnel for LACP bond.";
  }

  revision 2023-09-12 {
    description "Display debounce interval node based on interface name";
  }

  revision 2023-08-02 {
    description
      "Add in-pkts and out-pkts in counters";
  }

  revision 2023-04-18 {
    description
      "Added URPF mode support";
  }

  revision 2023-02-08 {
    description
      "Interface debounce timer support";
  }

  revision 2022-09-13 {
    description
      "Added mac-learning";
  }

  revision 2022-05-09 {
    description
      "portsec fixes";
  }

  typedef fec-types {
    type enumeration {
      enum fec-none {
        value 1;
      }
      enum base-r {
        value 2;
      }
      enum rs {
        value 3;
      }
      enum rs-108 {
        value 4;
      }
      enum rs-206 {
        value 5;
      }
      enum rs-272 {
        value 6;
      }
      enum rs-304 {
        value 7;
      }
      enum rs-544 {
        value 8;
      }
      enum rs-545 {
        value 9;
      }
      enum rs-272-2xn {
        value 10;
      }
      enum rs-544-2xn {
        value 11;
      }
    }
  }

  typedef urpf-mode-types {
    type enumeration {
      enum none {
        value 0;
        description
          "Disable URPF mode";
      }
      enum loose {
        value 1;
        description
          "Enable loose URPF mode";
      }
      enum strict {
        value 2;
        description
          "Enable strict URPF mode";
      }
    }
    default none;
  }

  grouping dynamic-ipv4-address {
    description
      "Per IPv4 address configuration data for the
       interface.";

    leaf ip {
      type inet:ipv4-address-no-zone;
      description
        "[adapted from IETF IP model RFC 7277]

         The IPv4 address on the interface.";
    }
    leaf prefix-length {
      type uint8 {
        range "0..32";
      }
      description
        "[adapted from IETF IP model RFC 7277]

         The length of the subnet prefix.";
    }
  }

  grouping dynamic-ipv6-address {
    description
      "Per IPv6 address configuration data for the
       interface.";

    leaf ipv6 {
      type inet:ipv6-address-no-zone;
      description
        "[adapted from IETF IP model RFC 7277]

         The IPv6 address on the interface.";
    }
    leaf ipv6-prefix-length {
      type uint8 {
        range "0..128";
      }
      description
        "[adapted from IETF IP model RFC 7277]

         The length of the subnet prefix.";
    }
  }

  grouping dynamic-address-top {
    description
      "Subinterface data for logical interfaces
       associated with a physical interface.";

    container dynamic {
      config false;
      description
        "Enclosing container for the list of subinterfaces
         associated with a physical interface.";

      uses dynamic-ipv4-address;
      uses dynamic-ipv6-address;
    }
  }

  grouping subinterface-config {
    leaf network-instance {
      type string;
      description
        "The L3 network-instance that this subinterface is associated
         with.  When this leaf is unspecified, the subinterface is
         associated with the default network instance.";
    }
    leaf priority-vlan {
       type boolean;
       default false;
       description
       "Priority-vlan; It enables a predefined set of actions -
        ingress push vlan-0 and egress pop any";
       when "current()/../oc-if:index = 0";
    }

  }

  grouping if-error-counters {
    description
      "Error counters";

    leaf fcs-error {
      when "/oc-if:interfaces/oc-if:interface/oc-if:config/" +
           "oc-if:type = 'ianaift:ethernetCsmacd'" {
        description
        "FCS Error count";
      }
      type yang:counter64;
    }
    leaf align-error {
      when "/oc-if:interfaces/oc-if:interface/oc-if:config/" +
           "oc-if:type = 'ianaift:ethernetCsmacd'" {
        description
        "Alignment Error count";
      }
      type yang:counter64;
    }
    leaf symbol-error {
      when "/oc-if:interfaces/oc-if:interface/oc-if:config/" +
           "oc-if:type = 'ianaift:ethernetCsmacd'" {
        description
        "Symbol Error count";
      }
      type yang:counter64;
    }
    leaf runt-pkts {
      when "/oc-if:interfaces/oc-if:interface/oc-if:config/" +
           "oc-if:type = 'ianaift:ethernetCsmacd'" {
        description
        "Undersize pkt count";
      }
      type yang:counter64;
    }
  }

  grouping urpf-mode-config {
    leaf urpf-mode {
      description
        "Unicast Reverse Path Forwarding mode to use for this subinterface ";
      type urpf-mode-types;
    }
  }

  augment "/oc-if:interfaces/oc-if:interface/oc-if:subinterfaces/" +
          "oc-if:subinterface/oc-if:config" {
    uses subinterface-config;
    uses urpf-mode-config {
      when "derived-from-or-self(/arc-platform:platform/arc-platform:family, 'arc-platform:BROADCOM_DNX') or "
         + "derived-from-or-self(/arc-platform:platform/arc-platform:deployment-type, 'arc-platform:DISTRIBUTED') or "
         + "(/oc-sys:system/arc-oc-sys-aug:cli/arc-oc-sys-aug:config/arc-oc-sys-aug:unhide-unsupported-cli = 'true')";
    }
  }

  augment "/oc-if:interfaces/oc-if:interface/oc-if:subinterfaces/" +
          "oc-if:subinterface/oc-if:state" {
    leaf network-instance {
      type oc-ni:network-instance-ref;
      description
        "The L3 network-instance that this subinterface is associated with.
         When this leaf is unspecified, subinterface is associated with the
         the default network instance.";
    }
    uses urpf-mode-config;
    leaf priority-vlan {
       type boolean;
       description
       "Priority-vlan; It enables a predefined set of actions -
        ingress push vlan-0 and egress pop any";
       when "current()/../oc-if:index = 0";
    }

  }

  augment "/oc-if:interfaces/oc-if:interface/oc-if:state/oc-if:counters" {
    uses interface-counters;
  }

  augment "/oc-if:interfaces/oc-if:interface/oc-if:subinterfaces/" +
          "oc-if:subinterface/oc-if:state/oc-if:counters" {
    uses interface-counters;
  }

  grouping interface-counters {
    leaf in-bits-rate {
      type yang:counter64;
      description
      "input rate in bits";
    }
    leaf in-bits-rate-brief {
      type string;
      description
      "input rate in bits in string format";
    }
    leaf in-pkts-rate {
      type yang:counter64;
      description
      "input pkts rate";
    }
    leaf in-pkts {
      type yang:counter64;
      description
      "The total number of packets received on the interface,
      including all unicast, multicast, broadcast and bad packets
      etc.";
    }
    leaf out-bits-rate {
      type yang:counter64;
      description
      "output rate in bits";
    }
    leaf out-bits-rate-brief {
      type string;
      description
      "output rate in bits in string format";
    }
    leaf out-bits-rate-unit {
      type string;
      description
      "output rate unit";
    }
    leaf out-pkts-rate {
      type yang:counter64;
      description
      "output pkts rate";
    }
    leaf out-pkts {
      type yang:counter64;
      description
      "The total number of packets transmitted out of the
      interface, including all unicast, multicast, broadcast,
      and bad packets etc.";
    }
    leaf queue-drop-pkts {
      when "/oc-if:interfaces/oc-if:interface/oc-if:config/" +
           "oc-if:type = 'ianaift:ethernetCsmacd' and " +
           "/arc-features:features/arc-features:feature[arc-features:name='arc-features:ARCOS_QoS']" +
           "/arc-features:supported = 'true'" {
        description
        "Count of Queue Drop Packets";
      }
      type yang:counter64;
    }
    container errors {
      config false;
      description
        "Error counters";
      uses if-error-counters;
    }
    leaf in-ipv4-discards {
      type oc-yang:counter64;
      description
        "input ipv4 discards packets";
    }
    leaf in-stp-discards {
      type oc-yang:counter64;
      description
        "input stp discards packets";
    }
    leaf in-vlan-discards {
      type oc-yang:counter64;
      description
        "input vlan discards packets";
    }
    leaf in-tcam-discards {
      type oc-yang:counter64;
      description
        "input tcam discards packets";
    }
    leaf in-policy-discards {
      type oc-yang:counter64;
      description
        "input policy discards packets";
    }

    leaf carrier-transitions {
      type oc-yang:counter64;
      description
        "Number of times the interface state has transitioned between up and
         down since the time the device restarted or the last-clear time,
         whichever is most recent";
    }
    leaf giant-pkts {
      type yang:counter64;
      description
        "Oversize pkt count";
    }

    leaf in-mtu-exceeded-discards {
      type oc-yang:counter64;
      description
        "Input MTU exceeded discards packets";
    }

    leaf in-64-octet-pkts {
      type oc-yang:counter64;
      description
        "Input 64 octet packets";
    }

    leaf in-65to127-octet-pkts {
      type oc-yang:counter64;
      description
        "Input 65to127 octet packets";
    }

    leaf in-128to255-octet-pkts {
      type oc-yang:counter64;
      description
        "Input 128to255 octet packets";
    }

    leaf in-256to511-octet-pkts {
      type oc-yang:counter64;
      description
        "Input 256to511 octet packets";
    }

    leaf in-512to1023-octet-pkts {
      type oc-yang:counter64;
      description
        "Input 512to1023 octet packets";
    }

    leaf in-1024to1518-octet-pkts {
      type oc-yang:counter64;
      description
        "Input 1024to1518 octet packets";
    }

    leaf in-1519to2047-octet-pkts {
      type oc-yang:counter64;
      description
        "Input 1519to2047 octet packets";
    }

    leaf in-2048to4095-octet-pkts {
      type oc-yang:counter64;
      description
        "Input 2048to4095 octet packets";
    }

    leaf in-4096to9216-octet-pkts {
      type oc-yang:counter64;
      description
        "Input 4096to9216 octet packets";
    }

    leaf out-64-octet-pkts {
      type oc-yang:counter64;
      description
        "Output 64 octet packets";
    }

    leaf out-65to127-octet-pkts {
      type oc-yang:counter64;
      description
        "Output 65to127 octet packets";
    }

    leaf out-128to255-octet-pkts {
      type oc-yang:counter64;
      description
        "Output 128to255 octet packets";
    }

    leaf out-256to511-octet-pkts {
      type oc-yang:counter64;
      description
        "Output 256to511 octet packets";
    }

    leaf out-512to1023-octet-pkts {
      type oc-yang:counter64;
      description
        "Output 512to1023 octet packets";
    }

    leaf out-1024to1518-octet-pkts {
      type oc-yang:counter64;
      description
        "Output 1024to1518 octet packets";
    }

    leaf out-1519to2047-octet-pkts {
      type oc-yang:counter64;
      description
        "Output 1519to2047 octet packets";
    }

    leaf out-2048to4095-octet-pkts {
      type oc-yang:counter64;
      description
        "Output 2048to4095 octet packets";
    }

    leaf out-4096to9216-octet-pkts {
      type oc-yang:counter64;
      description
        "Output 4096to9216 octet packets";
    }

  }

  grouping port-security-top {
    container port-security {
      leaf profile {
        type leafref {
          path "/arc-portsec:port-security/arc-portsec:profiles/arc-portsec:" +
          "profile/arc-portsec:name";
        }
        description
          "Port security profile";
      }
      leaf enable {
        type boolean;
        description
          "Enable or disable security profile";
      }
      leaf-list static-mac-list {
        type yang:mac-address;
        description
          "Configured list of static macs";
      }
    }
  }

  grouping interface-config {
    leaf fec {
      when "/oc-if:interfaces/oc-if:interface/oc-if:config/" +
           "oc-if:type = 'ianaift:ethernetCsmacd'";
      description
      "Forward error correction type to use for this ethernet interface";
      type fec-types;
    }

    leaf autostate {
      type boolean;
      when "/oc-if:interfaces/oc-if:interface/oc-if:config/" +
           "oc-if:type = 'ianaift:l3ipvlan'";
      description
        "Enable/disable interface state management on this interface";
    }

    leaf mac-learning {
      type boolean;
      default true;
      when "derived-from-or-self(current()/../oc-if:type, 'ianaift:ethernetCsmacd') or " +
           "derived-from-or-self(current()/../oc-if:type, 'ianaift:ieee8023adLag')";
      description
        "When this leaf is set to true, MAC learning is enabled for
        the interface, such that MAC addresses are learned
        from ingress frames and added to the FDB.";
    }

    leaf load-interval {
      type uint16 {
        range 5..300;
      }
      description "Interface counter load interval in seconds";
    }

    leaf custom-mac {
      type boolean;
      default false;
      description
        "Custom mac of the interface";
    }

    leaf link-training {
      type boolean;
      default false;
      description
        "Enable Link Training for the interface";
    }

    uses port-security-top {
      when "../oc-eth:ethernet/" +
           "oc-vlan:switched-vlan/oc-vlan:config/oc-vlan:interface-mode = 'ACCESS'" {
         description "Port security enabled only on ACCESS interfaces";
      }
    }
  }

  grouping interface-state {
    leaf load-interval {
      type uint16;
      description
        "Interface counter load interval in seconds";
    }

    leaf media-type {
      type string;
      description
        "Media type of the interface";
    } 

    leaf unit {
      type uint8 {
        range "0..1"; 
      } 
      description 
        "Unit number of the interface"; 
    } 
   
    leaf core { 
      type uint8 { 
        range "0..1"; 
      }
      description 
        "Core number of the interface"; 
    } 
  
    leaf module-type {
      type string;
      description
        "Module type of the interface";
    }

    leaf fec {
      type fec-types;
      when "/oc-if:interfaces/oc-if:interface/oc-if:config/" +
           "oc-if:type = 'ianaift:ethernetCsmacd'";
      description
        "Operational value of forward error correction type in use for this interface";
    }

    leaf fec-corrected-errors {
      type uint64;
      when "/oc-if:interfaces/oc-if:interface/oc-if:config/" +
           "oc-if:type = 'ianaift:ethernetCsmacd'";
      description
        "Count of FEC corrected errors";
    }

    leaf fec-uncorrected-errors {
      type uint64;
      when "/oc-if:interfaces/oc-if:interface/oc-if:config/" +
           "oc-if:type = 'ianaift:ethernetCsmacd'";
      description
        "Count of FEC uncorrected errors";
    }

    leaf pre-fec-ber {
      type string;
      when "/oc-if:interfaces/oc-if:interface/oc-if:config/" +
           "oc-if:type = 'ianaift:ethernetCsmacd'";
      description
        "Pre-Forward Error Correction (FEC) Bit Error Rate (BER) value.
         This value represents the bit error rate before FEC correction
         in scientific notation (e.g., 1.23e-12).";
    }

    leaf speed-group {
      type uint8;
      when "/oc-if:interfaces/oc-if:interface/oc-if:config/" +
           "oc-if:type = 'ianaift:ethernetCsmacd'";
      description
        "Speed group that this interface belongs to";
    }
    
    leaf breakout { 
      type boolean; 
      description "Breakout enabled";
    } 
    
    leaf parent-port {
      type uint16;
      description "Parent port of the interface"; 
    } 
    
    leaf paired-port {
      type uint16; 
      description "Paired port of the interface"; 
    }  

    leaf autostate {
      type boolean;
      when "/oc-if:interfaces/oc-if:interface/oc-if:config/" +
           "oc-if:type = 'ianaift:l3ipvlan'";
      description
        "Operation value of interface state management used for this interface";
    }

    leaf mac-learning {
      type boolean;
      when "derived-from-or-self(current()/../oc-if:type, 'ianaift:ethernetCsmacd') or " +
           "derived-from-or-self(current()/../oc-if:type, 'ianaift:ieee8023adLag')";
      description
        "Operation value of mac learning for this interface";
    }

    leaf custom-mac {
      type boolean;
      default false;
      description
        "Custom mac of the interface";
    }

    leaf link-training {
      type boolean;
      default false;
      description
        "Enable Link Training for the interface";
    }

    leaf errDisable {
      type string;
      description
        "Interface disable reason";
    }
    leaf time-elapsed-since-last-change {
      type string;
      description
        "Time Elapsed since last state change";
    }
    uses dynamic-address-top;
  }

  grouping debounce-info {
    description
      "Configuration and State data for interface debounce";

    leaf up {
      type uint32 {
        range 0..600000;
      }
      units "milliseconds";
      description "Interface debounce (from DOWN to UP) interval in milliseconds";
    }

    leaf down {
      type uint32 {
        range 0..600000;
      }
      units "milliseconds";
      description "Interface debounce (from UP to DOWN) interval in milliseconds";
    }
  }

  grouping debounce-logical-top {
    description "Top-level data definitions for interface debounce";

    container debounce-interval {
      description
        "Configuration and State for interface debounce interval";

      uses debounce-info;
      must
      "not(../../arc-oc-if-aug:damping/arc-oc-if-aug:config/arc-oc-if-aug:enabled = 'true') or " +
      "(not(./arc-oc-if-aug:up) and not(./arc-oc-if-aug:down)) " {
        error-message "Debounce Interval and Interface Damping cannot
        co-exist on the same interface";
      }
    }
  }

grouping damping-info {
    description
      "Configuration data for interface link damping settings.";

    leaf enabled {
      type boolean;
      default "false";
      description
        "When set to true, enables interface damping";
    }

    leaf max-suppress-time {
      type uint32 {
        range 10000..100000;
      }
      units milliseconds;
      default 20000;
      must "current() >= ../decay-half-life" {
        error-message "Max-suppress-time must not be less than decay-half-life.";
      }
      description
        "Maximum time an interface can remain damped since the last link down event.";
    }

    leaf decay-half-life {
      type uint32 {
        range 2000..30000;
      }
      units milliseconds;
      default 5000;
      description
        "The amount of time after which an interface's penalty is decreased by half.";
    }

    leaf suppress-threshold {
      type uint32 {
        range 1000..20000;
      }
      default 5000;
      description
        "The accumulated penalty that triggers the damping of an interface.";
    }

    leaf reuse-threshold {
      type uint32 {
        range 1000..20000;
      }
      default 2000;
      must "current() <= ../suppress-threshold" {
        error-message "Reuse Threshold must not be more than suppress-threshold.";
      }
      description
        "When the accumulated penalty decreases to this reuse threshold, the interface is not damped anymore.";
    }

    leaf flap-penalty {
      type uint32 {
        range 500..5000;
      }
      default 1000;
      description
        "A penalty that each down event costs.";
    }
  }

  grouping damping-logical-top {
    description "Top-level data definitions for interface damping";

    container damping {
      description
        "Configuration and State for interface debounce interval";

      container config {
        description
          "Interface Damping configuration";

        uses damping-info;
      }

      container state {
        config false;

        description
          "Interface Damping State";

        leaf suppress_state {
            type boolean;
            default "false";
            description
                "When set to true interface is in suppressed state";
        }

        leaf penalty_count {
            type uint64;
            description
                "Current penalty count associated with the interface";
        }

        uses damping-info;
      }
    }
  }

  augment "/oc-if:interfaces/oc-if:interface/oc-if:config" {
    uses interface-config;
  }

  augment "/oc-if:interfaces/oc-if:interface/oc-if:config" {
    uses debounce-logical-top {
      when "derived-from-or-self(./oc-if:type, 'ianaift:ethernetCsmacd') ";
    }
  }

  augment "/oc-if:interfaces/oc-if:interface" {
    uses damping-logical-top {
      when "derived-from-or-self(./oc-if:config/oc-if:type, 'ianaift:ethernetCsmacd') ";
    }
  }

  augment "/oc-if:interfaces/oc-if:interface/oc-if:state" {
    uses interface-state;
  }

  augment "/oc-if:interfaces/oc-if:interface/oc-if:state" {
    uses debounce-logical-top {
      when "starts-with(current()/../oc-if:name, 'swp')";
    }
  }

  grouping l2cp-tunnel-config {
    description
      "L2CP-tunnel mode information";

    leaf l2cp-tunnel {
      type boolean;
      default false;
      description
        "L2CP-tunnel mode is enabled if true, otherwise it is not enabled";
    }
  }

  grouping etree-leaf-config {
    description
      "grouping for etree-leaf AC configuration and operation data";

    leaf etree-leaf {
      type boolean;
      default false;
      description
        "etree-leaf AC is enabled if true, otherwise it is not enabled";
    }
  }

  augment "/oc-if:interfaces/oc-if:interface/oc-if:subinterfaces/" +
          "oc-if:subinterface/oc-if:config" {
    uses l2cp-tunnel-config {
      when "not(derived-from-or-self(../../../oc-if:config/oc-if:type,"
         + "'ianaift:ieee8023adLag')) or "
         + "../../../oc-lag:aggregation/oc-lag:config/oc-lag:lag-type"
	 + " != 'LACP'";
    }
  }

  augment "/oc-if:interfaces/oc-if:interface/oc-if:subinterfaces/" +
          "oc-if:subinterface/oc-if:config" {
    description
      "Augment to add  etree-leaf AC configuration to sub-interfaces";
    uses etree-leaf-config;
  }

  augment "/oc-if:interfaces/oc-if:interface/oc-if:subinterfaces/" +
          "oc-if:subinterface/oc-if:state" {
    description
      "Augment to add  etree-leaf AC operational state to sub-interfaces";
    uses etree-leaf-config;
  }

  augment "/oc-if:interfaces/oc-if:interface/oc-if:subinterfaces/" +
          "oc-if:subinterface/oc-if:state" {
    uses l2cp-tunnel-config{
      when "not(derived-from-or-self(../../../oc-if:config/oc-if:type,"
         + "'ianaift:ieee8023adLag')) or "
         + "../../../oc-lag:aggregation/oc-lag:config/oc-lag:lag-type"
	 + "!= 'LACP'";
    }
  }

}
