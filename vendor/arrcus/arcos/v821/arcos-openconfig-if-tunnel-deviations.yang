module arcos-openconfig-if-tunnel-deviations {
  yang-version 1.1;
  namespace "http://yang.arrcus.com/arcos/openconfig/if-tunnel/deviations";
  prefix arc-oc-if-tun-dev;

  import openconfig-if-tunnel {
    prefix oc-tun;
  }

  import ietf-inet-types { 
    prefix inet;
  }

  import openconfig-interfaces { prefix oc-if; }
  import iana-if-type { prefix ianaift; }
  import openconfig-if-ip { prefix oc-ip; }

  organization
    "Arrcus, Inc.";

  contact
    "Arrcus, Inc.
     2077 Gateway Place
     Suite 400
     San Jose, CA 95110

     E-mail: yang-support@arrcus.com";

  description
    "This module defines ArcOS deviations to the
     OpenConfig if-tunnel module.

     Copyright (c) 2016-2019 by Arrcus, Inc.
     All rights reserved.";

  deviation "/oc-if:interfaces/oc-if:interface" +
            "/oc-tun:tunnel/oc-tun:config/oc-tun:gre-key" {
    deviate not-supported;
    description "Not supported in this release";
  }

  deviation "/oc-if:interfaces/oc-if:interface" +
            "/oc-tun:tunnel/oc-tun:ipv4" {
    deviate not-supported;
    description "Not supported in this release";
  }

  deviation "/oc-if:interfaces/oc-if:interface" +
            "/oc-tun:tunnel/oc-tun:ipv6" {
    deviate not-supported;
    description "Not supported in this release";
  }

  deviation "/oc-if:interfaces/oc-if:interface" +
            "/oc-tun:tunnel/oc-tun:config/oc-tun:src" {
    deviate replace {
      type inet:ip-address;
    }
  }

  deviation "/oc-if:interfaces/oc-if:interface" +
            "/oc-tun:tunnel/oc-tun:config/oc-tun:dst" {
    deviate replace {
      type inet:ip-address;
    }
  }
}
