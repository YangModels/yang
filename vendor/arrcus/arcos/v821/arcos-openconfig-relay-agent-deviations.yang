module arcos-openconfig-relay-agent-deviations {
  yang-version 1.1;
  namespace "http://yang.arrcus.com/arcos/openconfig/relay-agent/deviations";
  prefix arc-oc-relay-dev;

  import openconfig-relay-agent {
    prefix oc-relay;
  }

  organization
    "Arrcus, Inc.";

  contact
    "Arrcus, Inc.
     2077 Gateway Place
     Suite 400
     San Jose, CA 95110

     E-mail: yang-support@arrcus.com";

  description
    "This module defines ArcOS deviations to the
     OpenConfig relay-agent module.

     Copyright (c) 2022 by Arrcus, Inc.
     All rights reserved.";

  revision 2022-09-12 {
    description
      "Re-enabled DHCPv6 interface-id option and per-interface DHCPv6 helper-address";
  }

  revision 2022-07-21 {
    description
      "Added back deviated out per interface DHCPv4 helper-address";
  }

  deviation "/oc-relay:relay-agent/oc-relay:dhcp" +
            "/oc-relay:config/oc-relay:enable-relay-agent" {
    deviate not-supported;
    description "Not supported in this release";
  }

  deviation "/oc-relay:relay-agent/oc-relay:dhcpv6" +
            "/oc-relay:config/oc-relay:enable-relay-agent" {
    deviate not-supported;
    description "Not supported in this release";
  }

  deviation "/oc-relay:relay-agent/oc-relay:dhcp/oc-relay:interfaces" +
            "/oc-relay:interface/oc-relay:config/oc-relay:enable" {
    deviate add {
      default true;
    }
  }

  deviation "/oc-relay:relay-agent/oc-relay:dhcp/oc-relay:interfaces" +
            "/oc-relay:interface/oc-relay:agent-information-option" +
            "/oc-relay:config/oc-relay:circuit-id" {
    deviate replace {
      type string {
        pattern '[A-Za-z0-9/:\-\+\._#@\[\]~\{\}=\^]{1,63}';
      }
    }
  }

  deviation "/oc-relay:relay-agent/oc-relay:dhcp/oc-relay:interfaces" +
            "/oc-relay:interface/oc-relay:state/oc-relay:counters" {
    deviate not-supported;
    description "Not supported in this release";
  }

  deviation "/oc-relay:relay-agent/oc-relay:dhcp/oc-relay:interfaces" +
            "/oc-relay:interface/oc-relay:agent-information-option" +
            "/oc-relay:config/oc-relay:enable" {
    deviate not-supported;
    description "Not supported in this release";
  }

  deviation "/oc-relay:relay-agent/oc-relay:dhcp/oc-relay:interfaces" +
            "/oc-relay:interface/oc-relay:agent-information-option" +
            "/oc-relay:config/oc-relay:remote-id" {
    deviate not-supported;
    description "Not supported in this release";
  }

  deviation "/oc-relay:relay-agent/oc-relay:dhcp/oc-relay:interfaces" +
            "/oc-relay:interface/oc-relay:agent-information-option" +
            "/oc-relay:state/oc-relay:enable" {
    deviate not-supported;
    description "Not supported in this release";
  }

  deviation "/oc-relay:relay-agent/oc-relay:dhcp/oc-relay:interfaces" +
            "/oc-relay:interface/oc-relay:agent-information-option" +
            "/oc-relay:state/oc-relay:remote-id" {
    deviate not-supported;
    description "Not supported in this release";
  }

  deviation "/oc-relay:relay-agent/oc-relay:dhcp/oc-relay:interfaces" +
            "/oc-relay:interface/oc-relay:agent-information-option" +
            "/oc-relay:state/oc-relay:sent-remote-id" {
    deviate not-supported;
    description "Not supported in this release";
  }

  deviation "/oc-relay:relay-agent/oc-relay:dhcpv6/oc-relay:options" +
  	    "/oc-relay:config/oc-relay:enable-remote-id"
  {
    deviate not-supported;
    description "Not supported in this release";
  }

  deviation "/oc-relay:relay-agent/oc-relay:dhcpv6/oc-relay:options" +
  	    "/oc-relay:state/oc-relay:enable-remote-id"
  {
    deviate not-supported;
    description "Not supported in this release";
  }

  deviation "/oc-relay:relay-agent/oc-relay:dhcpv6/oc-relay:interfaces" +
            "/oc-relay:interface/oc-relay:config/oc-relay:enable" {
    deviate add {
      default true;
    }
  }

  deviation "/oc-relay:relay-agent/oc-relay:dhcpv6/oc-relay:interfaces" +
            "/oc-relay:interface/oc-relay:state/oc-relay:counters" {
    deviate not-supported;
    description "Not supported in this release";
  }

  deviation "/oc-relay:relay-agent/oc-relay:dhcpv6/oc-relay:interfaces" +
            "/oc-relay:interface/oc-relay:options/oc-relay:config" +
	    "/oc-relay:enable-remote-id" {
    deviate not-supported;
    description "Not supported in this release";
  }

  deviation "/oc-relay:relay-agent/oc-relay:dhcpv6/oc-relay:interfaces" +
            "/oc-relay:interface/oc-relay:options/oc-relay:config" +
	    "/oc-relay:remote-id" {
    deviate not-supported;
    description "Not supported in this release";
  }

  deviation "/oc-relay:relay-agent/oc-relay:dhcpv6/oc-relay:interfaces" +
            "/oc-relay:interface/oc-relay:options/oc-relay:state" +
	    "/oc-relay:enable-remote-id" {
    deviate not-supported;
    description "Not supported in this release";
  }

  deviation "/oc-relay:relay-agent/oc-relay:dhcpv6/oc-relay:interfaces" +
            "/oc-relay:interface/oc-relay:options/oc-relay:state" +
	    "/oc-relay:remote-id" {
    deviate not-supported;
    description "Not supported in this release";
  }

  deviation "/oc-relay:relay-agent/oc-relay:dhcpv6/oc-relay:interfaces" +
            "/oc-relay:interface/oc-relay:options/oc-relay:state" +
	    "/oc-relay:sent-remote-id" {
    deviate not-supported;
    description "Not supported in this release";
  }

  deviation "/oc-relay:relay-agent/oc-relay:dhcpv6/oc-relay:interfaces" +
            "/oc-relay:interface/oc-relay:options" +
            "/oc-relay:config/oc-relay:interface-id" {
    deviate replace {
      type string {
        pattern '[A-Za-z0-9/:\-\+\._#@\[\]~\{\}=\^]{1,63}';
      }
    }
  }

  deviation "/oc-relay:relay-agent/oc-relay:dhcpv6/oc-relay:interfaces" +
            "/oc-relay:interface/oc-relay:options" +
            "/oc-relay:config/oc-relay:enable-interface-id" {
    deviate not-supported;
    description "Not supported in this release";
  }

  deviation "/oc-relay:relay-agent/oc-relay:dhcpv6/oc-relay:interfaces" +
            "/oc-relay:interface/oc-relay:options" +
            "/oc-relay:state/oc-relay:enable-interface-id" {
    deviate not-supported;
    description "Not supported in this release";
  }

}
