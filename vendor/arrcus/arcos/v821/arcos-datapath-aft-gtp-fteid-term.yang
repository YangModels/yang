submodule arcos-datapath-aft-gtp-fteid-term {
  yang-version "1.1";

  belongs-to "arcos-datapath-aft" {
    prefix "arcos-dp-aft";
  }

  import ietf-inet-types { prefix "inet"; }
  import arcos-aft-types { prefix "arc-aft-types"; }

  // Include common cross-AFT groupings from the common submodule.
  include arcos-datapath-aft-common;

  organization
    "Arrcus, Inc.";

  contact
    "Arrcus, Inc.
     2077 Gateway Place
     Suite 400
     San Jose, CA 95110

     E-mail: yang-support@arrcus.com";

  description
    "Submodule containing definitions of groupings for the abstract
     forwarding table for GTP FTEID Termination Objects.

     Copyright (c) 2024 by Arrcus, Inc.
     All rights reserved.";

  revision "2024-05-02" {
    description
      "Initial Version";
  }

  grouping aft-gtp-fteid-term-entry-state {
    description
      "Operational state parameters for the GTP FTEID Term entry.";
    leaf outer-vrf-id {
      type uint32;
      description
        "Outer VRF id in use for the entry";
    }

    leaf dst-prefix {
      type inet:ipv6-prefix;
      description
        "IPv6 Destination Prefix of the GTP FTEID term obj";
    }

    leaf teid {
      type inet:ipv4-prefix;
      description
        "IPv4 TEID of the GTP FTEID term obj";
    }

    leaf inner-vrf-id {
      type uint32;
      description
        "Inner VRF of GTP FTEID term obj";
    }
  }

  grouping aft-gtp-fteid-term-structural {
    description
      "Structural grouping defining the schema for the GTP FTEID Term
      table.";

    list gtp-fteid-term-entry {
      key "outer-vrf-id dst-prefix teid";

      description
        "List of the GTP FTEID Term entries within the abstract
        forwarding table. This list is keyed by the outer vrf id.";

      leaf outer-vrf-id {
        type uint32;
        description
          "Outer vrf id matched by the entry.";
      }

      leaf dst-prefix {
        type inet:ipv6-prefix;
        description
          "Destination address matched by the entry.";
      }

      leaf teid {
        type inet:ipv4-prefix;
        description
          "Flow tunnel endpoint id address matched by the entry.";
      }

      container state {
        config false;
        description
          "Operational state parameters for the GTP FTEID Term AFT entry.";
        uses aft-gtp-fteid-term-entry-state;
      }

    }
  }
}
