module arcos-openconfig-routing-policy-augments {
  yang-version 1.1;
  namespace "http://yang.arrcus.com/arcos/openconfig/routing-policy/augments";
  prefix arc-oc-rpol-aug;

  import openconfig-routing-policy {
    prefix oc-rpol;
  }

  import ietf-inet-types {
    prefix inet;
  }
  
  import arcos-oam {
    prefix arc-oam;
  }

  import arcos-features {
    prefix arc-features;
  }

  organization
    "Arrcus, Inc";

  contact
    "Arrcus, Inc.
    2077 Gateway Place,
    San Jose, CA 95110
    Tel: +1 (408) 884-1965
    E-mail: yang-support@arrcus.com";

  description
    "This module defines augmentation of Arrcus
    implemention to the openconfig routing-policy module.
    Copyright (c) 2016-2024 by Arrcus, Inc.
    All rights reserved.";

  revision 2024-07-23 {
    description "Adding match-method matching for string";
  }

  revision 2023-12-07 {
    description "Remove n4-network-instance-set defined set";
  }

  revision 2023-09-29 {
    description "Add defined-sets for string list";
  }

  revision 2023-09-26 {
    description
      "Add conditional enable of MUP specific routing policy config";
  }

  revision 2019-10-29 {
    description
      "Initial version";
  }

  typedef next-hop-type {
    type union {
      type inet:ip-address;
      type inet:ip-prefix;
      type enumeration {
        enum SELF {
          description "special designation for local router's own
          address, i.e., next-hop-self";
        }
      }
    }
    description
      "type definition for specifying next-hop in policy actions";
  }

  grouping next-hop-set-config {
    description
      "Configuration data for next-hop set definitions";

    leaf next-hop-set-name {
      type string {
        length "1..79";
      }
      mandatory true;
      description
          "name / label of the next-hop set -- this is used to
          reference the set in match conditions";
    }

    leaf-list address {
      type next-hop-type;
      max-elements 32;
      description
        "List of IP addresses in the next-hop set";
    }
  }

  grouping next-hop-set-state {
    description
      "Operational state data for next-hop set definitions";
  }

  grouping next-hop-set-top {
    description
      "Top-level data definition for a list of IPv4 or IPv6
      next-hops which can be matched in a routing policy";

    container next-hop-sets {
      description
        "Enclosing container for the list of next-hop set
        definitions";

      list next-hop-set {
        key "next-hop-set-name";
        description
          "List of defined next-hop sets for use in policies.";

        leaf next-hop-set-name {
          type leafref {
            path "../config/next-hop-set-name";
          }
          description
            "Reference to the next-hop set name list key.";
        }

        container config {
          description
            "Configuration data for next-hop sets.";

          uses next-hop-set-config;
        }

        container state {

          config false;

          description
            "Operational state data for next-hop sets.";

          uses next-hop-set-config;
          uses next-hop-set-state;
        }
      }
    }
  }

  grouping string-member-value-config {
    leaf string-value {
      type string {
        length "1..255";
      }
      mandatory true;
      description
        "String list member value";
    }

    leaf type {
      type enumeration {
        enum EXACT {
          value 1;
        }
        enum REGULAR_EXPRESSION {
          value 2;
        }
      }
      default EXACT;
    }
  }

  grouping string-members-config {
    container strings {
      list string {
        key "string-value";
        max-elements 32;

        leaf string-value {
          type leafref {
            path "../config/string-value";
          }
          description
            "String list member value";
        }
        container config {
          uses string-member-value-config;
        }
        container state {
          config false;
          uses string-member-value-config;
        }
      }
    }
  }

  grouping string-set-config {
    description
      "Configuration data for string set definitions";

    leaf name {
      type string {
        length "1..79";
      }
      description
          "name / label of the string set -- this is used to
          reference the set in match conditions";
    }

    leaf-list string-set-reference {
      type leafref {
        path "/oc-rpol:routing-policy/oc-rpol:defined-sets" +
             "/arc-oc-rpol-aug:string-sets/arc-oc-rpol-aug:string-set" +
             "/arc-oc-rpol-aug:name";
      }
      description
        "Reference to another string set to be used";
    }
  }

  grouping string-set-top {
    description
      "Top-level data definition for a list of strings
       which can be matched in a routing policy";

    container string-sets {
      description
        "Enclosing container for the list of string set
         definitions";

      list string-set {
        key "name";
        description
          "List of defined string sets for use in policies.";

        leaf name {
          type leafref {
            path "../config/name";
          }
          description
            "Reference to the string set name list key.";
        }

        container config {
          description
            "Configuration data for string sets.";
          uses string-set-config;
        }

        container state {
          config false;
          description
            "Operational state data for string sets.";
          uses string-set-config;
        }

        uses string-members-config;
      }
    }
  }

  grouping stmt-top {
    leaf auto-seq-num {
      type uint64;
      description
        "Auto generated sequence number";
    }
  }

  augment "/oc-rpol:routing-policy/oc-rpol:policy-definitions" +
          "/oc-rpol:policy-definition/oc-rpol:statements" +
          "/oc-rpol:statement/oc-rpol:state" {
    uses stmt-top;
  }

  grouping srv6-oam-set-profile-config {
    description
      "Setting OAM profile";
    leaf set-profile {
      type leafref {
        path "/arc-oam:oam/arc-oam:profiles/arc-oam:profile/arc-oam:name";
      }
      description
        "Set the SRv6 OAM profile for tracking next-hop health status";
    }
  }
  grouping srv6-oam-actions-top {
    container srv6-oam-actions {
      description
        "Actions specific to SRv6 OAM";
      container config {
        description
          "Configuration parameters for setting OAM profile";
        uses srv6-oam-set-profile-config;
      }
      container state {
        config false;
        description
          "State parameters for setting OAM profile";
        uses srv6-oam-set-profile-config;
      }
    }
  }

  grouping stmt-actions-top {
    leaf next-policy {
      type empty;
      description
        "skip to the next policy module";
    }
  }

  augment "/oc-rpol:routing-policy/oc-rpol:policy-definitions" +
          "/oc-rpol:policy-definition/oc-rpol:statements/oc-rpol:statement" +
          "/oc-rpol:actions" {
    uses srv6-oam-actions-top;
  }

  augment "/oc-rpol:routing-policy/oc-rpol:policy-definitions" +
          "/oc-rpol:policy-definition/oc-rpol:statements/oc-rpol:statement" +
          "/oc-rpol:actions/oc-rpol:config" {
    description "Policy action for skipping to next policy module";

    uses stmt-actions-top;
  }

  augment "/oc-rpol:routing-policy/oc-rpol:policy-definitions" +
          "/oc-rpol:policy-definition/oc-rpol:statements/oc-rpol:statement" +
          "/oc-rpol:actions/oc-rpol:state" {
    description "Policy action for skipping to next policy module";

    uses stmt-actions-top;
  }

  grouping stmt-conditions-top {
    leaf call-policy-expression {
      type string;
      description
        "logical expression of combinations of policy names, each of " +
        "which will be called as a call-policy. Logical operations allowed " +
        "include ~ (negate), + (or), * (and), ^ (xor), and parentheses. " +
        "The condition will be a pass if the logical expression evaluates " +
        "to true. Each call-policy's result will be true if it returns " +
        "accept-route.";
    }
  }

  augment "/oc-rpol:routing-policy/oc-rpol:policy-definitions" +
          "/oc-rpol:policy-definition/oc-rpol:statements/oc-rpol:statement" +
          "/oc-rpol:conditions/oc-rpol:config" {
    description "Policy condition for call-policy-expression";

    uses stmt-conditions-top;
  }

  augment "/oc-rpol:routing-policy/oc-rpol:policy-definitions" +
          "/oc-rpol:policy-definition/oc-rpol:statements/oc-rpol:statement" +
          "/oc-rpol:conditions/oc-rpol:state" {
    description "Policy condition for call-policy-expression";

    uses stmt-conditions-top;
  }

  grouping prefix-set-reference-config {
    description
      "Configuration data for prefix-set member set references for prefix-sets";
    leaf-list prefix-set-reference {
      type leafref {
        path "/oc-rpol:routing-policy/oc-rpol:defined-sets/oc-rpol:prefix-sets" +
          "/oc-rpol:prefix-set/oc-rpol:prefix-set-name";
      }
      max-elements 32;
      description
        "References to defined prefix-sets that are included in current one";
    }
  }

  augment "/oc-rpol:routing-policy/oc-rpol:defined-sets" +
          "/oc-rpol:prefix-sets/oc-rpol:prefix-set/oc-rpol:config" {

    uses prefix-set-reference-config;
  }

  augment "/oc-rpol:routing-policy/oc-rpol:defined-sets" +
          "/oc-rpol:prefix-sets/oc-rpol:prefix-set/oc-rpol:state" {

    uses prefix-set-reference-config;
  }

  augment "/oc-rpol:routing-policy/oc-rpol:defined-sets" {
    description
      "Arrcus augmented defined sets to defined-set container";
    uses next-hop-set-top;
    uses string-set-top;
  }

  grouping match-next-hop-set-config {
    description
      "Configuration data for match conditions on next-hops";
    leaf next-hop-set {
      type leafref {
        path "/oc-rpol:routing-policy/oc-rpol:defined-sets" +
             "/arc-oc-rpol-aug:next-hop-sets/arc-oc-rpol-aug:next-hop-set" +
             "/arc-oc-rpol-aug:next-hop-set-name";
      }
      description
        "References a defined next-hop set";
    }
    uses oc-rpol:match-set-options-group;
  }

  grouping match-next-hop-set-state {
    description
      "Operational state data for match conditions on next-hops";
  }

  grouping match-next-hop-set-top {
    description
      "Top-level grouping for match conditions on next-hops";
    container match-next-hop-set {
      description
        "Top-level container for match conditions on next-hop.
         Match a referenced next-hop-set according to the logic
         defined in the match-set-options leaf";
      container config {
        description
          "Configuration data for match conditions on large communities";
        uses match-next-hop-set-config;
      }
      container state {
        config false;
        description
          "Operational state data ";
        uses match-next-hop-set-config;
        uses match-next-hop-set-state;
      }
    }
  }

  augment "/oc-rpol:routing-policy" +
          "/oc-rpol:policy-definitions/oc-rpol:policy-definition" +
          "/oc-rpol:statements/oc-rpol:statement" +
          "/oc-rpol:conditions" {
    description
      "adds next-hop set to conditions";
    uses match-next-hop-set-top;
  }
}
