submodule arcos-hardware-ecmp {
  yang-version 1.1;

  belongs-to arcos-hardware {
    prefix arc-hw;
  }

  import arcos-platform {
    prefix arc-platform;
  }

  grouping hardware-ecmp {
    description "Controls for tuning ECMP hashing behavior";
    leaf hash-seed-value {
      type uint32;
      description "ECMP hash seed value";
      must "current() >= 0 and current() <= 65535 or" +
           " /arc-platform:platform/arc-platform:family = 'arc-platform:BROADCOM_XGS'" {
        error-message "ECMP hash seed value should be in the range of 0..65535, for Broadcom DNX devices";
      }
    }

    leaf hash-offset {
      type uint8;
      description "ECMP Hash offset value";
      when "(derived-from-or-self(/arc-platform:platform/arc-platform:family, 'arc-platform:BROADCOM_XGS'))";
      must "current() >= 0 and current() <= 15 or" +
           " /arc-platform:platform/arc-platform:family = 'arc-platform:BROADCOM_XGS'" {
        error-message "ECMP hash offset should be in the range of 0..15, for Broadcom DNX devices";
      }
      must "current() >= 0 and current() <= 199 or" +
           " (/arc-platform:platform/arc-platform:family = 'arc-platform:BROADCOM_DNX') or" +
           " (/arc-platform:platform/arc-platform:family = 'arc-platform:BROADCOM_DNX_JPLUS')" {
        error-message "ECMP hash offset should be in the range of 0..199, for Broadcom XGS devices";
      }
    }

    leaf hash-function-polynomial {
      type uint8;
      description "ECMP hash polynomial";
      when "(derived-from-or-self(/arc-platform:platform/arc-platform:family, 'arc-platform:BROADCOM_XGS'))";
      must "current() >= 1 and current() <= 13 or" +
           " (/arc-platform:platform/arc-platform:family = 'arc-platform:BROADCOM_DNX') or" +
           " (/arc-platform:platform/arc-platform:family = 'arc-platform:BROADCOM_DNX_JPLUS')" {
        error-message "ECMP hash polynomial should be in the range of 1..13, for Broadcom XGS devices";
      }
      must "current() >= 22 and current() <= 27 or" +
           " /arc-platform:platform/arc-platform:family = 'arc-platform:BROADCOM_XGS'" {
        error-message "ECMP hash polynomial should be in the range of 22..27, for Broadcom DNX devices";
      }
    }

    container hash-fields-ipv4 {
      description "ECMP IPv4 header fields";
      when "(derived-from-or-self(/arc-platform:platform/arc-platform:family, 'arc-platform:BROADCOM_XGS'))";
      leaf src-ip {
        type boolean;
        default true;
        description "Use source ip address for hash computation";
      }
      leaf dst-ip {
        type boolean;
        default true;
        description "Use destination ip address for hash computation";
      }
      leaf src-port {
        type boolean;
        default true;
        description "Use source L4 port for hash computation";
      }
      leaf dst-port {
        type boolean;
        default true;
        description "Use destination L4 port for hash computation";
      }
      leaf proto {
        type boolean;
        default true;
        description "Use IP protocol for hash computation";
      }
    }

    container hash-fields-ipv6 {
      description "ECMP IPv6 header fields";
      when "(derived-from-or-self(/arc-platform:platform/arc-platform:family, 'arc-platform:BROADCOM_XGS'))";
      leaf src-ip {
        type boolean;
        default true;
        description "Use source ip address for hash computation";
      }
      leaf dst-ip {
        type boolean;
        default true;
        description "Use destination ip address for hash computation";
      }
      leaf src-port {
        type boolean;
        default true;
        description "Use source L4 port for hash computation";
      }
      leaf dst-port {
        type boolean;
        default true;
        description "Use destination L4 port for hash computation";
      }
    }

    container hash-fields-l2 {
      description "ECMP L2 header fields";
      when "(derived-from-or-self(/arc-platform:platform/arc-platform:family, 'arc-platform:BROADCOM_XGS'))";
      leaf vlan {
        type boolean;
        default true;
        description "Use vlan ID for hash computation";
      }
      leaf eth-type {
        type boolean;
        default true;
        description "Use ethertype for hash computation";
      }
      leaf src-mac {
        type boolean;
        default true;
        description "Use source MAC address for hash computation";
      }
      leaf dst-mac {
        type boolean;
        default true;
        description "Use destination MAC address for hash computation";
      }
    }

    uses hash-fields-dnx {
      when "(derived-from-or-self(/arc-platform:platform/arc-platform:family, 'arc-platform:BROADCOM_DNX'))";
    }

    container hash-mpls {
      description "MPLS Speculative next protocol";
      container speculate-next-protocol {
        description "Set the speculative parsing to the expected next protocol 
                     after the MPLS BoS label";
        leaf control-word {
          type boolean;
          default false;
          description "Set the speculative parsing to MPLS Next protocol  
                      ControlWord if the nibble value following BoS label is 0"; 
        }
      }
      leaf all-labels {
        type boolean;
        default false;
        description "Use all labels including terminated labels in hash computation";
      } 
      when "(derived-from-or-self(/arc-platform:platform/arc-platform:family, 'arc-platform:BROADCOM_DNX'))";
    }
  }

  grouping hash-fields-dnx { 
    container hash-ipv4 {
      description "ECMP IPv4 header fields";
      leaf ip-address {
        type boolean;
        default true;
        description "When set to true IPV4 address to be used for hash computation";
      }
      leaf symmetric-ip {
        type boolean;
        default true;
        description "When set to true IPv4 address to be used in symmetric format for hash computation";
      }
      leaf proto {
        type boolean;
        default true;
        description "When set to true IPV4 proto to be used for hash computation";
      }
    }

    container hash-ipv6 {
      description "ECMP IPv6 header fields";
      leaf ip-address {
        type boolean;
        default true;
        description "When set to true IPv6 address to be used for hash computation";
      }
      leaf flow-label {
        type boolean;
        default true;
        description "When set to true IPv6 flow-label to be used for hash computation";
      }
      leaf next-header {
        type boolean;
        default true;
        description "When set to true IPv6 next-header to be used for hash computation";
      }
    }
 
    container hash-l2 {
      description "ECMP L2 header fields";
      leaf vlan {
        type boolean;
        default true;
        description "When set to true vlan ID to be used for hash computation";
      }
      leaf eth-type {
        type boolean; 
        default true;
        description "When set to true eth-type to be used for hash computation";
      }
      leaf mac-address { 
        type boolean;
        default true;
        description "When set to true mac addresses to be used for hash computation";
      }
      leaf symmetric-mac {
        type boolean;
        default true;
        description "When set to true mac address to be used in symmetric format for hash computation";
      }
      leaf terminated-l2 { 
        type boolean;
        default false;
        description "when set to true terminated L2 header to be used in the hash computation";
      }
    }

    container hash-l4 {
      description "ECMP L2 header fields";
      leaf l4-port {
        type boolean;
        default true;
        description "when set to true L4 ports to be used for hash computation";
      }
      leaf symmetric-port {
        type boolean;
        default true;
        description "When set to true L4 ports to be used in symmetric format for hash computation";
      }
    }

  } 
}
