module arcos-qos-tablemap-types {
  yang-version 1.1;
  namespace "http://yang.arrcus.com/arcos/qos/tablemap/types";
  prefix arc-qos-tbl-types;

  organization
    "Arrcus, Inc.";

  contact
    "Arrcus, Inc.
     Customer Service
     Postal: 2077 Gateway Place
     San Jose, CA 95110
     Tel: +1 1XXX XXX-XXXX
     E-mail: xxx@arrcus.com";

  description
    "YANG data-model for tablemap types";

  revision 2023-08-14 {
    description
      "Added new UNTAG map type to map untagged traffic";
  }

  identity MAP_TYPE {
    description
      "This is an identity of base type";
  }
  identity COS {
    base MAP_TYPE;
    description
      "Class of Service code point type";
  }
  identity DSCP {
    base MAP_TYPE;
    description
      "Differentiated Services code point type";
  }
  identity MPLS_TC {
    base MAP_TYPE;
    description
      "MPLS TC code point type";
  }
  identity LOCAL_TC {
    base MAP_TYPE;
    description
      "Local Priority Traffic Class";
  }
  identity UNTAG {
    base MAP_TYPE;
    description
      "Untaged traffic class";
  }

}
