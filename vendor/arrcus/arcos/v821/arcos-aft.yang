module arcos-aft {

  yang-version "1.1";

  // namespace
  namespace "http://yang.arrcus.com/arcos/aft";

  prefix "arc-aft";

  // import some basic types
  import ietf-inet-types { prefix "inet"; }

  import arcos-aft-types { prefix "arc-aft-types"; }
  import arcos-srv6-types { prefix "arc-srv6-types"; }

  organization "Arrcus, Inc";

  contact
    "Email: eng@arrcus.com";

  description
    "This module lists the aft related information";

  revision "2020-02-22" {
    description
      "Initial version";
  }

  grouping aft-srv6-sids {
    description
      "SRv6 SID Information";

    container srv6-sids {
      description
        "SRv6 SID Information";

      list srv6-sid {
        config false;
        key "local-sid";

        description
          "List of SRv6 SID";

        leaf local-sid {
          type leafref {
            path "../state/local-sid";
          }
          description
            "reference to the local-sid";
        }

        container state {
          description
            "Operational Data for SRv6 SID";

          uses aft-srv6-sid-state;
        }
      }
    }
  }

  grouping aft-srv6-sid-state {
    description
      "SRv6 SID Info";

    leaf local-sid {
      description
        "SRv6 Local SID";
      type inet:ipv6-prefix;
    }

    leaf sid-type {
      description
        "SRv6 SID Type";
      type arc-srv6-types:srv6-sid-type;
    }

    leaf function {
      description
        "SRv6 Function";
      type arc-srv6-types:srv6-endpoint-behavior-type;
    }

    leaf nh-id {
      description
        "NH ID for End.DX/End.X";
      type uint32;
    }

    leaf sid-vrf-id {
      description
        "HW VRF ID for End.DT/uDT";
      type uint32;
    }
    
    leaf flags {
      description
        "SID specific flag";
      type uint32;
    }

    leaf tunnel-terminator-id {
      description
        "SRv6 tunnel terminator HW ID";
      type uint32;
    }
    
    leaf tunnel-terminator-priority {
      description
        "SRv6 tunnel terminator TCAM entry priority";
      type uint32;
    }
  }
}
