/*
 * Generated by confdc --mib2yang
 * Source: BGP4-MIB.mib
 */
module BGP4-MIB {
  namespace "http://tail-f.com/ns/mibs/BGP4-MIB/199902100000Z";
  prefix BGP4_MIB;
  tailf:id "";
  tailf:snmp-mib-module-name "BGP4-MIB";

  import ietf-yang-types {
    prefix yang;
  }
  import ietf-inet-types {
    prefix inet;
  }
  import tailf-common {
    prefix tailf;
  }

  revision 1999-02-10 {
    description
      "";
  }

  container BGP4-MIB {
    config false;
    container bgp {
      tailf:snmp-name "bgp";
      leaf bgpVersion {
        type bgpVersionType;
        tailf:snmp-name "bgpVersion";
      }
      leaf bgpLocalAs {
        type bgpLocalAsType;
        tailf:snmp-name "bgpLocalAs";
      }
      leaf bgpIdentifier {
        type inet:ipv4-address;
        tailf:snmp-name "bgpIdentifier";
      }
    }
    container bgpPeerTable {
      list bgpPeerEntry {
        key "bgpPeerRemoteAddr";
        tailf:sort-order "snmp";
        tailf:snmp-name "bgpPeerTable";
        leaf bgpPeerRemoteAddr {
          type inet:ipv4-address;
          tailf:snmp-name "bgpPeerRemoteAddr";
        }
        leaf bgpPeerIdentifier {
          type inet:ipv4-address;
          tailf:snmp-name "bgpPeerIdentifier";
        }
        leaf bgpPeerState {
          type bgpPeerStateType;
          tailf:snmp-name "bgpPeerState";
        }
        leaf bgpPeerAdminStatus {
          type bgpPeerAdminStatusType;
          tailf:snmp-name "bgpPeerAdminStatus";
        }
        leaf bgpPeerNegotiatedVersion {
          type int32;
          tailf:snmp-name "bgpPeerNegotiatedVersion";
        }
        leaf bgpPeerLocalAddr {
          type inet:ipv4-address;
          tailf:snmp-name "bgpPeerLocalAddr";
        }
        leaf bgpPeerLocalPort {
          type bgpPeerLocalPortType;
          tailf:snmp-name "bgpPeerLocalPort";
        }
        leaf bgpPeerRemotePort {
          type bgpPeerRemotePortType;
          tailf:snmp-name "bgpPeerRemotePort";
        }
        leaf bgpPeerRemoteAs {
          type bgpPeerRemoteAsType;
          tailf:snmp-name "bgpPeerRemoteAs";
        }
        leaf bgpPeerInUpdates {
          type yang:counter32;
          tailf:snmp-name "bgpPeerInUpdates";
        }
        leaf bgpPeerOutUpdates {
          type yang:counter32;
          tailf:snmp-name "bgpPeerOutUpdates";
        }
        leaf bgpPeerInTotalMessages {
          type yang:counter32;
          tailf:snmp-name "bgpPeerInTotalMessages";
        }
        leaf bgpPeerOutTotalMessages {
          type yang:counter32;
          tailf:snmp-name "bgpPeerOutTotalMessages";
        }
        leaf bgpPeerLastError {
          type bgpPeerLastErrorType;
          tailf:snmp-name "bgpPeerLastError";
        }
        leaf bgpPeerFsmEstablishedTransitions {
          type yang:counter32;
          tailf:snmp-name "bgpPeerFsmEstablishedTransitions";
        }
        leaf bgpPeerFsmEstablishedTime {
          type yang:gauge32;
          tailf:snmp-name "bgpPeerFsmEstablishedTime";
        }
        leaf bgpPeerConnectRetryInterval {
          type bgpPeerConnectRetryIntervalType;
          tailf:snmp-name "bgpPeerConnectRetryInterval";
        }
        leaf bgpPeerHoldTime {
          type bgpPeerHoldTimeType;
          tailf:snmp-name "bgpPeerHoldTime";
        }
        leaf bgpPeerKeepAlive {
          type bgpPeerKeepAliveType;
          tailf:snmp-name "bgpPeerKeepAlive";
        }
        leaf bgpPeerHoldTimeConfigured {
          type bgpPeerHoldTimeConfiguredType;
          tailf:snmp-name "bgpPeerHoldTimeConfigured";
        }
        leaf bgpPeerKeepAliveConfigured {
          type bgpPeerKeepAliveConfiguredType;
          tailf:snmp-name "bgpPeerKeepAliveConfigured";
        }
        leaf bgpPeerMinASOriginationInterval {
          type bgpPeerMinASOriginationIntervalType;
          tailf:snmp-name "bgpPeerMinASOriginationInterval";
        }
        leaf bgpPeerMinRouteAdvertisementInterval {
          type bgpPeerMinRouteAdvertisementIntervalType;
          tailf:snmp-name "bgpPeerMinRouteAdvertisementInterval";
        }
        leaf bgpPeerInUpdateElapsedTime {
          type yang:gauge32;
          tailf:snmp-name "bgpPeerInUpdateElapsedTime";
        }
      }
    }
    container bgp4PathAttrTable {
      list bgp4PathAttrEntry {
        key "bgp4PathAttrIpAddrPrefix bgp4PathAttrIpAddrPrefixLen bgp4PathAttrPeer";
        tailf:sort-order "snmp";
        tailf:snmp-name "bgp4PathAttrTable";
        leaf bgp4PathAttrIpAddrPrefix {
          type inet:ipv4-address;
          tailf:snmp-name "bgp4PathAttrIpAddrPrefix";
        }
        leaf bgp4PathAttrIpAddrPrefixLen {
          type bgp4PathAttrIpAddrPrefixLenType;
          tailf:snmp-name "bgp4PathAttrIpAddrPrefixLen";
        }
        leaf bgp4PathAttrPeer {
          type inet:ipv4-address;
          tailf:snmp-name "bgp4PathAttrPeer";
        }
        leaf bgp4PathAttrOrigin {
          type bgp4PathAttrOriginType;
          tailf:snmp-name "bgp4PathAttrOrigin";
        }
        leaf bgp4PathAttrASPathSegment {
          type bgp4PathAttrASPathSegmentType;
          tailf:snmp-name "bgp4PathAttrASPathSegment";
        }
        leaf bgp4PathAttrNextHop {
          type inet:ipv4-address;
          tailf:snmp-name "bgp4PathAttrNextHop";
        }
        leaf bgp4PathAttrMultiExitDisc {
          type bgp4PathAttrMultiExitDiscType;
          tailf:snmp-name "bgp4PathAttrMultiExitDisc";
        }
        leaf bgp4PathAttrLocalPref {
          type bgp4PathAttrLocalPrefType;
          tailf:snmp-name "bgp4PathAttrLocalPref";
        }
        leaf bgp4PathAttrAtomicAggregate {
          type bgp4PathAttrAtomicAggregateType;
          tailf:snmp-name "bgp4PathAttrAtomicAggregate";
        }
        leaf bgp4PathAttrAggregatorAS {
          type bgp4PathAttrAggregatorASType;
          tailf:snmp-name "bgp4PathAttrAggregatorAS";
        }
        leaf bgp4PathAttrAggregatorAddr {
          type inet:ipv4-address;
          tailf:snmp-name "bgp4PathAttrAggregatorAddr";
        }
        leaf bgp4PathAttrCalcLocalPref {
          type bgp4PathAttrCalcLocalPrefType;
          tailf:snmp-name "bgp4PathAttrCalcLocalPref";
        }
        leaf bgp4PathAttrBest {
          type bgp4PathAttrBestType;
          tailf:snmp-name "bgp4PathAttrBest";
        }
        leaf bgp4PathAttrUnknown {
          type bgp4PathAttrUnknownType;
          tailf:snmp-name "bgp4PathAttrUnknown";
        }
      }
    }
  }

  typedef bgpVersionType {
    type tailf:hex-list {
      tailf:value-length "1 .. 255";
    }
  }

  typedef bgpLocalAsType {
    type int32 {
      range "0 .. 65535";
    }
  }

  typedef bgpPeerStateType {
    type enumeration {
      enum "idle" {
        value 1;
      }
      enum "connect" {
        value 2;
      }
      enum "active" {
        value 3;
      }
      enum "opensent" {
        value 4;
      }
      enum "openconfirm" {
        value 5;
      }
      enum "established" {
        value 6;
      }
    }
  }

  typedef bgpPeerAdminStatusType {
    type enumeration {
      enum "stop" {
        value 1;
      }
      enum "start" {
        value 2;
      }
    }
  }

  typedef bgpPeerLocalPortType {
    type int32 {
      range "0 .. 65535";
    }
  }

  typedef bgpPeerRemotePortType {
    type int32 {
      range "0 .. 65535";
    }
  }

  typedef bgpPeerRemoteAsType {
    type int32 {
      range "0 .. 65535";
    }
  }

  typedef bgpPeerLastErrorType {
    type tailf:hex-list {
      tailf:value-length "2";
    }
  }

  typedef bgpPeerConnectRetryIntervalType {
    type int32 {
      range "1 .. 65535";
    }
  }

  typedef bgpPeerHoldTimeType {
    type int32 {
      range "0 .. 65535";
    }
  }

  typedef bgpPeerKeepAliveType {
    type int32 {
      range "0 .. 21845";
    }
  }

  typedef bgpPeerHoldTimeConfiguredType {
    type int32 {
      range "0 .. 65535";
    }
  }

  typedef bgpPeerKeepAliveConfiguredType {
    type int32 {
      range "0 .. 21845";
    }
  }

  typedef bgpPeerMinASOriginationIntervalType {
    type int32 {
      range "1 .. 65535";
    }
  }

  typedef bgpPeerMinRouteAdvertisementIntervalType {
    type int32 {
      range "1 .. 65535";
    }
  }

  typedef bgp4PathAttrIpAddrPrefixLenType {
    type int32 {
      range "0 .. 32";
    }
  }

  typedef bgp4PathAttrOriginType {
    type enumeration {
      enum "igp" {
        value 1;
      }
      enum "egp" {
        value 2;
      }
      enum "incomplete" {
        value 3;
      }
    }
  }

  typedef bgp4PathAttrASPathSegmentType {
    type tailf:hex-list {
      tailf:value-length "2 .. 255";
    }
  }

  typedef bgp4PathAttrMultiExitDiscType {
    type int32 {
      range "-1 .. 2147483647";
    }
  }

  typedef bgp4PathAttrLocalPrefType {
    type int32 {
      range "-1 .. 2147483647";
    }
  }

  typedef bgp4PathAttrAtomicAggregateType {
    type enumeration {
      enum "lessSpecificRrouteNotSelected" {
        value 1;
      }
      enum "lessSpecificRouteSelected" {
        value 2;
      }
    }
  }

  typedef bgp4PathAttrAggregatorASType {
    type int32 {
      range "0 .. 65535";
    }
  }

  typedef bgp4PathAttrCalcLocalPrefType {
    type int32 {
      range "-1 .. 2147483647";
    }
  }

  typedef bgp4PathAttrBestType {
    type enumeration {
      enum "false" {
        value 1;
      }
      enum "true" {
        value 2;
      }
    }
  }

  typedef bgp4PathAttrUnknownType {
    type tailf:hex-list {
      tailf:value-length "min .. 255";
    }
  }
}
