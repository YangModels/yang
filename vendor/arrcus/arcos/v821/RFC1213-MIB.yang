/*
 * Generated by confdc --mib2yang
 * Source: RFC1213-MIB.mib
 */
module RFC1213-MIB {
  namespace "http://tail-f.com/ns/mibs/RFC1213-MIB/1.0";
  prefix RFC1213_MIB;
  tailf:id "";
  tailf:snmp-mib-module-name "RFC1213-MIB";

  import ietf-yang-types {
    prefix yang;
  }
  import ietf-inet-types {
    prefix inet;
  }
  import tailf-common {
    prefix tailf;
  }

  container RFC1213-MIB {
    config false;
    container system {
      tailf:snmp-name "system";
      leaf sysDescr {
        type sysDescrType;
        tailf:snmp-name "sysDescr";
      }
      leaf sysObjectID {
        type yang:object-identifier;
        tailf:snmp-name "sysObjectID";
      }
      leaf sysUpTime {
        type yang:timeticks;
        tailf:snmp-name "sysUpTime";
      }
      leaf sysContact {
        type sysContactType;
        tailf:snmp-name "sysContact";
      }
      leaf sysName {
        type sysNameType;
        tailf:snmp-name "sysName";
      }
      leaf sysLocation {
        type sysLocationType;
        tailf:snmp-name "sysLocation";
      }
      leaf sysServices {
        type sysServicesType;
        tailf:snmp-name "sysServices";
      }
    }
    container interfaces {
      tailf:snmp-name "interfaces";
      leaf ifNumber {
        type int32;
        tailf:snmp-name "ifNumber";
      }
    }
    container ip {
      tailf:snmp-name "ip";
      leaf ipForwarding {
        type ipForwardingType;
        tailf:snmp-name "ipForwarding";
      }
      leaf ipDefaultTTL {
        type int32;
        tailf:snmp-name "ipDefaultTTL";
      }
      leaf ipInReceives {
        type yang:counter32;
        tailf:snmp-name "ipInReceives";
      }
      leaf ipInHdrErrors {
        type yang:counter32;
        tailf:snmp-name "ipInHdrErrors";
      }
      leaf ipInAddrErrors {
        type yang:counter32;
        tailf:snmp-name "ipInAddrErrors";
      }
      leaf ipForwDatagrams {
        type yang:counter32;
        tailf:snmp-name "ipForwDatagrams";
      }
      leaf ipInUnknownProtos {
        type yang:counter32;
        tailf:snmp-name "ipInUnknownProtos";
      }
      leaf ipInDiscards {
        type yang:counter32;
        tailf:snmp-name "ipInDiscards";
      }
      leaf ipInDelivers {
        type yang:counter32;
        tailf:snmp-name "ipInDelivers";
      }
      leaf ipOutRequests {
        type yang:counter32;
        tailf:snmp-name "ipOutRequests";
      }
      leaf ipOutDiscards {
        type yang:counter32;
        tailf:snmp-name "ipOutDiscards";
      }
      leaf ipOutNoRoutes {
        type yang:counter32;
        tailf:snmp-name "ipOutNoRoutes";
      }
      leaf ipReasmTimeout {
        type int32;
        tailf:snmp-name "ipReasmTimeout";
      }
      leaf ipReasmReqds {
        type yang:counter32;
        tailf:snmp-name "ipReasmReqds";
      }
      leaf ipReasmOKs {
        type yang:counter32;
        tailf:snmp-name "ipReasmOKs";
      }
      leaf ipReasmFails {
        type yang:counter32;
        tailf:snmp-name "ipReasmFails";
      }
      leaf ipFragOKs {
        type yang:counter32;
        tailf:snmp-name "ipFragOKs";
      }
      leaf ipFragFails {
        type yang:counter32;
        tailf:snmp-name "ipFragFails";
      }
      leaf ipFragCreates {
        type yang:counter32;
        tailf:snmp-name "ipFragCreates";
      }
      leaf ipRoutingDiscards {
        type yang:counter32;
        tailf:snmp-name "ipRoutingDiscards";
      }
    }
    container icmp {
      tailf:snmp-name "icmp";
      leaf icmpInMsgs {
        type yang:counter32;
        tailf:snmp-name "icmpInMsgs";
      }
      leaf icmpInErrors {
        type yang:counter32;
        tailf:snmp-name "icmpInErrors";
      }
      leaf icmpInDestUnreachs {
        type yang:counter32;
        tailf:snmp-name "icmpInDestUnreachs";
      }
      leaf icmpInTimeExcds {
        type yang:counter32;
        tailf:snmp-name "icmpInTimeExcds";
      }
      leaf icmpInParmProbs {
        type yang:counter32;
        tailf:snmp-name "icmpInParmProbs";
      }
      leaf icmpInSrcQuenchs {
        type yang:counter32;
        tailf:snmp-name "icmpInSrcQuenchs";
      }
      leaf icmpInRedirects {
        type yang:counter32;
        tailf:snmp-name "icmpInRedirects";
      }
      leaf icmpInEchos {
        type yang:counter32;
        tailf:snmp-name "icmpInEchos";
      }
      leaf icmpInEchoReps {
        type yang:counter32;
        tailf:snmp-name "icmpInEchoReps";
      }
      leaf icmpInTimestamps {
        type yang:counter32;
        tailf:snmp-name "icmpInTimestamps";
      }
      leaf icmpInTimestampReps {
        type yang:counter32;
        tailf:snmp-name "icmpInTimestampReps";
      }
      leaf icmpInAddrMasks {
        type yang:counter32;
        tailf:snmp-name "icmpInAddrMasks";
      }
      leaf icmpInAddrMaskReps {
        type yang:counter32;
        tailf:snmp-name "icmpInAddrMaskReps";
      }
      leaf icmpOutMsgs {
        type yang:counter32;
        tailf:snmp-name "icmpOutMsgs";
      }
      leaf icmpOutErrors {
        type yang:counter32;
        tailf:snmp-name "icmpOutErrors";
      }
      leaf icmpOutDestUnreachs {
        type yang:counter32;
        tailf:snmp-name "icmpOutDestUnreachs";
      }
      leaf icmpOutTimeExcds {
        type yang:counter32;
        tailf:snmp-name "icmpOutTimeExcds";
      }
      leaf icmpOutParmProbs {
        type yang:counter32;
        tailf:snmp-name "icmpOutParmProbs";
      }
      leaf icmpOutSrcQuenchs {
        type yang:counter32;
        tailf:snmp-name "icmpOutSrcQuenchs";
      }
      leaf icmpOutRedirects {
        type yang:counter32;
        tailf:snmp-name "icmpOutRedirects";
      }
      leaf icmpOutEchos {
        type yang:counter32;
        tailf:snmp-name "icmpOutEchos";
      }
      leaf icmpOutEchoReps {
        type yang:counter32;
        tailf:snmp-name "icmpOutEchoReps";
      }
      leaf icmpOutTimestamps {
        type yang:counter32;
        tailf:snmp-name "icmpOutTimestamps";
      }
      leaf icmpOutTimestampReps {
        type yang:counter32;
        tailf:snmp-name "icmpOutTimestampReps";
      }
      leaf icmpOutAddrMasks {
        type yang:counter32;
        tailf:snmp-name "icmpOutAddrMasks";
      }
      leaf icmpOutAddrMaskReps {
        type yang:counter32;
        tailf:snmp-name "icmpOutAddrMaskReps";
      }
    }
    container tcp {
      tailf:snmp-name "tcp";
      leaf tcpRtoAlgorithm {
        type tcpRtoAlgorithmType;
        tailf:snmp-name "tcpRtoAlgorithm";
      }
      leaf tcpRtoMin {
        type int32;
        tailf:snmp-name "tcpRtoMin";
      }
      leaf tcpRtoMax {
        type int32;
        tailf:snmp-name "tcpRtoMax";
      }
      leaf tcpMaxConn {
        type int32;
        tailf:snmp-name "tcpMaxConn";
      }
      leaf tcpActiveOpens {
        type yang:counter32;
        tailf:snmp-name "tcpActiveOpens";
      }
      leaf tcpPassiveOpens {
        type yang:counter32;
        tailf:snmp-name "tcpPassiveOpens";
      }
      leaf tcpAttemptFails {
        type yang:counter32;
        tailf:snmp-name "tcpAttemptFails";
      }
      leaf tcpEstabResets {
        type yang:counter32;
        tailf:snmp-name "tcpEstabResets";
      }
      leaf tcpCurrEstab {
        type yang:gauge32;
        tailf:snmp-name "tcpCurrEstab";
      }
      leaf tcpInSegs {
        type yang:counter32;
        tailf:snmp-name "tcpInSegs";
      }
      leaf tcpOutSegs {
        type yang:counter32;
        tailf:snmp-name "tcpOutSegs";
      }
      leaf tcpRetransSegs {
        type yang:counter32;
        tailf:snmp-name "tcpRetransSegs";
      }
      leaf tcpInErrs {
        type yang:counter32;
        tailf:snmp-name "tcpInErrs";
      }
      leaf tcpOutRsts {
        type yang:counter32;
        tailf:snmp-name "tcpOutRsts";
      }
    }
    container udp {
      tailf:snmp-name "udp";
      leaf udpInDatagrams {
        type yang:counter32;
        tailf:snmp-name "udpInDatagrams";
      }
      leaf udpNoPorts {
        type yang:counter32;
        tailf:snmp-name "udpNoPorts";
      }
      leaf udpInErrors {
        type yang:counter32;
        tailf:snmp-name "udpInErrors";
      }
      leaf udpOutDatagrams {
        type yang:counter32;
        tailf:snmp-name "udpOutDatagrams";
      }
    }
    container egp {
      tailf:snmp-name "egp";
      leaf egpInMsgs {
        type yang:counter32;
        tailf:snmp-name "egpInMsgs";
      }
      leaf egpInErrors {
        type yang:counter32;
        tailf:snmp-name "egpInErrors";
      }
      leaf egpOutMsgs {
        type yang:counter32;
        tailf:snmp-name "egpOutMsgs";
      }
      leaf egpOutErrors {
        type yang:counter32;
        tailf:snmp-name "egpOutErrors";
      }
      leaf egpAs {
        type int32;
        tailf:snmp-name "egpAs";
      }
    }
    container snmp {
      tailf:snmp-name "snmp";
      leaf snmpInPkts {
        type yang:counter32;
        tailf:snmp-name "snmpInPkts";
      }
      leaf snmpOutPkts {
        type yang:counter32;
        tailf:snmp-name "snmpOutPkts";
      }
      leaf snmpInBadVersions {
        type yang:counter32;
        tailf:snmp-name "snmpInBadVersions";
      }
      leaf snmpInBadCommunityNames {
        type yang:counter32;
        tailf:snmp-name "snmpInBadCommunityNames";
      }
      leaf snmpInBadCommunityUses {
        type yang:counter32;
        tailf:snmp-name "snmpInBadCommunityUses";
      }
      leaf snmpInASNParseErrs {
        type yang:counter32;
        tailf:snmp-name "snmpInASNParseErrs";
      }
      leaf snmpInTooBigs {
        type yang:counter32;
        tailf:snmp-name "snmpInTooBigs";
      }
      leaf snmpInNoSuchNames {
        type yang:counter32;
        tailf:snmp-name "snmpInNoSuchNames";
      }
      leaf snmpInBadValues {
        type yang:counter32;
        tailf:snmp-name "snmpInBadValues";
      }
      leaf snmpInReadOnlys {
        type yang:counter32;
        tailf:snmp-name "snmpInReadOnlys";
      }
      leaf snmpInGenErrs {
        type yang:counter32;
        tailf:snmp-name "snmpInGenErrs";
      }
      leaf snmpInTotalReqVars {
        type yang:counter32;
        tailf:snmp-name "snmpInTotalReqVars";
      }
      leaf snmpInTotalSetVars {
        type yang:counter32;
        tailf:snmp-name "snmpInTotalSetVars";
      }
      leaf snmpInGetRequests {
        type yang:counter32;
        tailf:snmp-name "snmpInGetRequests";
      }
      leaf snmpInGetNexts {
        type yang:counter32;
        tailf:snmp-name "snmpInGetNexts";
      }
      leaf snmpInSetRequests {
        type yang:counter32;
        tailf:snmp-name "snmpInSetRequests";
      }
      leaf snmpInGetResponses {
        type yang:counter32;
        tailf:snmp-name "snmpInGetResponses";
      }
      leaf snmpInTraps {
        type yang:counter32;
        tailf:snmp-name "snmpInTraps";
      }
      leaf snmpOutTooBigs {
        type yang:counter32;
        tailf:snmp-name "snmpOutTooBigs";
      }
      leaf snmpOutNoSuchNames {
        type yang:counter32;
        tailf:snmp-name "snmpOutNoSuchNames";
      }
      leaf snmpOutBadValues {
        type yang:counter32;
        tailf:snmp-name "snmpOutBadValues";
      }
      leaf snmpOutGenErrs {
        type yang:counter32;
        tailf:snmp-name "snmpOutGenErrs";
      }
      leaf snmpOutGetRequests {
        type yang:counter32;
        tailf:snmp-name "snmpOutGetRequests";
      }
      leaf snmpOutGetNexts {
        type yang:counter32;
        tailf:snmp-name "snmpOutGetNexts";
      }
      leaf snmpOutSetRequests {
        type yang:counter32;
        tailf:snmp-name "snmpOutSetRequests";
      }
      leaf snmpOutGetResponses {
        type yang:counter32;
        tailf:snmp-name "snmpOutGetResponses";
      }
      leaf snmpOutTraps {
        type yang:counter32;
        tailf:snmp-name "snmpOutTraps";
      }
      leaf snmpEnableAuthenTraps {
        type snmpEnableAuthenTrapsType;
        tailf:snmp-name "snmpEnableAuthenTraps";
      }
    }
    container ifTable {
      list ifEntry {
        key "ifIndex";
        tailf:sort-order "snmp";
        tailf:snmp-name "ifTable";
        leaf ifIndex {
          type int32;
          tailf:snmp-name "ifIndex";
        }
        leaf ifDescr {
          type ifDescrType;
          tailf:snmp-name "ifDescr";
        }
        leaf ifType {
          type ifTypeType;
          tailf:snmp-name "ifType";
        }
        leaf ifMtu {
          type int32;
          tailf:snmp-name "ifMtu";
        }
        leaf ifSpeed {
          type yang:gauge32;
          tailf:snmp-name "ifSpeed";
        }
        leaf ifPhysAddress {
          type PhysAddress;
          tailf:snmp-name "ifPhysAddress";
        }
        leaf ifAdminStatus {
          type ifAdminStatusType;
          tailf:snmp-name "ifAdminStatus";
        }
        leaf ifOperStatus {
          type ifOperStatusType;
          tailf:snmp-name "ifOperStatus";
        }
        leaf ifLastChange {
          type yang:timeticks;
          tailf:snmp-name "ifLastChange";
        }
        leaf ifInOctets {
          type yang:counter32;
          tailf:snmp-name "ifInOctets";
        }
        leaf ifInUcastPkts {
          type yang:counter32;
          tailf:snmp-name "ifInUcastPkts";
        }
        leaf ifInNUcastPkts {
          type yang:counter32;
          tailf:snmp-name "ifInNUcastPkts";
        }
        leaf ifInDiscards {
          type yang:counter32;
          tailf:snmp-name "ifInDiscards";
        }
        leaf ifInErrors {
          type yang:counter32;
          tailf:snmp-name "ifInErrors";
        }
        leaf ifInUnknownProtos {
          type yang:counter32;
          tailf:snmp-name "ifInUnknownProtos";
        }
        leaf ifOutOctets {
          type yang:counter32;
          tailf:snmp-name "ifOutOctets";
        }
        leaf ifOutUcastPkts {
          type yang:counter32;
          tailf:snmp-name "ifOutUcastPkts";
        }
        leaf ifOutNUcastPkts {
          type yang:counter32;
          tailf:snmp-name "ifOutNUcastPkts";
        }
        leaf ifOutDiscards {
          type yang:counter32;
          tailf:snmp-name "ifOutDiscards";
        }
        leaf ifOutErrors {
          type yang:counter32;
          tailf:snmp-name "ifOutErrors";
        }
        leaf ifOutQLen {
          type yang:gauge32;
          tailf:snmp-name "ifOutQLen";
        }
        leaf ifSpecific {
          type yang:object-identifier;
          tailf:snmp-name "ifSpecific";
        }
      }
    }
    container ipAddrTable {
      list ipAddrEntry {
        key "ipAdEntAddr";
        tailf:sort-order "snmp";
        tailf:snmp-name "ipAddrTable";
        leaf ipAdEntAddr {
          type inet:ipv4-address;
          tailf:snmp-name "ipAdEntAddr";
        }
        leaf ipAdEntIfIndex {
          type int32;
          tailf:snmp-name "ipAdEntIfIndex";
        }
        leaf ipAdEntNetMask {
          type inet:ipv4-address;
          tailf:snmp-name "ipAdEntNetMask";
        }
        leaf ipAdEntBcastAddr {
          type int32;
          tailf:snmp-name "ipAdEntBcastAddr";
        }
        leaf ipAdEntReasmMaxSize {
          type ipAdEntReasmMaxSizeType;
          tailf:snmp-name "ipAdEntReasmMaxSize";
        }
      }
    }
    container ipRouteTable {
      list ipRouteEntry {
        key "ipRouteDest";
        tailf:sort-order "snmp";
        tailf:snmp-name "ipRouteTable";
        leaf ipRouteDest {
          type inet:ipv4-address;
          tailf:snmp-name "ipRouteDest";
        }
        leaf ipRouteIfIndex {
          type int32;
          tailf:snmp-name "ipRouteIfIndex";
        }
        leaf ipRouteMetric1 {
          type int32;
          tailf:snmp-name "ipRouteMetric1";
        }
        leaf ipRouteMetric2 {
          type int32;
          tailf:snmp-name "ipRouteMetric2";
        }
        leaf ipRouteMetric3 {
          type int32;
          tailf:snmp-name "ipRouteMetric3";
        }
        leaf ipRouteMetric4 {
          type int32;
          tailf:snmp-name "ipRouteMetric4";
        }
        leaf ipRouteNextHop {
          type inet:ipv4-address;
          tailf:snmp-name "ipRouteNextHop";
        }
        leaf ipRouteType {
          type ipRouteTypeType;
          tailf:snmp-name "ipRouteType";
        }
        leaf ipRouteProto {
          type ipRouteProtoType;
          tailf:snmp-name "ipRouteProto";
        }
        leaf ipRouteAge {
          type int32;
          tailf:snmp-name "ipRouteAge";
        }
        leaf ipRouteMask {
          type inet:ipv4-address;
          tailf:snmp-name "ipRouteMask";
        }
        leaf ipRouteMetric5 {
          type int32;
          tailf:snmp-name "ipRouteMetric5";
        }
        leaf ipRouteInfo {
          type yang:object-identifier;
          tailf:snmp-name "ipRouteInfo";
        }
      }
    }
    container ipNetToMediaTable {
      list ipNetToMediaEntry {
        key "ipNetToMediaIfIndex ipNetToMediaNetAddress";
        tailf:sort-order "snmp";
        tailf:snmp-name "ipNetToMediaTable";
        leaf ipNetToMediaIfIndex {
          type int32;
          tailf:snmp-name "ipNetToMediaIfIndex";
        }
        leaf ipNetToMediaNetAddress {
          type inet:ipv4-address;
          tailf:snmp-name "ipNetToMediaNetAddress";
        }
        leaf ipNetToMediaPhysAddress {
          type PhysAddress;
          tailf:snmp-name "ipNetToMediaPhysAddress";
        }
        leaf ipNetToMediaType {
          type ipNetToMediaTypeType;
          tailf:snmp-name "ipNetToMediaType";
        }
      }
    }
    container tcpConnTable {
      list tcpConnEntry {
        key "tcpConnLocalAddress tcpConnLocalPort tcpConnRemAddress tcpConnRemPort";
        tailf:sort-order "snmp";
        tailf:snmp-name "tcpConnTable";
        leaf tcpConnLocalAddress {
          type inet:ipv4-address;
          tailf:snmp-name "tcpConnLocalAddress";
        }
        leaf tcpConnLocalPort {
          type tcpConnLocalPortType;
          tailf:snmp-name "tcpConnLocalPort";
        }
        leaf tcpConnRemAddress {
          type inet:ipv4-address;
          tailf:snmp-name "tcpConnRemAddress";
        }
        leaf tcpConnRemPort {
          type tcpConnRemPortType;
          tailf:snmp-name "tcpConnRemPort";
        }
        leaf tcpConnState {
          type tcpConnStateType;
          tailf:snmp-name "tcpConnState";
        }
      }
    }
    container udpTable {
      list udpEntry {
        key "udpLocalAddress udpLocalPort";
        tailf:sort-order "snmp";
        tailf:snmp-name "udpTable";
        leaf udpLocalAddress {
          type inet:ipv4-address;
          tailf:snmp-name "udpLocalAddress";
        }
        leaf udpLocalPort {
          type udpLocalPortType;
          tailf:snmp-name "udpLocalPort";
        }
      }
    }
    container egpNeighTable {
      list egpNeighEntry {
        key "egpNeighAddr";
        tailf:sort-order "snmp";
        tailf:snmp-name "egpNeighTable";
        leaf egpNeighAddr {
          type inet:ipv4-address;
          tailf:snmp-name "egpNeighAddr";
        }
        leaf egpNeighState {
          type egpNeighStateType;
          tailf:snmp-name "egpNeighState";
        }
        leaf egpNeighAs {
          type int32;
          tailf:snmp-name "egpNeighAs";
        }
        leaf egpNeighInMsgs {
          type yang:counter32;
          tailf:snmp-name "egpNeighInMsgs";
        }
        leaf egpNeighInErrs {
          type yang:counter32;
          tailf:snmp-name "egpNeighInErrs";
        }
        leaf egpNeighOutMsgs {
          type yang:counter32;
          tailf:snmp-name "egpNeighOutMsgs";
        }
        leaf egpNeighOutErrs {
          type yang:counter32;
          tailf:snmp-name "egpNeighOutErrs";
        }
        leaf egpNeighInErrMsgs {
          type yang:counter32;
          tailf:snmp-name "egpNeighInErrMsgs";
        }
        leaf egpNeighOutErrMsgs {
          type yang:counter32;
          tailf:snmp-name "egpNeighOutErrMsgs";
        }
        leaf egpNeighStateUps {
          type yang:counter32;
          tailf:snmp-name "egpNeighStateUps";
        }
        leaf egpNeighStateDowns {
          type yang:counter32;
          tailf:snmp-name "egpNeighStateDowns";
        }
        leaf egpNeighIntervalHello {
          type int32;
          tailf:snmp-name "egpNeighIntervalHello";
        }
        leaf egpNeighIntervalPoll {
          type int32;
          tailf:snmp-name "egpNeighIntervalPoll";
        }
        leaf egpNeighMode {
          type egpNeighModeType;
          tailf:snmp-name "egpNeighMode";
        }
        leaf egpNeighEventTrigger {
          type egpNeighEventTriggerType;
          tailf:snmp-name "egpNeighEventTrigger";
        }
      }
    }
  }

  typedef DisplayString {
    type tailf:hex-list;
  }

  typedef PhysAddress {
    type tailf:hex-list;
  }

  typedef sysDescrType {
    type string {
      length "min .. 255";
    }
  }

  typedef sysContactType {
    type string {
      length "min .. 255";
    }
  }

  typedef sysNameType {
    type string {
      length "min .. 255";
    }
  }

  typedef sysLocationType {
    type string {
      length "min .. 255";
    }
  }

  typedef sysServicesType {
    type int32 {
      range "0 .. 127";
    }
  }

  typedef ipForwardingType {
    type enumeration {
      enum "forwarding" {
        value 1;
      }
      enum "not-forwarding" {
        value 2;
      }
    }
  }

  typedef tcpRtoAlgorithmType {
    type enumeration {
      enum "other" {
        value 1;
      }
      enum "constant" {
        value 2;
      }
      enum "rsre" {
        value 3;
      }
      enum "vanj" {
        value 4;
      }
    }
  }

  typedef snmpEnableAuthenTrapsType {
    type enumeration {
      enum "enabled" {
        value 1;
      }
      enum "disabled" {
        value 2;
      }
    }
  }

  typedef ifDescrType {
    type string {
      length "min .. 255";
    }
  }

  typedef ifTypeType {
    type enumeration {
      enum "other" {
        value 1;
      }
      enum "regular1822" {
        value 2;
      }
      enum "hdh1822" {
        value 3;
      }
      enum "ddn-x25" {
        value 4;
      }
      enum "rfc877-x25" {
        value 5;
      }
      enum "ethernet-csmacd" {
        value 6;
      }
      enum "iso88023-csmacd" {
        value 7;
      }
      enum "iso88024-tokenBus" {
        value 8;
      }
      enum "iso88025-tokenRing" {
        value 9;
      }
      enum "iso88026-man" {
        value 10;
      }
      enum "starLan" {
        value 11;
      }
      enum "proteon-10Mbit" {
        value 12;
      }
      enum "proteon-80Mbit" {
        value 13;
      }
      enum "hyperchannel" {
        value 14;
      }
      enum "fddi" {
        value 15;
      }
      enum "lapb" {
        value 16;
      }
      enum "sdlc" {
        value 17;
      }
      enum "ds1" {
        value 18;
      }
      enum "e1" {
        value 19;
      }
      enum "basicISDN" {
        value 20;
      }
      enum "primaryISDN" {
        value 21;
      }
      enum "propPointToPointSerial" {
        value 22;
      }
      enum "ppp" {
        value 23;
      }
      enum "softwareLoopback" {
        value 24;
      }
      enum "eon" {
        value 25;
      }
      enum "ethernet-3Mbit" {
        value 26;
      }
      enum "nsip" {
        value 27;
      }
      enum "slip" {
        value 28;
      }
      enum "ultra" {
        value 29;
      }
      enum "ds3" {
        value 30;
      }
      enum "sip" {
        value 31;
      }
      enum "frame-relay" {
        value 32;
      }
    }
  }

  typedef ifAdminStatusType {
    type enumeration {
      enum "up" {
        value 1;
        tailf:code-name "IF_ADMIN_STATUS_TYPE_up";
      }
      enum "down" {
        value 2;
        tailf:code-name "IF_ADMIN_STATUS_TYPE_down";
      }
      enum "testing" {
        value 3;
        tailf:code-name "IF_ADMIN_STATUS_TYPE_testing";
      }
    }
  }

  typedef ifOperStatusType {
    type enumeration {
      enum "up" {
        value 1;
        tailf:code-name "IF_OPER_STATUS_TYPE_up";
      }
      enum "down" {
        value 2;
        tailf:code-name "IF_OPER_STATUS_TYPE_down";
      }
      enum "testing" {
        value 3;
        tailf:code-name "IF_OPER_STATUS_TYPE_testing";
      }
    }
  }

  typedef ipAdEntReasmMaxSizeType {
    type int32 {
      range "0 .. 65535";
    }
  }

  typedef ipRouteTypeType {
    type enumeration {
      enum "other" {
        value 1;
        tailf:code-name "IF_ROUTE_PROTO_TYPE_other";
      }
      enum "invalid" {
        value 2;
      }
      enum "direct" {
        value 3;
      }
      enum "indirect" {
        value 4;
      }
    }
  }

  typedef ipRouteProtoType {
    type enumeration {
      enum "other" {
        value 1;
        tailf:code-name "IF_ROUTE_PROTO_TYPE_other";
      }
      enum "local" {
        value 2;
      }
      enum "netmgmt" {
        value 3;
      }
      enum "icmp" {
        value 4;
        tailf:code-name "IF_ROUTE_PROTO_TYPE_icmp";
      }
      enum "egp" {
        value 5;
        tailf:code-name "IF_ROUTE_PROTO_TYPE_egp";
      }
      enum "ggp" {
        value 6;
      }
      enum "hello" {
        value 7;
      }
      enum "rip" {
        value 8;
      }
      enum "is-is" {
        value 9;
      }
      enum "es-is" {
        value 10;
      }
      enum "ciscoIgrp" {
        value 11;
      }
      enum "bbnSpfIgp" {
        value 12;
      }
      enum "ospf" {
        value 13;
      }
      enum "bgp" {
        value 14;
      }
    }
  }

  typedef ipNetToMediaTypeType {
    type enumeration {
      enum "other" {
        value 1;
      }
      enum "invalid" {
        value 2;
      }
      enum "dynamic" {
        value 3;
      }
      enum "static" {
        value 4;
      }
    }
  }

  typedef tcpConnLocalPortType {
    type int32 {
      range "0 .. 65535";
    }
  }

  typedef tcpConnRemPortType {
    type int32 {
      range "0 .. 65535";
    }
  }

  typedef tcpConnStateType {
    type enumeration {
      enum "closed" {
        value 1;
      }
      enum "listen" {
        value 2;
      }
      enum "synSent" {
        value 3;
      }
      enum "synReceived" {
        value 4;
      }
      enum "established" {
        value 5;
      }
      enum "finWait1" {
        value 6;
      }
      enum "finWait2" {
        value 7;
      }
      enum "closeWait" {
        value 8;
      }
      enum "lastAck" {
        value 9;
      }
      enum "closing" {
        value 10;
      }
      enum "timeWait" {
        value 11;
      }
      enum "deleteTCB" {
        value 12;
      }
    }
  }

  typedef udpLocalPortType {
    type int32 {
      range "0 .. 65535";
    }
  }

  typedef egpNeighStateType {
    type enumeration {
      enum "idle" {
        value 1;
      }
      enum "acquisition" {
        value 2;
      }
      enum "down" {
        value 3;
      }
      enum "up" {
        value 4;
      }
      enum "cease" {
        value 5;
      }
    }
  }

  typedef egpNeighModeType {
    type enumeration {
      enum "active" {
        value 1;
      }
      enum "passive" {
        value 2;
      }
    }
  }

  typedef egpNeighEventTriggerType {
    type enumeration {
      enum "start" {
        value 1;
      }
      enum "stop" {
        value 2;
      }
    }
  }
}
