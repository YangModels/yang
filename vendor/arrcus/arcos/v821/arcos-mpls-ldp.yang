module arcos-mpls-ldp {

  yang-version "1.1";

  // namespace
  namespace "http://yang.arrcus.com/arcos/mpls/ldp";

  prefix "arc-mpls-ldp";

  // import some basic types
  import ietf-inet-types { prefix "inet"; }
  import openconfig-routing-policy { prefix "oc-rpol"; }
  import openconfig-interfaces { prefix "oc-if"; }
  import openconfig-mpls-ldp {prefix "oc-ldp"; }
  import arcos-common-types { prefix arc-common-types; }
  import ietf-yang-types {
    prefix "yang";
  }

  organization "Arrcus, Inc";

  contact
    "Email: eng@arrcus.com";

  description
    "This module lists the ldp related information";

  revision 2024-01-25 {
    description
      "Add established timestamp and last update timestamp leaves to
       session state";
  }

  revision 2024-01-16 {
    description
      "Adjust range of LDP preference config";
  }

  revision 2023-05-13 {
    description
      "Add targeted hellos config";
  }

  revision 2023-05-01 {
    description
      "Add GR state to IPv6 sessions";
  }

  revision 2023-04-10 {
    description
      "Add LDP global enable config";
  }

  revision 2023-03-08 {
    description
      "Add LDP preference config";
  }

  revision 2022-09-16 {
    description
      "Add reset count to hello adjacency and session state";
  }

  revision 2022-09-14 {
    description
      "Add uptime to hello adjacency and session state";
  }

  revision "2019-08-21" {
    description
      "Initial version";
  }

  grouping mpls-ldp-session-protection-config {
    description
      "Grouping containing session protection configuration";

    container session-protection {
      description
        "Session protection timer option";
      
      container config {
        description
          "Configuration of session protection";

        uses mpls-ldp-session-protection;
      }

      container state {
        config false;
        description
          "Operation data for session protection";

        uses mpls-ldp-session-protection;
      }
    }
  }

  grouping mpls-ldp-session-protection {
    description
      "Grouping containing session protection option";
    
    leaf session-protection {
      type uint16 {
        range 0..max;
      }
      units "seconds";
      description
        "Duration in seconds an LDP session is to stay up without link " +
        "adjacencies established";
    }
  }

  grouping mpls-ldp-targeted-dest-config {
    description
      "Grouping containing targeted hello destination address configuration";

    leaf destination-address {
      type inet:ip-address;
      description
        "Destination address of the targeted hello";
    }
  }

  grouping mpls-ldp-neighbor-targeted-hello-config {
    description
      "Grouping containing per-neighbor targeted hello configuration";

    container targeted {
      description
        "Specific neighbor targeted hello configuration";
      
      list address-family {
        key "afi-name";
        description
          "List of possible target address families";
        
        leaf afi-name {
          type leafref {
            path "../config/afi-name";
          }
        }

        container config {
          description
            "Configuration for a specific address family of targeted hellos";

          uses oc-ldp:mpls-ldp-address-family-config;
          uses oc-ldp:admin-config;
          uses mpls-ldp-targeted-dest-config;
        }

        container state {
          config false;
          description
            "Operation data for a specific address family of targeted hellos";

          uses oc-ldp:mpls-ldp-address-family-config;
          uses oc-ldp:admin-config;
          uses mpls-ldp-targeted-dest-config;
        }
      }

      container config {
        description
          "Configuration of targeted hello values which don't depend on a " +
          "specific address family";

          uses oc-ldp:mpls-ldp-hello-timers-top-config;
      }

      container state {
        config false;
        description
          "Operation data for neighbor wide targeted hellos values";

        uses oc-ldp:mpls-ldp-hello-timers-top-config;
      }
    }
  }

  grouping mpls-ldp-strict-targeted-hellos-config {
    description
      "Grouping containing strict targeted hellos configuration";
    
    container strict-targeted-hellos {
      description
        "Enable or disable strict targeted hellos mode";
      
      container config {
        description
          "Configuration of strict targeted hellos";
        
        uses mpls-ldp-strict-targeted-hellos;
      }

      container state {
        config false;
        description
          "Operation data for strict targeted hellos mode";
        uses mpls-ldp-strict-targeted-hellos;
      }
    }
  }

  grouping mpls-ldp-strict-targeted-hellos {
    description
      "Grouping containing strict targeted hellos mode";
    
    leaf strict-targeted-hellos {
      type boolean;
      default true;
      description
        "Enable or disable strict targeted hellos mode";
    }
  }

  grouping mpls-ldp-enable {
    description
      "Grouping containing the option to globally enable LDP";
    
    leaf enable {
      type boolean;
      default true;
      description
        "Globally enable or disable LDP";
    }
  }

  grouping mpls-ldp-global-enable-config {
    description
      "Grouping containing LDP global enable configuration";

    container enable {
      description
        "Globally enable or disable LDP";

      container config {
        description
          "Configuration for LDP enable or disable";

        uses mpls-ldp-enable;
      }

      container state {
        config false;
        description
          "Operation data for LDP global enable";

        uses mpls-ldp-enable;
      }
    }
  }

  grouping mpls-ldp-preference {
    description
      "Grouping containing the configurable preference for LDP LSP routes";

    leaf rib-preference {
      type uint8 {
        range "1..max";
      }
      description
        "RIB Route Preference value for LDP LSP routes";
    }
  }

  grouping mpls-ldp-preference-config {
    description
      "Grouping containing LDP RIB route preference configuration and state";

    container rib-preference {
      description
        "RIB LSP route preference";

      container config {
        description
          "Configuration of LDP route preference";

        uses mpls-ldp-preference;
      }

      container state {
        config false;
        description
          "Operation data for LDP route preference";

        uses mpls-ldp-preference;
      }
    }
  }

  grouping mpls-ldp-max-local-binding-config {
    description
      "Grouping containing maximum number of local binding configuration";

    container max-local-binding {
      description
        "Maximum number of local binding";

      container config {
        description
          "Configuration for maximum number of local binding";

        uses mpls-ldp-max-local-binding;
      }

      container state {
        config false;
        description
          "Operation data for the maximum number of local binding";

        uses mpls-ldp-max-local-binding;
      }
    }
  }

  grouping mpls-ldp-max-local-binding {
    description
      "Grouping containing maximum number of local binding";

    leaf maximum-local-binding {
      type uint32 {
        range "0..max";
      }
      description
        "Define the maximum number of local binding";
    }
  }

  grouping mpls-ldp-max-remote-binding-config {
    description
      "Grouping containing maximum number of remote binding configuration";

    container max-remote-binding {
      description
        "Maximum number of remote binding";

      container config {
        description
          "Configuration for maximum number of remote binding";

        uses mpls-ldp-max-remote-binding;
      }

      container state {
        config false;
        description
          "Operation data for the maximum number of remote binding";

        uses mpls-ldp-max-remote-binding;
      }
    }
  }

  grouping mpls-ldp-max-remote-binding {
    description
      "Grouping containing maximum number of remote binding";

    leaf maximum-remote-binding {
      type uint32 {
        range "0..max";
      }
      description
        "Define the maximum number of remote binding";
    }
  }

  grouping mpls-ldp-transport-address-config {
    description
      "Grouping containing interface-related attributes
       that can be configured for LDP.";

    container transport-address {
      description
        "Transport address configuration.";

      container config {
        description
          "Configuration for the transport address";

        uses mpls-ldp-transport-addresses;
      }

      container state {
        config false;
        description
          "Operation data for the tranport address.";

        uses mpls-ldp-transport-addresses;
      }
    }
  }

  grouping mpls-ldp-transport-addresses {
    description
      "Grouping containing transport address configuration.";

    leaf ipv4 {
      type inet:ip-address;
      description
        "Defines the transport address for Hello message and session
         on this interface.";
    }

    leaf ipv6 {
       type inet:ipv6-address;
       description
         "Defines the transport ipv6 address for Hello message and session
          on this interface.";
     }
  }

  grouping mpls-ldp-fec-filter {
    description
      "LDP FEC filtering";

    container fec-filter {
      description
        "LDP FEC filtering";

      container config {
        description
          "Configuration for FEC filtering";

        uses oc-rpol:apply-policy-export-config;
      }

      container state {
        config false;
        description
          "Operation data for FEC filtering";
        uses oc-rpol:apply-policy-export-config;
      }
    }
  }

  grouping mpls-ldp-sessions {
    description
      "LDP session information";

    container sessions {
      description
        "LDP Sessions";

      container ipv4 {
        config false;
        description
          "IPv4 LDP session information";

        uses mpls-ldp-sessions-v4;
      }

      container ipv6 {
        config false;
        description
          "IPv6 LDP session information";

        uses mpls-ldp-sessions-v6;
      }
    }
  }

  grouping mpls-ldp-sessions-v4 {
    description
      "IPv4 LDP session information";

    list session {
      config false;
      key "peer-address";

      description
        "List of IPv4 LDP sessions";

      leaf peer-address {
        type leafref {
          path "../state/peer-address";
        }
        description
          "reference to the peer-address data";
      }

      container state {
        description
          "Operational data for LDP session";

        uses mpls-ldp-session-state;
      }
    }
  }

  grouping mpls-ldp-sessions-v6 {
    description
      "IPv6 LDP session information";

    list session {
      config false;
      key "peer-address";

      description
        "List of IPv6 LDP sessions";

      leaf peer-address {
        type leafref {
          path "../state/peer-address";
        }
        description
          "reference to the peer-address data";
      }

      container state {
        description
          "Operational data for LDP session";

        uses mpls-ldp-session-state-v6;
      }
    }
  }

  grouping mpls-ldp-label-mapping {
    description
      "LDP Label Mapping";

    container label-mappings {
      description
        "LDP Label Mapping";

      container ipv4 {
        config false;
        description
          "IPv4 LDP Label Mapping";

        uses mpls-ldp-label-mapping-v4;
      }

      container ipv6 {
        config false;
        description
          "IPv6 LDP Label Mapping";

        uses mpls-ldp-label-mapping-v6;
      }
    }
  }

  grouping mpls-ldp-label-mapping-v4 {
    description
      "LDP Label Mapping";

    list label-mapping {
      config false;
      key "peer-address fec";

      description
        "List of Label Mapping";

      leaf peer-address {
        type leafref {
          path "../state/peer-address";
        }
        description
          "reference to the peer-address data";
      }

      leaf fec {
        type leafref {
          path "../state/fec";
        }
        description
          "reference to the fec data";
      }

      container state {
        description
          "Operational data of Label Mapping";

        uses mpls-ldp-label-mapping-state;
      }
    }
  }

  grouping mpls-ldp-label-mapping-v6 {
    description
      "LDP Label Mapping";

    list label-mapping {
      config false;
      key "peer-address fec";

      description
        "List of Label Mapping";

      leaf peer-address {
        type leafref {
          path "../state/peer-address";
        }
        description
          "reference to the peer-address data";
      }

      leaf fec {
        type leafref {
          path "../state/fec";
        }
        description
          "reference to the fec data";
      }

      container state {
        description
          "Operational data of Label Mapping";

        uses mpls-ldp-label-mapping-state-v6;
      }
    }
  }

  grouping mpls-ldp-hello-adjacency {
    description
      "LDP Hello Adjacency";

    container hello-adjacencies {
      description
        "LDP Hello Adjacency";

      container ipv4 {
        config false;
        description
          "IPv4 LDP hHello Adjacency";

        uses mpls-ldp-hello-adjacency-v4;
      }

      container ipv6 {
        config false;
        description
          "IPv6 LDP hHello Adjacency";

        uses mpls-ldp-hello-adjacency-v6;
      }
    }
  }

  grouping mpls-ldp-hello-adjacency-v4 {
    description
      "LDP Hello Adjacency";

    list hello-adjacency {
      config false;
      key "peer-address";

      description
        "list of Hello Adjacency";

      leaf peer-address {
        type leafref {
          path "../state/peer-address";
        }
        description
          "reference to the peer-address data";
      }

      container state {
        description
          "Operational Data of Hello Adjacency";

        uses mpls-ldp-hello-adjacency-state;
      }
    }
  }

  grouping mpls-ldp-hello-adjacency-v6 {
    description
      "LDP Hello Adjacency";

    list hello-adjacency {
      config false;
      key "peer-address";

      description
        "list of Hello Adjacency";

      leaf peer-address {
        type leafref {
          path "../state/peer-address";
        }
        description
          "reference to the peer-address data";
      }

      container state {
        description
          "Operational Data of Hello Adjacency";

        uses mpls-ldp-hello-adjacency-state-v6;
      }
    }
  }

  grouping mpls-ldp-session-state {
    description
      "Set of LDP session related state attribute";

    leaf peer-address {
      description
        "Peer address for a particular LDP session";
      type inet:ip-address;
    }

    leaf local-address {
      description
        "Local address for a particular LDP session";
      type inet:ip-address;
    }

    leaf session-state {
      description
        "Current state for a particular LDP session";
      type string;
    }

    leaf session-role {
      description
        "Session role for a particular LDP session";
      type string;
    }

    leaf keepalive-timeout {
      description
        "Keepalive timeout for a particular LDP session";
      type uint16;
    }

    leaf keepalive-interval {
      description
        "Keepalive interval for a particular LDP session";
      type uint16;
    }

    leaf local-lsr-id {
      description
        "Local LSR-ID for a particular LDP session";
      type inet:ip-address;
    }

    leaf local-label-space-id {
      description
        "Local Label Space ID for a particular LDP session";
      type uint16;
    }

    leaf remote-lsr-id {
      description
        "Remote LSR-ID for a particular LDP session";
      type inet:ip-address;
    }

    leaf remote-label-space-id {
      description
        "Remote Label Space ID for a particular LDP session";
      type uint16;
    }

    leaf graceful-restart {
      description
        "Graceful Restart of Remote peer";
      type string;
    }

    leaf graceful-restart-state {
      description
        "Graceful Restart State";
      type string;
    }

    leaf reconnect-time {
      description
        "Reconnect time";
      type uint16;
    }

    leaf recovery-time {
      description
        "Recovery timeout";
      type uint16;
    }

    leaf forwarding-holdtime {
      description
        "Forwarding Holdtime";
      type uint16;
    }

    leaf last-update-timestamp {
      type yang:date-and-time;
      description
        "The timestamp of when the session last changed states.";
    }

    leaf last-established-time {
      type yang:date-and-time;
      description
        "The timestamp of from when the session last transitioned to the
         operational state";
    }

    leaf uptime {
      type string;
      description
        "Elapsed time since a particular session has been established in " +
        "operational state";
    }

    leaf reset-count {
      type yang:zero-based-counter32;
      description
        "Number of times a particular session has transitioned from " +
        "operational state to non operational state";
    }
  }

  grouping mpls-ldp-session-state-v6 {
    description
      "Set of LDP session related state attribute";

    leaf peer-address {
      description
        "Peer address for a particular LDP session";
      type inet:ipv6-address;
    }

    leaf local-address {
      description
        "Local address for a particular LDP session";
      type inet:ipv6-address;
    }

    leaf session-state {
      description
        "Current state for a particular LDP session";
      type string;
    }

    leaf session-role {
      description
        "Session role for a particular LDP session";
      type string;
    }

    leaf keepalive-timeout {
      description
        "Keepalive timeout for a particular LDP session";
      type uint16;
    }

    leaf keepalive-interval {
      description
        "Keepalive interval for a particular LDP session";
      type uint16;
    }

    leaf local-lsr-id {
      description
        "Local LSR-ID for a particular LDP session";
      type inet:ip-address;
    }

    leaf local-label-space-id {
      description
        "Local Label Space ID for a particular LDP session";
      type uint16;
    }

    leaf remote-lsr-id {
      description
        "Remote LSR-ID for a particular LDP session";
      type inet:ip-address;
    }

    leaf remote-label-space-id {
      description
        "Remote Label Space ID for a particular LDP session";
      type uint16;
    }

    leaf graceful-restart {
      description
        "Graceful Restart of Remote peer";
      type string;
    }

    leaf graceful-restart-state {
      description
        "Graceful Restart State";
      type string;
    }

    leaf reconnect-time {
      description
        "Reconnect time";
      type uint16;
    }

    leaf recovery-time {
      description
        "Recovery timeout";
      type uint16;
    }

    leaf forwarding-holdtime {
      description
        "Forwarding Holdtime";
      type uint16;
    }

    leaf last-update-timestamp {
      type yang:date-and-time;
      description
        "The timestamp of when the session last changed states.";
    }

    leaf last-established-time {
      type yang:date-and-time;
      description
        "The timestamp of from when the session last transitioned to the
         operational state";
    }

    leaf uptime {
      type string;
      description
        "Elapsed time since a particular session has been established in " +
        "operational state";
    }

    leaf reset-count {
      type yang:zero-based-counter32;
      description
        "Number of times a particular session has transitioned from " +
        "operational state to non operational state";
    }
  }

  grouping mpls-ldp-label-mapping-state {
    description
      "Set of LDP Label Mapping related state attribute";

    leaf peer-address {
      description
        "Peer address for a particular LDP session";
      type inet:ip-address;
    }

    leaf fec {
      description
        "FEC";
      type inet:ip-prefix;
    }

    leaf upstream-binding {
      description 
        "Upstream label binding for a particular FEC";
      type uint32;
    }

    leaf downstream-binding {
      description
        "Downstream label binding for a particular FEC";
      type uint32;
    }
  }

  grouping mpls-ldp-label-mapping-state-v6 {
    description
      "Set of LDP Label Mapping related state attribute";

    leaf peer-address {
      description
        "Peer address for a particular LDP session";
      type inet:ipv6-address;
    }

    leaf fec {
      description
        "FEC";
      type inet:ipv6-prefix;
    }

    leaf upstream-binding {
      description 
        "Upstream label binding for a particular FEC";
      type uint32;
    }

    leaf downstream-binding {
      description
        "Downstream label binding for a particular FEC";
      type uint32;
    }
  }

  grouping mpls-ldp-hello-adjacency-state {
    description
      "Set of hello-adjacency related state attribute";

    leaf peer-address {
      description
        "LDP Peer address";
      type inet:ip-address;
    }

    leaf version {
      description
        "LDP version";
      type uint16;
    }

    leaf lsr-id {
      description
        "LDP Peer LSR ID";
      type inet:ip-address;
    }

    leaf label-space-id {
      description
        "LDP Peer Label Space ID";
      type uint16;
    }

    leaf transport-address {
      description
        "LDP Hello Transport Address";
      type inet:ip-address;
    }

    leaf source-address {
      description
        "LDP Hello Srouce Address";
      type inet:ip-address;
    }

    leaf holdtime {
      description
        "LDP Hello Holdtime";
      type uint32;
    }

    leaf interface {
      description
        "Interface on this hello adjacency";
      type string;
    }

    leaf uptime {
      type string;
      description
        "Length of time since the hello adjacency was established in " +
        "ddd:hh:mm:ss format";
    }

    leaf reset-count {
      type yang:zero-based-counter32;
      description
        "Number of times this hello adjacency has been recreated after " +
        "initial discovery";
    }

    leaf adjacency-type {
      type oc-ldp:mpls-ldp-adjacency-type;
      description
        "Hello adjacency type, from either basic or extended discovery";
    }
  }

  grouping mpls-ldp-hello-adjacency-state-v6 {
    description
      "Set of hello-adjacency related state attribute";

    leaf peer-address {
      description
        "LDP Peer address";
      type inet:ipv6-address;
    }

    leaf version {
      description
        "LDP version";
      type uint16;
    }

    leaf lsr-id {
      description
        "LDP Peer LSR ID";
      type inet:ip-address;
    }

    leaf label-space-id {
      description
        "LDP Peer Label Space ID";
      type uint16;
    }

    leaf transport-address {
      description
        "LDP Hello Transport Address";
      type inet:ipv6-address;
    }

    leaf source-address {
      description
        "LDP Hello Srouce Address";
      type inet:ipv6-address;
    }

    leaf holdtime {
      description
        "LDP Hello Holdtime";
      type uint32;
    }

    leaf interface {
      description
        "Interface on this hello adjacency";
      type string;
    }

    leaf uptime {
      type string;
      description
        "Length of time since the hello adjacency was established in " +
        "ddd:hh:mm:ss format";
    }

    leaf reset-count {
      type yang:zero-based-counter32;
      description
        "Number of times this hello adjacency has been recreated after " +
        "initial discovery";
    }

    leaf adjacency-type {
      type oc-ldp:mpls-ldp-adjacency-type;
      description
        "Hello adjacency type, from either basic or extended discovery";
    }
  }

  rpc clear-ldp-neighbor {
    description
      "Clear one or all LDP sessions.";

    input {
      leaf address-family {
        mandatory true;
        description
          "Address family";

        type oc-ldp:mpls-ldp-afi;
      }

      leaf address {
        mandatory true;
        description
          "All LDP sessions or the address of one LDP session.";
        type union {
          type enumeration {
            enum ALL {
              description
                "All LDP sessions";
            }
          }
          type inet:ip-address;
        }
      }
    }
  }

  rpc clear-ldp-adjacency {
    description
      "Clear one or all LDP adjacencies.";

    input {
      leaf interface {
        mandatory true;
        description
          "LDP adjacencies on all interfaces  or LDP adjacency on a specific interface.";
        type union {
          type enumeration {
            enum ALL {
              description
                "All LDP adjacencies";
            }
          }
          type oc-if:interface-id;
        }
      }
    }
  }

}
