module arcos-openconfig-if-aggregate-deviations {
  yang-version 1.1;
  namespace "http://yang.arrcus.com/arcos/openconfig/interfaces/aggregate/deviations";
  prefix arc-oc-lag-dev;

  import openconfig-if-aggregate {
    prefix oc-lag;
  }
  import openconfig-interfaces {
    prefix oc-if;
  }

  deviation "/oc-if:interfaces/oc-if:interface/oc-lag:aggregation" +
            "/oc-lag:config/oc-lag:lag-type"  {
    deviate add {
      default LACP;
    }
  }
}
