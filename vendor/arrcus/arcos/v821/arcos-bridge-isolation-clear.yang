module arcos-bridge-isolation-clear {
  yang-version 1.1;
  namespace "http://yang.arrcus.com/arcos/bridge-isolation/clear";

  prefix arc-brdg-isltn-clr;

  import openconfig-interfaces {
    prefix oc-if;
  }

  container bridge-isolation {
    description
      "Clear Interface Bridge Isolation drop statistics";

    action counters {
      description
        "Clear bridge isolation drop counters for a specific interface";
      input {
        leaf name {
          type leafref {
            path "/oc-if:interfaces/oc-if:interface/oc-if:name";
          }
          mandatory true;
          description
            "Interface name";
        }
      }
      output {
        leaf result {
          type string;
          description
            "The status of the clear operation";
        }
      }
    }
  }
}
