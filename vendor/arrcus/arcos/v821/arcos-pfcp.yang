module arcos-pfcp {
  yang-version 1.1;
  namespace "http://yang.arrcus.com/arcos/pfcp";
  prefix arc-pfcp;

  import openconfig-system {
    prefix oc-sys;
  }

  import ietf-yang-types {
    prefix "ietf-yang";
  }

  import ietf-inet-types {
    prefix inet;
  }

  import arcos-features {
    prefix arc-features;
  }

  organization
    "Arrcus, Inc.";

  contact
    "Arrcus, Inc.
     2077 Gateway Place
     Suite 400
     San Jose, CA 95110

     E-mail: yang-support@arrcus.com";

  description
    "This module defines ArcOS model for PFCP.

     Copyright (c) 2016-2022 by Arrcus, Inc.
     All rights reserved.";

  revision "2025-03-17" {
    description
      "Adding the forwarding-idle-time.";
  }

  revision "2023-10-27" {
    description
      "Adding the description.";
  }

  revision 2023-05-03 {
    description
      "Conditionally enable pfcp configs.";
  }

  revision "2022-07-29" {
    description
      "Adding pfcp config as a new module";
  }

  grouping system-pfcp-proxy-predefined-rule {
    leaf-list core-predefined-rule {
      type string;
      description
        "Predefined Rule for Core";
    }

    leaf-list access-predefined-rule {
      type string;
      description
        "Predefined rule for Access";
    }
  }

  grouping system-pfcp-proxy-application-id {
    leaf-list core-application-id {
      type string;
      description
        "Application ID for Core";
    }

    leaf-list access-application-id {
      type string;
      description
        "Application ID for Access";
    }
  }

  grouping system-pfcp-proxy-config {
    description
      "PFCP Proxy configuration";

    leaf pid {
      type int32 {
        range 0..64;
      }
      description
        "PFCP Proxy Process ID";
    }

    leaf description {
      type string;
      description
        "Description";
    }

    leaf node-id {
      type string;
      description
        "Node ID string";
    }

    leaf smf {
      type inet:ip-address;
      description
        "IP Address for SMF";
    }

    leaf upf {
      type inet:ip-address;
      description
        "IP Address for UPF";
    }

    leaf pfcp {
      type inet:ip-address;
      description
        "IP Address for PFCP Proxy";
    }

    leaf smf-port {
      type int32 {
        range 1024..65535;
      }
      description
        "Local port number for SMF";
    }

    leaf upf-port {
      type int32 {
        range 1024..65535;
      }
      description
        "Local port number for SMF";
    }

    leaf heartbeat-timeout-base {
        type uint32;
        description
            "Heartbeat Timeout";
    }

    leaf heartbeat-timeout-retry-interval {
        type uint32;
        description
            "Heartbeat timeout retry interval";
    }

    leaf heartbeat-timeout-retry {
        type uint32;
        description
            "Heartbeat timeoout retry";
    }

    leaf network-instance {
      type string;
      description
        "Network Instance";
    }

    leaf encoded-label {
      type boolean;
      default false;
      description
        "Encoded Label Syntax";
    }

    leaf enable-nat {
      type boolean;
      default false;
      description
        "Enable NAT";
    }

    leaf enable-message-forward {
      type boolean;
      default false;
      description
        "Enable to forward PFCP message between SMF and UPF";
    }

    leaf passthrough {
      type boolean;
      description
        "PFCP Pass Through mode";
    }

    leaf interface {
      type string;
      description
        "Interface for PFCP Pass Through mode";
    }

    leaf logging {
      type boolean;
      default false;
      description
        "Enable PFCP Proxy logging";
    }

    leaf pfcp-buffer-size {
      type uint32;
      description
        "PFCP Message buffer size";
    }

    leaf buffer-size {
      type uint32;
      description
        "Socket buffer size";
    }

    leaf forwarding-idle-time {
      type uint64;
      description
        "Idle Time in second after forwarding state is off";
    }

    leaf worker {
      type uint32 {
        range 1..64;
      }
      default 1;
      description
        "Number of PFCP Proxy worker thread";
    }

    leaf ie-format {
      type uint16 {
        range 0..1;
      }
      default 0;
      description
        "IE format (0 - normal, 1 - cisco)";
    }
  }

  grouping system-pfcp-proxy-policy-config {
    leaf access-network-instance {
      type string;
      description
        "N4 Network Instance Name for Access";
    }

    leaf remote-tep {
      type inet:ip-address;
      description
        "Remote TEP address";
    }
  }

  grouping system-pfcp-proxy-slave {
    description
      "PFCP Proxy slave";

    container pfcp-proxy-slave {
      container config {
        description
          "PFCP Proxy slave configuration";

        leaf smf-source {
          type inet:ip-address;
          description
            "PFCP Proxy slave source address for SMF";
        }

        leaf upf-source {
          type inet:ip-address;
          description
            "PFCP Proxy slave source address for UPF";
        }

        list slave {
          key "slave-address";

          description
            "PFCP Proxy slave configuration";

          leaf slave-address {
            type inet:ip-address;
            description
              "PFCP Proxy slave address";
          }
        }
      }
    }
  }

  grouping system-pfcp-proxy-state-per-seid {
    container sessions-per-seid {
      list session-per-seid {
        key "seid";

        description
          "PFCP Session information";

        leaf seid {
          type uint64;
          description
            "SEID";
        }

        leaf upf-n3-address {
          type inet:ip-address;
          description
            "N3 address of UPF";
        }

        leaf gnb-n3-address {
          type inet:ip-address;
          description
            "N3 address of gNB";
        }

        leaf access-teid {
          type uint32;
          description
            "TEID for Access";
        }

        leaf core-teid {
          type uint32;
          description
            "TEID for Core";
        }

        leaf qfi {
          type uint8;
          description
            "QFI value";
        }

        leaf ue-address-v4 {
          type inet:ip-address;
          description
            "IPv4 UE address";
        }

        leaf ue-address-v6 {
          type inet:ipv6-address;
          description
            "IPv6 UE address";
        }

        leaf core-network-instance {
          type string;
          description
            "Network Instance for Core";
        }

        leaf access-network-instance {
          type string;
          description
            "Network Instance for Access";
        }

        leaf imei {
          type string;
          description
            "IMEI";
        }

        leaf imsi {
          type string;
          description
            "IMSI";
        }

        leaf msisdn {
          type string;
          description
            "MSISDN";
        }

        leaf node-id {
          type string;
          description
            "Node ID";
        }

        leaf s-nssai-sst {
          type uint8;
          description
            "Slice Service Type";
        }

        leaf s-nssai-sd {
          type ietf-yang:hex-string;
          description
            "Slice Differentiator";
        }

        leaf core-traffic-class {
          type uint8;
          description
            "Traffic Class for Core";
        }

        leaf core-traffic-class-mask {
          type uint8;
          description
            "Traffic Class Mask for Core";
        }

        leaf access-traffic-class {
          type uint8;
          description
            "Traffic Class for Access";
        }

        leaf access-traffic-class-mask {
          type uint8;
          description
            "Traffic Class Mask for Access";
        }

        leaf forwarding-state {
          type boolean;
          description
            "Forwarding state";
        }

        leaf publish-state {
          type boolean;
          description
            "Publish state";
        }

        uses system-pfcp-proxy-predefined-rule;
        uses system-pfcp-proxy-application-id;
      }
    }
  }

  grouping system-pfcp-proxy-state-per-imsi {
    container sessions-per-imsi {
      list session-per-imsi {
        key "imsi index";

        description
          "PFCP Session information";

        leaf imsi {
          type string;
          description
            "IMSI";
        }

        leaf index {
          type uint32 {
            range 1..1024;
          }
          description
            "Index for the session";
        }

        leaf seid {
          type uint64;
          description
            "SEID";
        }

        leaf upf-n3-address {
          type inet:ip-address;
          description
            "N3 address of UPF";
        }

        leaf gnb-n3-address {
          type inet:ip-address;
          description
            "N3 address of gNB";
        }

        leaf access-teid {
          type uint32;
          description
            "TEID for Access";
        }

        leaf core-teid {
          type uint32;
          description
            "TEID for Core";
        }

        leaf qfi {
          type uint8;
          description
            "QFI value";
        }

        leaf ue-address-v4 {
          type inet:ip-address;
          description
            "IPv4 UE address";
        }

        leaf ue-address-v6 {
          type inet:ipv6-address;
          description
            "IPv6 UE address";
        }

        leaf core-network-instance {
          type string;
          description
            "Network Instance for Core";
        }

        leaf access-network-instance {
          type string;
          description
            "Network Instance for Access";
        }

        leaf imei {
          type string;
          description
            "IMEI";
        }

        leaf msisdn {
          type string;
          description
            "MSISDN";
        }

        leaf node-id {
          type string;
          description
            "Node ID";
        }

        leaf s-nssai-sst {
          type uint8;
          description
            "Slice Service Type";
        }

        leaf s-nssai-sd {
          type ietf-yang:hex-string;
          description
            "Slice Differentiator";
        }

        leaf core-traffic-class {
          type uint8;
          description
            "Traffic Class for Core";
        }

        leaf core-traffic-class-mask {
          type uint8;
          description
            "Traffic Class Mask for Core";
        }

        leaf access-traffic-class {
          type uint8;
          description
            "Traffic Class for Access";
        }

        leaf access-traffic-class-mask {
          type uint8;
          description
            "Traffic Class Mask for Access";
        }

        leaf forwarding-state {
          type boolean;
          description
            "Forwarding state";
        }

        leaf publish-state {
          type boolean;
          description
            "Publish state";
        }

        uses system-pfcp-proxy-predefined-rule;
        uses system-pfcp-proxy-application-id;
      }
    }
  }

  grouping system-pfcp-proxy-stat-counters {
    leaf session-establishment-request {
      type uint64;
      description
        "Number of Session-Establishment-Request";
    }
  
    leaf session-establishment-response {
      type uint64;
      description
        "Number of Session-Establishment-Response";
    }
  
    leaf session-establishment-response-success {
      type uint64;
      description
        "Number of success for Session-Establishment-Response";
    }
  
    leaf session-establishment-response-failure {
      type uint64;
      description
        "Number of failure for Session-Establishment-Response";
    }
  
    leaf session-modification-request {
      type uint64;
      description
        "Number of Session-Modification-Response";
    }
  
    leaf session-modification-response {
      type uint64;
      description
        "Number of Session-Modification-Response";
    }
  
    leaf session-modification-response-success {
      type uint64;
      description
        "Number of success for Session-Modification-Response";
    }
  
    leaf session-modification-response-failure {
      type uint64;
      description
        "Number of failure for Session-Modification-Response";
    }
  
    leaf session-deletion-request {
      type uint64;
      description
        "Number of Session-Deletion-Request";
    }
  
    leaf session-deletion-response {
      type uint64;
      description
        "Number of Session-Deletion-Response";
    }

    leaf session-report-request {
      type uint64;
      description
        "Number of Session-Report-Request";
    }
  }

  grouping system-pfcp-proxy-stat-per-seid {
    container sessions-statistics-per-seid {
      list session-statistics-per-seid {
        key "seid";
  
        description
          "Statistics for PFCP session";
  
        leaf seid {
          type uint64;
          description
            "SEID";
        }
  
        uses system-pfcp-proxy-stat-counters;
      }
    }
  }

  grouping system-pfcp-proxy-stat-per-imsi {
    container sessions-statistics-per-imsi {
      list session-statistics-per-imsi {
        key "imsi index";
  
        description
          "Statistics for PFCP session";
  
        leaf imsi {
          type string;
          description
            "IMSI";
        }

        leaf index {
          type uint32 {
            range 1..1024;
          }
          description
            "Index for the session";
        }

        leaf seid {
          type uint64;
          description
            "SEID";
        }
  
        uses system-pfcp-proxy-stat-counters;
      }
    }
  }

  grouping system-pfcp-proxy-stat-all {
    container statistics {
      description
        "Overall statistics";

      uses system-pfcp-proxy-stat-counters;
    }
  }

  grouping system-pfcp-proxy-state-summary {
    container session-summary {
      description
        "Summary of PDU session";

      leaf description {
        type string;
        description
          "Description of this PFCP Proxy instance";
      }

      leaf total-pdu-session {
        type uint64;
        description
          "Total number of PDU sessions";
      }

      leaf active-pdu-session {
        type uint64;
        description
          "Total number pf active PDU sessions";
      }

      leaf published-pdu-session {
        type uint64;
        description
          "Total number of published PDU sessions";
      }

      leaf deleted-pdu-session {
        type uint64;
        description
          "Total number of deleted PDU sessions";
      }
    }
  }

  grouping system-pfcp-proxy-top {
    description
      "Top-level grouping for PFCP Proxy";

    list pfcp-proxy {
      key "pid";

      description
        "PFCP Proxy configuration";

      leaf pid {
        type leafref {
          path "../config/pid";
        }
        description
          "PFCP Proxy Process ID";
      }

      container config {
        description
          "PFCP Proxy configuration";

        uses system-pfcp-proxy-config;
      }

      container state {
        config false;
        description
          "PFCP Proxy state";

        uses system-pfcp-proxy-state-per-seid;
        uses system-pfcp-proxy-state-per-imsi;
        uses system-pfcp-proxy-stat-per-seid;
        uses system-pfcp-proxy-stat-per-imsi;
        uses system-pfcp-proxy-state-summary;
        uses system-pfcp-proxy-stat-all;
      }
    }

    list n4-network-policy {
      key "access-network-instance";

      description
        "PFCP Policy Configuration";

      leaf access-network-instance {
        type leafref {
          path "../config/access-network-instance";
        }
        description
          "N4 Access Network Instance Name";
      }

      container config {
        description
          "PFCP Policy Configuration";

        uses system-pfcp-proxy-policy-config;
      }
    }

    uses system-pfcp-proxy-slave;
  }

  augment "/oc-sys:system" {
    uses system-pfcp-proxy-top {
      when "/arc-features:features/arc-features:feature[arc-features:name='arc-features:ARCOS_SRV6_MUP']/arc-features:supported = 'true' ";
    }
  }

  rpc restart-pfcp-proxy {
    description
      "Restart PFCP Proxy.";

    input {
      leaf pid {
        mandatory true;
        description
          "PID for PFCP Proxy.";
        type union {
          type enumeration {
            enum ALL {
              description
                "All PFCP Proxy.";
            }
          }
          type uint32;
        }
      }
    }
  }

  rpc clear-pfcp-session-imsi {
    description
      "Clear PFCP Session";

    input {
      leaf val {
        mandatory true;
        description
          "IMSI value";
        type union {
          type enumeration {
            enum ALL {
              description
                "All PFCP Session";
            }
          }
          type string;
        }
      }
    }
  }

  rpc clear-pfcp-session-seid {
    description
      "Clear PFCP Session";

    input {
      leaf val {
        mandatory true;
        description
          "SEID value";
        type union {
          type enumeration {
            enum ALL {
              description
                "All PFCP Session";
            }
          }
          type uint64;
        }
      }
    }
  }
}
