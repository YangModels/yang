submodule arcos-ospf-global {

  yang-version "1.1";

  belongs-to arcos-ospf {
    prefix "arc-ospf";
  }

  import ietf-yang-types { prefix "yang"; }
  import openconfig-network-instance { prefix "oc-netinst"; }
  import arcos-ospf-types { prefix "arc-ospf-types"; }
  import openconfig-policy-types { prefix "oc-pol-types"; }

  // Include submodules
  include arcos-ospf-common;
  include arcos-ospf-statistics;
  include arcos-ospf-spf;
  include arcos-ospf-rib;
  include arcos-ospf-aggregate;


  organization
    "Arrcus, Inc";

  contact
    "Arrcus, Inc.
     2077 Gateway Place
     Suite 400
     San Jose, CA 95110

     E-mail: yang-support@arrcus.com";

  description
    "This submodule provides OSPF configuration and operational
     state parameters that are global to a particular OSPF instance.

     Copyright (c) 2020-2024 by Arrcus, Inc.
     All rights reserved.";

  revision "2025-01-16" {
    description
      "Add igp-ldp-sync configuration";
  }

  revision "2024-02-29" {
    description
      "Add max-ecmp-paths configuration";
  }

  revision "2020-01-01" {
    description
      "Initial version";
  }


  grouping ospf-global-config {
    description
      "Global configuration for OSPF";

    leaf router-id {
      type yang:dotted-quad;
      description
        "A 32-bit number represented as a dotted quad assigned to
        each router running the OSPF protocol. This number should
        be unique within the autonomous system";
      reference "rfc2828";
    }

    leaf log-adjacency-changes {
      type arc-ospf-types:ospf-log-adj-changes-type;
      description
        "Specify whether and how often syslogs are generated when
        an OSPF neighbor changes its state.";
    }

    leaf max-ecmp-paths {
      type uint32 {
        range "1 .. 128";
      }
      description
        "Maximum count of ECMP paths.";
    }
  }

  grouping ospf-global-state {
    description
      "Global information for OSPF";

    leaf vrf-id {
      type uint32;
      description
        "L3VRF ID of this network-instance.";
    }

    leaf abr-router {
      type boolean;
      description
        "Indicates that this router is an ABR.";
    }

    leaf asbr-router {
      type boolean;
      description
        "Indicates that this router is an ASBR.";
    }

    leaf area-count {
      type uint32;
      description
        "Total number of areas configured.";
    }

    leaf stub-area-count {
      type uint32;
      description
        "Total number of stub areas configured.";
    }

    leaf configured-interface-count {
      type uint32;
      description
        "Total number of interfaces configured.";
    }

    leaf up-interface-count {
      type uint32;
      description
        "Total number of interfaces that are UP.";
    }

    leaf neighbor-count {
      type uint32;
      description
        "The number of neighbors under this interface";
    }

    leaf exchange-neighbor-count {
      type uint32;
      description
        "The number of neighbors under this interface that are in
         EXCHANGE state";
    }

    leaf loading-neighbor-count {
      type uint32;
      description
        "The number of neighbors under this interface that are in
         LOADING state";
    }

    leaf full-neighbor-count {
      type uint32;
      description
        "The number of neighbors under this interface that are in
         FULL state";
    }
  }

  grouping ospf-global-structure {
    description
      "Top level structural grouping for OSPF global parameters";

    container global {
      description
        "Configuration and operational state parameters for settings
        that are global to the OSPF instance";

      container config {
        description
          "Global configuration parameters for OSPF";

        uses ospf-global-config;
      }

      container state {
        config false;
        description
          "Operational state parameters for OSPF";

        uses ospf-global-config;
        uses ospf-global-state;
      }

      /*
       * OSPF Maintenance mode
       */
      container maintenance-mode {
        description
          "This container defines global maintenance mode
           configuration and state.";

        uses ospf-maint-structure;
      }

      /*
       * OSPF Max-LSA
       */
      container max-lsa {
        description
          "This container defines global Max-LSA configuration and state.";

        uses ospf-max-lsa-structure;
      }

      /*
       * OSPF SPF
       */
      container spf {
        description
          "This container defines global SPF
          configuration, state, statistics and logging.";

        uses ospf-spf-throttle-structure;
        uses ospf-spf-logging-structure;
      }

      /*
       * OSPF RIB
       */
      container rib {
        description
          "This container defines OSPF RIB.";

        uses ospf-nexthop-sets-structure;
        uses ospf-prefixes-structure;
        uses ospf-redistributed-prefixes-structure;
        uses ospf-asbrs-structure;
      }

      /*
       * OSPF auto-cost reference-bandwidth
       */
      container auto-cost {
        description
          "Enables the auto-cost of metric calculation for interfaces.";
        container config {
          uses ospf-auto-cost-config;
        }
        container state {
          config false;
          uses ospf-auto-cost-config;
        }
      }

      /*
       * OSPF Redistribute Aggregates
       */
      uses ospf-redistribute-aggregates-structure;

      /*
       * OSPF Statistics
       */
      container statistics {
        config false;
        description
          "This container defines global statistics.";

        uses ospf-pkt-statistics-structure;
        uses ospf-global-lsa-statistics-structure;
        uses ospf-global-spf-statistics-structure;
        uses ospf-global-rib-statistics-structure;

        uses ospf-global-snmp-statistics-structure {
          when "../../../oc-netinst:config/oc-netinst:identifier = 'oc-pol-types:OSPF'" {
            description
              "Only OSPFv2 SNMP MIBs are supported currently";
          }
        }
      }

      /*
       * OSPF SNMP
       */
      container snmp {
        description
          "This container defines global SNMP
           configuration and state.";

        when "../../../oc-netinst:config/oc-netinst:identifier = 'oc-pol-types:OSPF'" {
          description
            "Only OSPFv2 SNMP MIBs are supported currently";
        }

        uses ospf-snmp-structure;
      }

      container mpls {
        description
          "OSPF parameters relating to MPLS";

        container igp-ldp-sync {
          description
            "OSPF parameters relating to LDP/IGP synchronization";

          container config {
            description
              "Configuration parameters relating to LDP/IG
               synchronization.";
            uses ospf-common-mpls-igp-ldp-sync-config;
          }

          container state {
            config false;
            description
              "Operational state variables relating to LDP/IGP
               synchronization";
            uses ospf-common-mpls-igp-ldp-sync-config;
          }
        }
      }
    }
  }
}
