module arcos-rsvp-debug-mplste {
  yang-version "1";
  namespace "http://yang.arrcus.com/arcos/rsvp/debug/mplste";
  prefix arc-rsvp-dbg-mplste;

  import openconfig-policy-types {
    prefix oc-pol-types;
  }

  import arcos-openconfig-policy-types {
    prefix arc-oc-pol-types;
  }

  import arcos-debug {
    prefix arc-dbg;
  }

  organization
    "Arrcus, Inc";

  contact
    "Arrcus, Inc.
     2077 Gateway Place
     Suite 400
     San Jose, CA 95110

     E-mail: yang-support@arrcus.com";

  description
    "This module defines debug statements for Arrcus 
     implementation of MPLS-TE.";

  revision "2022-05-31" {
    description
      "Initial version.";
  }

  grouping rsvp-debug-mplste-top {
    container rsvp {
      description
        "This container defines instance-specific RSVP component debug "
        + "information for MPLS-TE configs.";
      config false;

      uses arc-dbg:debug-component-top;
    }
  }

  augment "/arc-dbg:debug/arc-dbg:network-instances/arc-dbg:network-instance" +
          "/arc-dbg:debug-attach-points" {
    uses rsvp-debug-mplste-top {
      when "arc-dbg:component = 'mpls-te'" {
        description
          "Include MPLS-TE related debug information in RSVP component when "
          + "MPLS-TE is configured for a network instance.";
      }
      description
        "MPLS-TE related debug information from RSVP component.";
    }
  }
}
