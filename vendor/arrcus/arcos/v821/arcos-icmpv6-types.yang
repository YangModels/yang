module arcos-icmpv6-types {
  yang-version 1.1;
  namespace "http://yang.arrcus.com/arcos/icmpv6/types";
  prefix arc-icmpv6-types;

  organization
    "Arrcus, Inc.";

    contact
        "Email: eng@arrcus.com";

  description
    "This module defines Internet Control Message Protocol version 6
    (ICMPv6) message types and codes for use in models requiring data
    definitions related to ICMPv6.";

  revision 2023-08-30 {
      description 
        "Removed icmp type/code range restriction";
  }

  revision 2018-08-14 {
      description "ArcOS release 2.2.1";
  }


  revision "2017-09-21" {
    description
      "Initial revision.";

    reference "1.0.0";
  }


  identity ICMPV6_TYPE {
    description
      "Base identity for ICMPv6 message type values used in ICMPv6 packet
      header. The reserved and experimental types are not defined in this
      identity.";
    reference
      "RFC 4443";
  }

  identity ICMPV6_DST_UNREACH {
    base ICMPV6_TYPE;
    description
      "Destination Unreachable (1)";
  }

  identity ICMPV6_PKT_TOO_BIG {
    base ICMPV6_TYPE;
    description
      "Packet Too Big (2)";
  }

  identity ICMPV6_TIME_EXCEEDED {
    base ICMPV6_TYPE;
    description
      "Time Exceeded (3)";
  }

  identity ICMPV6_PARAM_PROBLEM {
    base ICMPV6_TYPE;
    description
      "Parameter Problem (4)";
  }

  identity ICMPV6_ECHO_REQUEST {
    base ICMPV6_TYPE;
    description
      "Echo Request (128)";
  }

  identity ICMPV6_ECHO_REPLY {
    base ICMPV6_TYPE;
    description
      "Echo Reply (129)";
  }

  identity ICMPV6_MCAST_LISTENER_QUERY {
    base ICMPV6_TYPE;
    description
      "Multicast Listener Query (130)";
  }

  identity ICMPV6_MCAST_LISTENER_REPORT {
    base ICMPV6_TYPE;
    description
      "Multicast Listener Report (131)";
  }

  identity ICMPV6_MCAST_LISTENER_DONE {
    base ICMPV6_TYPE;
    description
      "Multicast Listener Done (132)";
  }

  identity ICMPV6_ROUTER_SOLICIT {
    base ICMPV6_TYPE;
    description
      "Router Solicitation (133)";
  }

  identity ICMPV6_ROUTER_ADVERT {
    base ICMPV6_TYPE;
    description
      "Router Advertisement (134)";
  }

  identity ICMPV6_NEIGHBOR_SOLICIT {
    base ICMPV6_TYPE;
    description
      "Neighbor Solicitation (135)";
  }

  identity ICMPV6_NEIGHBOR_ADVERT {
    base ICMPV6_TYPE;
    description
      "Neighbor Advertisement (136)";
  }

  identity ICMPV6_REDIRECT {
    base ICMPV6_TYPE;
    description
      "Redirect Message (137)";
  }

  identity ICMPV6_ROUTER_RENUMBER {
    base ICMPV6_TYPE;
    description
      "Router Renumbering (138)";
  }

  identity ICMPV6_NODE_INFO_QUERY {
    base ICMPV6_TYPE;
    description
      "ICMP Node Information Query (139)";
  }

  identity ICMPV6_NODE_INFO_RESPONSE {
    base ICMPV6_TYPE;
    description
      "ICMP Node Information Response (140)";
  }

  identity ICMPV6_INVERSE_ND_SOLICIT {
    base ICMPV6_TYPE;
    description
      "Inverse Neighbor Discovery Solicitation Message (141)";
  }

  identity ICMPV6_INVERSE_ND_ADVERT {
    base ICMPV6_TYPE;
    description
      "Inverse Neighbor Discovery Advertisement Message (142)";
  }

  identity ICMPV6_MCAST_LISTENER_DISCOVERY_REPORT {
    base ICMPV6_TYPE;
    description
      "Multicast Listener Discovery Reports (143)";
  }

  identity ICMPV6_HOME_AGENT_AD_REQUEST {
    base ICMPV6_TYPE;
    description
      "Home Agent Address Discovery Request Message (144)";
  }

  identity ICMPV6_HOME_AGENT_AD_REPLY {
    base ICMPV6_TYPE;
    description
      "Home Agent Address Discovery Reply Message (145)";
  }

  identity ICMPV6_MOBILE_PREFIX_SOLICIT {
    base ICMPV6_TYPE;
    description
      "Mobile Prefix Solicitation (146)";
  }

  identity ICMPV6_MOBILE_PREFIX_ADVERT {
    base ICMPV6_TYPE;
    description
      "Mobile Prefix Advertisement (147)";
  }

  identity ICMPV6_CERTIFICATION_PATH_SOLICIT {
    base ICMPV6_TYPE;
    description
      "Certification Path Solicitation (148)";
  }

  identity ICMPV6_CERTIFICATION_PATH_ADVERT {
    base ICMPV6_TYPE;
    description
      "Certification Path Advertisement (149)";
  }

  identity ICMPV6_MCAST_ROUTER_ADVERT {
    base ICMPV6_TYPE;
    description
      "Multicast Router Advertisement (151)";
  }

  identity ICMPV6_MCAST_ROUTER_SOLICIT {
    base ICMPV6_TYPE;
    description
      "Multicast Router Solicitation (152)";
  }

  identity ICMPV6_MCAST_ROUTER_TERMINATION {
    base ICMPV6_TYPE;
    description
      "Multicast Router Termination (153)";
  }

  identity ICMPV6_RPL_CONTROL {
    base ICMPV6_TYPE;
    description
      "RPL Control Message (155)";
  }


  identity ICMPV6_DST_UNREACH_CODE {
    description
      "Base identity for ICMPv6 message code values for type
      Destination Unreachable used in ICMPv6 packet header.";
    reference
      "RFC 4443";
  }

  identity ICMPV6_NO_ROUTE_TO_DST {
    base ICMPV6_DST_UNREACH_CODE;
    description
      "No Route to Destination (0)";
  }

  identity ICMPV6_COMM_PROHIBITED {
    base ICMPV6_DST_UNREACH_CODE;
    description
      "Communication with Destination Administratively Prohibited (1)";
  }

  identity ICMPV6_BEYOND_SCOPE {
    base ICMPV6_DST_UNREACH_CODE;
    description
      "Beyond Scope of Source Address (2)";
  }

  identity ICMPV6_ADDRESS_UNREACH {
    base ICMPV6_DST_UNREACH_CODE;
    description
      "Address Unreachable (3)";
  }

  identity ICMPV6_PORT_UNREACH {
    base ICMPV6_DST_UNREACH_CODE;
    description
      "Port Unreachable (4)";
  }

  identity ICMPV6_SRC_ADDRESS_FAIL {
    base ICMPV6_DST_UNREACH_CODE;
    description
      "Source Address Failed Ingress/Egress Policy (5)";
  }

  identity ICMPV6_REJECT_ROUTE {
    base ICMPV6_DST_UNREACH_CODE;
    description
      "Reject Route to Destination (6)";
  }

  identity ICMPV6_ERR_IN_SR_HEADER {
    base ICMPV6_DST_UNREACH_CODE;
    description
      "Error in Source Routing Header (7)";
  }


  // ICMPv6 codes for type Time Exceeded (Type 3)
  identity ICMPV6_TIME_EXCEEDED_CODE {
    description
      "Base identity for ICMPv6 message code values for type
      Time Exceeded used in ICMPv6 packet header.";
    reference
      "RFC 4443";
  }

  identity ICMPV6_HOP_LIMIT_EXCEEDED {
    base ICMPV6_TIME_EXCEEDED_CODE;
    description
      "Hop Limit Exceeded in Transit (0)";
  }

  identity ICMPV6_REASSEMBLY_TIME_EXCEEDED {
    base ICMPV6_TIME_EXCEEDED_CODE;
    description
      "Fragment Reassembly Time Exceeded (1)";
  }


  identity ICMPV6_PARAM_PROB_CODE {
    description
      "Base identity for ICMPv6 message code values for type
      Parameter Problem used in ICMPv6 packet header.";
    reference
      "RFC 4443";
  }

  identity ICMPV6_ERR_HEADER_FIELD {
    base ICMPV6_PARAM_PROB_CODE;
    description
      "Erroneous Header Field Encountered (0)";
  }

  identity ICMPV6_UNRECOGNIZED_NEXT_HEADER_TYPE {
    base ICMPV6_PARAM_PROB_CODE;
    description
      "Unrecognized Next Header Type Encountered (1)";
  }

  identity ICMPV6_UNRECOGNIZED_IPV6_OPTION {
    base ICMPV6_PARAM_PROB_CODE;
    description
      "Unrecognized IPv6 Option Encountered (2)";
  }


  identity ICMPV6_ROUTER_RENUMBER_CODE {
    description
      "Base identity for ICMPv6 message code values for type
      Router Renumbering used in ICMPv6 packet header.";
    reference
      "N/A";
  }

  identity ICMPV6_ROUTER_RENUMBER_COMMAND {
    base ICMPV6_ROUTER_RENUMBER_CODE;
    description
      "Router Renumbering Command (0)";
  }

  identity ICMPV6_ROUTER_RENUMBER_RESULT {
    base ICMPV6_ROUTER_RENUMBER_CODE;
    description
      "Router Renumbering Result (1)";
  }

  identity ICMPV6_SEQUENCE_NUMBER_RESET {
    base ICMPV6_ROUTER_RENUMBER_CODE;
    description
      "Sequence Number Reset (255)";
  }


  identity ICMPV6_NODE_INFO_QUERY_CODE {
    description
      "Base identity for ICMPv6 message code values for type
      ICMP Node Information Query used in ICMPv6 packet header.";
    reference
      "RFC 4620";
  }

  identity ICMPV6_QUERY_SUBJECT_IPV6_ADDRESS {
    base ICMPV6_NODE_INFO_QUERY_CODE;
    description
      "The Data field contains an IPv6 address which is the Subject of
      this Query (0)";
  }

  identity ICMPV6_QUERY_SUBJECT_NAME {
    base ICMPV6_NODE_INFO_QUERY_CODE;
    description
      "The Data field contains a name which is the Subject of this Query,
      or is empty, as in the case of a NOOP (1)";
  }

  identity ICMPV6_QUERY_SUBJECT_IPV4_ADDRESS {
    base ICMPV6_NODE_INFO_QUERY_CODE;
    description
      "The Data field contains an IPv4 address which is the Subject of
      this Query (2)";
  }

  identity ICMPV6_NODE_INFO_RESPONSE_CODE {
    description
      "Base identity for ICMPv6 message code values for type
      ICMP Node Information Response used in ICMPv6 packet header.";
    reference
      "RFC 4620";
  }

  identity ICMPV6_SUCCESSFUL_REPLY {
    base ICMPV6_NODE_INFO_RESPONSE_CODE;
    description
      "A successful reply. The Reply Data field may or may not be empty (1)";
  }

  identity ICMPV6_ANSWER_REFUSED {
    base ICMPV6_NODE_INFO_RESPONSE_CODE;
    description
      "The Responder refuses to supply the answer. The Reply Data field
      will be empty (1)";
  }

  identity ICMPV6_QTYPE_UNKNOWN {
    base ICMPV6_NODE_INFO_RESPONSE_CODE;
    description
      "The Qtype of the Query is unknown to the Responder. The Reply Data
      field will be empty (2)";
  }


  typedef icmpv6-type {
    type union {
      type uint8 {
        range 0..255;
      }
      type identityref {
        base ICMPV6_TYPE;
      }
      type string {
        pattern '(2[0-5][0-5]|[0-1]?[0-9]?[0-9]?)\.\.(2[0-5][0-5]|[0-1]?' +
                '[0-9]?[0-9]?)';
      }
    }
    description
      "The ICMPv6 message type value(s) may be represented as a single
      valid number (integer [0, 255]), using a type defined by the
      ICMPV6_TYPE identity.";
  }

  typedef icmpv6-dst-unreach-code {
    type union {
      type uint8 {
        range 0..7;
      }
      type identityref {
        base ICMPV6_DST_UNREACH_CODE;
      }
      type string {
        pattern '([0-7])\.\.([0-7])';
      }
    }
    description
      "The ICMPv6 Destination Unreachable code value(s) may be represented
      as a single valid number (integer [0, 7]), using a type defined by
      the ICMPV6_DST_UNREACH_CODE identity, or using a string to indicate a
      range of code as <lower>..<higher>.";
  }

  typedef icmpv6-time-exceeded-code {
    type union {
      type uint8 {
        range 0..1;
      }
      type identityref {
        base ICMPV6_TIME_EXCEEDED_CODE;
      }
      type string {
        pattern '(0|1)\.\.(0|1)';
      }
    }
    description
      "The ICMPv6 Time Exceeded code value(s) may be represented as
      a single valid number (integer 0 or 1), using a type defined
      by the ICMPV6_TIME_EXCEEDED_CODE identity, or using a string
      to indicate a range of codes as <lower>..<higher>.";
  }

  typedef icmpv6-param-problem-code {
    type union {
      type uint8 {
        range 0..2;
      }
      type identityref {
        base ICMPV6_PARAM_PROB_CODE;
      }
      type string {
        pattern '([0-2])\.\.([0-2])';
      }
    }
    description
      "The ICMPv6 Parameter Problem code value(s) may be represented
      as a single valid number (integer [0, 2]), using a type defined
      by the ICMPV6_PARAM_PROB_CODE identity, or using a string to
      indicate a range of codes as <lower>..<higher>.";

  }

  typedef icmpv6-router-renumber-code {
    type union {
      type uint8 {
        range "0..1 | 255";
      }
      type identityref {
        base ICMPV6_ROUTER_RENUMBER_CODE;
      }
      type string {
        pattern '(0|1)\.\.(0|1|255)';
      }
    }
    description
      "The ICMPv6 Router Renumbering code value(s) may be represented
      as a single valid number (integer 0, 1 or 255), using a type
      defined by the ICMPV6_ROUTER_RENUMBER_CODE identity, or using a
      string to indicate a range of codes as <lower>..<higher>.";
  }

  typedef icmpv6-node-info-query-code {
    type union {
      type uint8 {
        range 0..2;
      }
      type identityref {
        base ICMPV6_NODE_INFO_QUERY_CODE;
      }
      type string {
        pattern '([0-2])\.\.([0-2])';
      }
    }
    description
      "The ICMPv6 Note Information Query code value(s) may be
      represented as a single valid number (integer [0, 2]),
      using a type defined by the ICMPV6_NODE_INFO_QUERY_CODE
      identity, or using a string to indicate a range of codes
      as <lower>..<higher>.";
  }

  typedef icmpv6-node-info-response-code {
    type union {
      type uint8 {
        range 0..2;
      }
      type identityref {
        base ICMPV6_NODE_INFO_RESPONSE_CODE;
      }
      type string {
        pattern '([0-2])\.\.([0-2])';
      }
    }
    description
      "The ICMPv6 Note Information RESPONSE code value(s) may be
      represented as a single valid number (integer [0, 2]),
      using a type defined by the ICMPV6_NODE_INFO_RESPONSE_CODE
      identity, or using a string to indicate a range of codes
      as <lower>..<higher>.";
  }
}
