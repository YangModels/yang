module arcos-openconfig-if-ethernet-deviations {
  yang-version 1.1;
  namespace "http://yang.arrcus.com/arcos/openconfig/interfaces/ethernet/deviations";
  prefix arc-oc-eth-dev;

  import openconfig-if-ethernet {
    prefix oc-eth;
  }
  import openconfig-interfaces {
    prefix oc-if;
  }

  deviation "/oc-if:interfaces/oc-if:interface/oc-eth:ethernet" +
            "/oc-eth:config/oc-eth:mac-address"  {
    deviate not-supported;
    description "Not supported in this release";
  }
  deviation "/oc-if:interfaces/oc-if:interface/oc-eth:ethernet" +
            "/oc-eth:config/oc-eth:auto-negotiate"  {
    deviate delete {
      default true;
    }
    deviate add {
      must "(boolean(current() = 'true') != 'true') or not(../oc-eth:port-speed)" {
        error-message "If auto_neg is True, speed must not be set";
      }
    }
  }
  deviation "/oc-if:interfaces/oc-if:interface/oc-eth:ethernet" +
            "/oc-eth:config/oc-eth:port-speed"  {
    deviate add {
      must "not(current()) or (boolean(../oc-eth:auto-negotiate = 'true') != 'true')" {
        error-message "If speed is set, auto-negotiate must not be set";
      }
    }
  }
  deviation "/oc-if:interfaces/oc-if:interface/oc-eth:ethernet" +
            "/oc-eth:config/oc-eth:duplex-mode"  {
    deviate not-supported;
    description "Not supported in this release";
  }
  deviation "/oc-if:interfaces/oc-if:interface/oc-eth:ethernet" +
            "/oc-eth:config/oc-eth:enable-flow-control"  {
    deviate not-supported;
    description "Not supported in this release";
  }
}
