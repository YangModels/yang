module arcos-copp {
  yang-version 1.1;
  namespace "http://yang.arrcus.com/arcos/copp";
  prefix arc-copp;

  import arcos-platform {
    prefix arc-platform;
  }
  import openconfig-system {
    prefix oc-sys;
  }

  import arcos-openconfig-system-augments {
    prefix arc-oc-sys-aug;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for top-level CoPP
    
    Copyright (c) 2016-2023 by Arrcus, Inc.
     All rights reserved.";

  revision 2024-11-07 {
    description "Modified the 'when' clause to ensure that the condition considers additional cases";
  }
  
  revision 2023-06-27 {
    description
      "Initial revision.";
  }

  grouping copp-top {
    description
      "Top level grouping for CoPP";
    container copp {
      description
        "Control Plane Policer";
      action counters {
        description
          "Clear all CoPP statistics";
        output {
          leaf result {
            type string;
            description
              "The status of the clear operation";
          }
        }
      }
    }
  }

  uses copp-top {
    when "(/arc-platform:platform/arc-platform:asic != 'arc-platform:X86_64') or " +
        "(/arc-platform:platform/arc-platform:deployment-type = 'arc-platform:DISTRIBUTED') or "+
        "(/oc-sys:system/arc-oc-sys-aug:cli/arc-oc-sys-aug:config/arc-oc-sys-aug:unhide-unsupported-cli = 'true')";
  }
}
