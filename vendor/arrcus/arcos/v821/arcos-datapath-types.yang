module arcos-datapath-types {

  yang-version "1.1";

  namespace "http://yang.arrcus.com/arcos/datapath/types";

  prefix "arcos-dp-types";

  organization
    "XXXX - TBD - XXXX";

  contact
    "XXXX - TBD - XXXX";

  description
    "This model describes the various types used by the ArcOS datapath
     model.";

  identity ARCOS_DATAPATH_TYPE {
    description
      "Base identity for datapath types.";
  }

  identity ARCOS_DATAPATH_ASIC {
    base ARCOS_DATAPATH_TYPE;
    description
      "ASIC datapath";
  }

  identity ARCOS_DATAPATH_SOFTWARE {
    base ARCOS_DATAPATH_TYPE;
    description
      "Software datapath";
  }
}
