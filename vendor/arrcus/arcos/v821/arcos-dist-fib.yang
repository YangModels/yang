module arcos-dist-fib {
  yang-version 1.1;
  namespace "http://yang.arrcus.com/arcos/dist/fib";
  prefix arc-dist-fib;

  import openconfig-network-instance {
    prefix oc-netinst;
  }
  import openconfig-yang-types {
    prefix oc-yang;
  }
  import ietf-inet-types {
    prefix inet;
  }
  import openconfig-mpls-types {
    prefix oc-mplst;
  }
  import openconfig-types {
    prefix oc-types;
  }
  import ietf-yang-types {
    prefix yang;
  }
  import arcos-runtime {
    prefix arc-runtime;
  }

  organization
    "Arrcus, Inc";

  contact
    "Arrcus, Inc.
     2077 Gateway Place,
     San Jose, CA 95110
     Tel: +1 (408) 884-1965
     E-mail: yang-support@arrcus.com";

  description
    "This module lists the FIB related information for distributed platforms.
     Copyright 2019-2023 by Arrcus, Inc.
     All rights reserved.";
    
  revision 2025-07-20 {
    description
      "Add dpal publish stats";
  }

  revision 2024-10-21 {
    description
      "Add jmirror header state to tunnels";
  }

  revision 2024-08-11 {
    description
      "Add NHT stats in fib stats output";
  }

  revision 2024-08-01 {
    description
      "Separation of ipv* and ipv*-eos0-nh container-id tables";
  }

  revision 2024-07-30 {
    description
      "* Change RNH list keys to include type along with value
       * Define bits for nexthop and prefix flags";
  }

  revision 2024-04-30 {
    description
      "Add LI tunnel type";
  }

  revision 2024-03-11 {
    description
      "* Add IP UNNUMBERED display bit for path.";
  }

  revision 2023-08-13 {
    description
      "Use prefix types based on IPV4 or IPV6 route";
  }

  revision 2023-05-13 {
    description
      "* Add Nexthop-type for the path and recursive-nexthops
       * Type changes for flags attribute in path
       * SR-Policy recursive nexthops is merged with IPv4/IPv6 recursive nexthops";
  }

  revision 2023-02-08 {
    description
      "Fix naming inconsistencies in comparison to arcos-fib module";
  }

  typedef fib-path-type {
    type enumeration {
      enum "RECURSIVE" {
        value 1;
      }
      enum "CONNECTED_V4" {
        value 2;
      }
      enum "ADJ_RNH_V4" {
        value 3;
      }
      enum "LOCAL_V4" {
        value 4;
      }
      enum "GLEAN_V4" {
        value 5;
      }
      enum "CONNECTED_V6" {
        value 6;
      }
      enum "ADJ_RNH_V6" {
        value 7;
      }
      enum "LOCAL_V6" {
        value 8;
      }
      enum "GLEAN_V6" {
        value 9;
      }
      enum "DROP" {
        value 10;
      }
      enum "VXLAN_V4" {
        value 11;
      }
    }
  }

  typedef publish-path-type {
    type enumeration {
      enum PATH {
        value 1;
        description "Path";
      }
      enum ECMP {
        value 2;
        description "Equal cost multi paths";
      }
      enum RECURSIVE_PATH {
        value 3;
        description "Recursive path";
      }
      enum VXLAN_PATH {
        value 4;
        description "VxLAN path";
      }
      enum PROTECTED_PATH {
        value 5;
        description "Protected path";
      }
    }
  }

  typedef rnh-state-type {
    type enumeration {
      enum INVALID {
        value 0;
        description "RNH is invalid";
      }
      enum RESOLVED {
        value 1;
        description "RNH is resolved";
      }
      enum UNRESOLVED {
        value 2;
        description "RNH is not-resolved";
      }
      enum REJECT {
        value 3;
        description "RNH is not-resolved";
      }
      enum ENQUEUE {
        value 4;
        description "RNH is enqueued";
      }
      enum PLACEHOLDER {
        value 5;
        description "RNH is a place-holder";
      }
    }
  }

  typedef nexthop-value-type {
    type union {
      type inet:ip-address-no-zone;
      type inet:ip-prefix;
      type uint32;
    }
    description
      "Type for the nexthop ID";
  }

  typedef base-flags-type {
    type bits {
      bit DELETE_PENDING {
        position 0;
      }
      bit STALE {
        position 1;
      }
      bit ON_PUBLISH_LIST {
        position 2;
      }
      bit ACK_REQUIRED {
        position 3;
      }
      bit STATUS_VALID {
        position 4;
      }
      bit FORCE_PUBLISH {
        position 5;
      }
    }
  }

  typedef prefix-flags-type {
    type bits {
      bit UNRESOLVED {
        position 0;
      }
      bit DEFAULT {
        position 1;
      }
      bit LOCAL {
        position 2;
      }
    }
  }

  typedef nexthop-flags-type {
    type bits {
      bit UNRESOLVED {
        position 0;
      }
      bit RECURSIVE {
        position 1;
      }
      bit LOCAL {
        position 2;
      }
      bit IP_REACH {
        position 3;
      }
      bit MPLS_REACH {
        position 4;
      }
      bit MIXED_REACH {
        position 5;
      }
      bit PLACEHOLDER {
        position 6;
      }
      bit HAS_BACKUP {
        position 7;
      }
    }
  }

  typedef nexthop-type {
    type enumeration {
      enum "IPV4" {
        value 1;
        description "IPv4 address as nexthop";
      }
      enum "IPV6" {
        value 2;
        description "IPv6 address as nexthop";
      }
      enum "SR-POLICY" {
        value 3;
        description "SR-Policy ID as nexthop";
      }
      enum "IGP" {
        value 4;
        description "IGP ID as next-hop";
      }
    }
  }

  grouping ipv4-nexthop-info {
    container paths {
      list path {
        key "path-id";
        leaf path-id {
          type uint32;
          description
            "ID of the Path";
        }
        leaf path-type {
          type fib-path-type;
          description
            "Type of the Path";
        }
        leaf nh-type {
          type nexthop-type;
          description
            "Next-hop type";
        }
        leaf next-hop {
          type nexthop-value-type;
          description
            "IP address or nexthop ID of the Path";
        }
        leaf-list push-label {
          type oc-mplst:mpls-label;
          description
            "The MPLS label stack imposed when forwarding packets
             to the nexthop  ";
        }
        leaf nh-tunnel-id {
          type uint32;
          description
            "VXLAN Tunnel id for the nexthop";
        }
        leaf nh-tunnel-vni-id {
          type uint32;
          description
            "VXLAN Tunnel vni id for the nexthop";
        }
        leaf rtep-mac {
          type oc-yang:mac-address;
          description
            "Remote tunnel-endpoint MAC address for a vxlan tunnel nexthop";
        }
        leaf interface {
          type string;
          description
            "Name of the interface for the connected nexthop type";
        }
        leaf network-instance {
          type string;
          description
            "Network Instance name";
        }
        leaf num-coll-paths {
          type uint32;
          description
            "Number of collapsed paths downloaded to hardware.
             Applicable only if this path is a recursive path";
        }
        leaf-list coll-path-id {
          type uint32;
          description
            "List of collapsed Path ids downloaded to hardware";
        }
        leaf-list igp-path-id {
          type uint32;
          description
            "List of underlying igp path ids. Applicable only
             if the path is a a recursive path";
        }
        leaf igp-path-type {
          type uint32;
          description
            "IGP path type pointed by this path.
             Applicable only if this path is a recursive labelled path";
        }
      }
    }
  }

  grouping ipv6-nexthop-info {
    container paths {
      list path {
        key "path-id";
        leaf path-id {
          type uint32;
          description
            "ID of the Path";
        }
        leaf path-type {
          type fib-path-type;
          description
            "Type of the Path";
        }
        leaf nh-type {
          type nexthop-type;
          description
            "Next-hop type";
        }
        leaf next-hop {
          type nexthop-value-type;
          description
            "IP address of the Path";
        }
        leaf-list push-label {
          type oc-mplst:mpls-label;
          description
            "The MPLS label stack imposed when forwarding packets
             to the nexthop  ";
        }
        leaf nh-tunnel-id {
          type uint32;
          description
            "VXLAN Tunnel id for the nexthop";
        }
        leaf nh-tunnel-vni-id {
          type uint32;
          description
            "VXLAN Tunnel vni id for the nexthop";
        }
        leaf rtep-mac {
          type oc-yang:mac-address;
          description
            "Remote tunnel-endpoint MAC address for a vxlan tunnel nexthop";
        }
        leaf interface {
          type string;
          description
            "Name of the interface for the connected nexthop type";
        }
        leaf network-instance {
          type string;
          description
            "Network Instance name";
        }
        leaf num-coll-paths {
          type uint32;
          description
            "Number of collapsed paths downloaded to hardware.
             Applicable only if this path is a recursive path";
        }
        leaf-list coll-path-id {
          type uint32;
          description
            "List of collapsed Path ids downloaded to hardware";
        }
        leaf-list igp-path-id {
          type uint32;
          description
            "List of underlying igp path ids. Applicable only
             if the path is a a recursive path";
        }
        leaf igp-path-type {
          type uint32;
          description
            "IGP path type pointed by this path.
             Applicable only if this path is a recursive labelled path";
        }
      }
    }
  }

  grouping ipv4-adjacency-info {
    container adjacencies {
      list adjacency {
        key "ip-address";
        leaf ip-address {
          type inet:ip-address-no-zone;
          description
            "Layer 3 ip address";
        }
        leaf mac-address {
          type oc-yang:mac-address;
          description
            "Layer 2 address";
        }
        leaf l2ifindex {
          type uint64;
          description
            "Layer 2 ifindex";
        }
      }
    }
  }

  grouping ipv6-adjacency-info {
    container adjacencies {
      list adjacency {
        key "ip-address";
        leaf ip-address {
          type inet:ip-address-no-zone;
          description
            "Layer 3 ip address";
        }
        leaf mac-address {
          type oc-yang:mac-address;
          description
            "Layer 2 address";
        }
        leaf l2ifindex {
          type uint64;
          description
            "Layer 2 ifindex";
        }
      }
    }
  }

  grouping ipv4-nht-info {
    container nhts {
      list nht {
        key "ip-address";
        leaf ip-address {
          type inet:ip-address-no-zone;
          description
            "Layer 3 ip address";
        }
        leaf path-id {
          type uint32;
          description
            "The Path id corresponding to the tracked ip and interface ";
        }
      }
    }
  }

  grouping ipv6-nht-info {
    container nhts {
      list nht {
        key "ip-address";
        leaf ip-address {
          type inet:ip-address-no-zone;
          description
            "Layer 3 ip address";
        }
        leaf path-id {
          type uint32;
          description
            "The Path id corresponding to the tracked ip and interface ";
        }
      }
    }
  }

  grouping ipv4-nexthops {
    container ipv4-nexthops {
      config false;
      list nexthop {
        description
          "List of Nexthops in the fib table";
        key "index";
        leaf index {
          type uint32;
          description
            "Id of the nexthop (NHID)";
        }
        leaf eos0-nexthop-index {
          type uint32;
          description
            "Id of the eos0 nexthop (NHID)";
        }
        leaf source-nexthop-index {
          type uint32;
          description
            "Id of the source nexthop (NHID)";
        }
        uses ipv4-nexthop-info;
      }
    }
  }

  grouping ipv6-nexthops {
    container ipv6-nexthops {
      config false;
      list nexthop {
        description
          "List of Nexthops in the fib table";
        key "index";
        leaf index {
          type uint32;
          description
            "Id of the nexthop (NHID)";
        }
        leaf eos0-nexthop-index {
          type uint32;
          description
            "Id of the eos0 nexthop (NHID)";
        }
        leaf source-nexthop-index {
          type uint32;
          description
            "Id of the source nexthop (NHID)";
        }
        uses ipv6-nexthop-info;
      }
    }
  }

  grouping ipv4-interface-adjacencies {
    container ipv4-interface-adjacencies {
      config false;
      list interface-adjacency {
        description
          "Adjacency information, IP to MAC binding";
        key "if-index";
        leaf if-index {
          type uint64;
          description
            "Interface Index";
        }
        leaf interface {
          type string;
          description
            "Interface Name";
        }
        leaf link-status {
          type string;
          description
            "Interface status";
        }
        leaf network-instance {
          type oc-netinst:network-instance-ref;
          description
            "Reference to network instance that the interface belongs to";
        }
        uses ipv4-adjacency-info;
        uses ipv4-nht-info;
      }
    }
  }

  grouping ipv6-interface-adjacencies {
    container ipv6-interface-adjacencies {
      config false;
      list interface-adjacency {
        description
          "Adjacency information, IP to MAC binding";
        key "if-index";
        leaf if-index {
          type uint64;
          description
            "Interface Index";
        }
        leaf interface {
          type string;
          description
            "Interface Name";
        }
        leaf link-status {
          type string;
          description
            "Interface status";
        }
        leaf network-instance {
          type oc-netinst:network-instance-ref;
          description
            "Reference to network instance that the interface belongs to";
        }
        uses ipv6-adjacency-info;
        uses ipv6-nht-info;
      }
    }
  }

  grouping pub-info {
    leaf nexthop-id {
      type uint32;
    }
    leaf publish-id {
      type uint32;
      description
        "Path/Nexthop ID published to forwarding layer";
    }
  }

  grouping nh-reach-info {
    leaf next-hop-id {
      type uint32;
    }
    leaf publish-type {
      type publish-path-type;
      description
        "Publish ID type";
    }
    leaf publish-id {
      type uint32;
      description
        "Path/Nexthop ID published to forwarding layer";
    }
  }

  grouping prefix-entry-attributes {
    leaf base-flags {
      type base-flags-type;
    }
    leaf flags {
      type prefix-flags-type;
    }
    leaf forwarding-status {
      type uint32;
      description
        "Last reported forwarding status";
    }
    leaf cookie {
      type uint64;
      description
        "Last received opaque cookie for this route";
    }
    leaf qos-class-id {
      type uint32;
      description
        "QoS class id";
    }
    leaf locator-args {
      type inet:ip-prefix;
      description
        "The mobile gateway locator address";
    }
    uses nh-reach-info;
  }

  grouping ipv4-prefix-entries {
    container ipv4-prefix-entries {
      list prefix-entry {
        description
          "List of prefix entries in the fib table";
        key "prefix";
        leaf prefix {
          type inet:ipv4-prefix;
          description
            "The IP prefix corresponding to the route";
        }

        uses prefix-entry-attributes;
      }
    }
  }

  grouping ipv6-prefix-entries {
    container ipv6-prefix-entries {
      list prefix-entry {
        description
          "List of prefix entries in the fib table";
        key "prefix";
        leaf prefix {
          type inet:ipv6-prefix;
          description
            "The IP prefix corresponding to the route";
        }

        uses prefix-entry-attributes;
      }
    }
  }

  grouping rnh-info {
    description
      "Recursive next-hop reachability state";
    leaf rnh-res-state {
      type rnh-state-type;
      description
        "RNH resolution state";
    }
    leaf recur-level{
      type uint32;
      description
        "Recursion level if RNH is resolved";
    }
    leaf next-hop-id {
      type uint32;
      description
        "Nexthop ID corresponding to rnh prefix given by rib";
    }
    leaf num-ip-igp-paths {
      type uint32;
      description
        "Number of underlay IP IGP paths";
    }
    leaf-list ip-igp-path-id {
      type uint32;
      description
        "List of IP IGP path IDs";
    }
    leaf mpls-igp-type {
      type publish-path-type;
      description
        "Underlay  MPLS ID type";
    }
    leaf mpls-igp-id {
      type uint32;
      description
        "Underlay  MPLS ID";
    }
    leaf srv6-igp-type {
      type publish-path-type;
      description
        "Underlay SRV6 ID type";
    }
    leaf srv6-igp-id {
      type uint32;
      description
        "Underlay SRV6 ID";
    }
  }

  grouping ipv4-rnh-entries {
    container ipv4-rnh-entries {
      list rnh-entry {
        description
          "List of rnh entries";
        key "type next-hop";
        leaf type {
          type nexthop-type;
          description
            "The type of RNH";
        }
        leaf next-hop {
          type nexthop-value-type;
          description
            "The IP address corresponding to the rnh";
        }
        uses rnh-info;
      }
    }
  }

  grouping ipv6-rnh-entries {
    container ipv6-rnh-entries {
      list rnh-entry {
        description
          "List of rnh entries";
        key "type next-hop";
        leaf type {
          type nexthop-type;
          description
            "The type of RNH";
        }
        leaf next-hop {
          type nexthop-value-type;
          description
            "The IP address corresponding to the rnh";
        }
        uses rnh-info;
      }
    }
  }

  grouping ipv4-nht-entries {
    container ipv4-nht-entries {
      list nht-entry {
        description
          "List of Nexthop tracking requests in fib table";
        key "ip-address";
        leaf ip-address {
          type inet:ip-address-no-zone;
          description
            "Address of the tracked Nexthop";
        }
        leaf res-route {
          type inet:ip-prefix;
          description
            "The prefix corresponding to the tracked nexthop";
        }
        leaf-list client {
          type string;
          description
            "List of clients tracking nexthop";
        }
      }
    }
  }

  grouping ipv6-nht-entries {
    container ipv6-nht-entries {
      list nht-entry {
        description
          "List of Nexthop tracking requests in fib table";
        key "ip-address";
        leaf ip-address {
          type inet:ip-address-no-zone;
          description
            "Address of the tracked Nexthop";
        }
        leaf res-route {
          type inet:ip-prefix;
          description
            "The prefix corresponding to the tracked nexthop";
        }
        leaf-list client {
          type string;
          description
            "List of clients tracking nexthop";
        }
      }
    }
  }

  grouping ipv4-label-entries {
    container ipv4-label-entries {
      list label-entry {
        description
          "Label entries in the fib table";
        key "local-label";
        leaf local-label {
          type uint32;
          description
            "The FEC Label entry (ILM) associated with the fib table";
        }
        uses pub-info;
      }
    }
  }

  grouping ipv6-label-entries {
    container ipv6-label-entries {
      list label-entry {
        description
          "Label entries in the fib table";
        key "local-label";
        leaf local-label {
          type uint32;
          description
            "The FEC Label entry (ILM) associated with the fib table";
        }
        uses pub-info;
      }
    }
  }

  grouping total-stats {
    container all-stats {
      leaf total-count {
        type yang:counter64;
        description
          "Total number of objects present in the fib table";
      }
      leaf total-creates {
        type yang:counter64;
        description
          "Total number of creates received  for the object";
      }
      leaf total-updates {
        type yang:counter64;
        description
          "Total number of updates received for the object";
      }
      leaf total-deletes {
        type yang:counter64;
        description
          "Total number of deletes received for the object";
      }
      leaf total-drop-suppress {
        type yang:counter64;
      }
      leaf total-duplicate-updates {
        type yang:counter64;
        description
          "Total number of duplicate updates received for the object";
      }
    }
  }

  grouping curr-ids {
    container all-ids {
      leaf id-count {
        type yang:counter32;
        description
          "Total number of container IDs in use";
      }
    }
  }

  grouping txl-stats {
    container txlist-stats {
      leaf retry-count {
        type yang:counter64;
        description
          "Total number of ipc retries";
      }
    }
  }

  grouping publish-stats {
    container publish-stats {
      leaf total-published {
        type yang:counter64;
        description "Current number of objects in use (published to DPAL)";
      }
      leaf high-water-mark {
        type yang:counter64;
        description "High-water mark of objects in use (peak concurrent published)";
      }
      leaf high-water-mark-time {
        type yang:date-and-time;
        description
          "Time when the current high-water mark was recorded";
      }
    }
  }

  grouping restart-stats {
    container all-stats {
      leaf stale-marks {
        type yang:counter64;
        description
          "Total number of objects marked stale";
      }
      leaf stale-refreshes {
        type yang:counter64;
        description
          "Total number of objects refreshed";
      }
      leaf stale-sweeps {
        type yang:counter64;
        description
          "Total number of objects swept";
      }
      leaf last-stale-marks {
        type yang:counter64;
      }
      leaf last-stale-refreshes {
        type yang:counter64;
      }
      leaf last-stale-sweeps {
        type yang:counter64;
      }
    }
  }

  grouping stats {
    description
      "Table specific counters";
    container routes {
      description
        "Number of Routes";
      uses total-stats;
    }
    container rnhs {
      description
        "Number of RNHs";
      uses total-stats;
    }
    container cross-af-rnhs {
      description
        "Number of Cross AF RNHs";
      uses total-stats;
    }
    container labels {
      description
        "Number of Labels";
      uses total-stats;
    }
    container adj-routes {
      description
        "Number of adj Routes";
      uses total-stats;
    }
    container nexthops {
      description
        "Number of Nexthops (nhids)";
      uses total-stats;
    }
    container paths {
      description
        "Number of Paths (path-ctx)";
      uses total-stats;
    }
    container tables {
      description
        "Number of Tables ";
      uses total-stats;
    }
    container ids {
      description
        "Current Number of Containers Ids allocated ";
      uses curr-ids;
    }
    container eos0-nh-ids {
      description
        "Current Number of EOS0_NH Containers Ids allocated ";
      uses curr-ids;
    }
    container txlist {
      description
        "Txlist statistics";
      uses txl-stats;
    }
    container nht-req-stats {
      description
        "NHT request statistics";
      uses total-stats;
    }
    container nht-resp-stats {
      description
        "NHT response statistics";
       uses total-stats;
     }
  }

  grouping rib-restart-stats {
    description
      "RIB restartability Table specific counters";
    container routes {
      description
        "Number of Routes";
      uses restart-stats;
    }
    container rnhs {
      description
        "Number of RNHs";
      uses restart-stats;
    }
    container labels {
      description
        "Number of Labels";
      uses restart-stats;
    }
    container nexthops-recursive {
      description
        "Number of Recursive Nexthops (nhids)";
      uses restart-stats;
    }
    container nexthops-non-recursive {
      description
        "Number of Non-Recursive Nexthops (nhids)";
      uses restart-stats;
    }
  }

  grouping dpal-publish-stats {
    description
      "counters specific to publish stats from FIB.";

    container nexthop {
        description "single nexthop";
        uses publish-stats;
    }
    container nexthop-group {
        description "ecmp nexthop";
        uses publish-stats;
    }
    container protected-nexthop {
        description "protected nexthop";
        uses publish-stats;
    }
  }

  grouping ipv4-stats-entries {
    description
      "grouping for FIB statistics";
    container ipv4-stats-entries {
      config false;
      description
        "container for FIB stats";
      uses stats;
    }
    container ipv4-rib-restart-stats {
      config false;
      description
        "FIB Counters related to RIB restartability ";
      uses rib-restart-stats;
    }
    container ipv4-dpal-publish-stats {
      config false;
      description
        "FIB Counters related to DPAL publish ";
      uses dpal-publish-stats;
    }
  }

  grouping ipv6-stats-entries {
    description
      "grouping for FIB statistics";
    container ipv6-stats-entries {
      config false;
      description
        "container for FIB stats";
      uses stats;
    }
    container ipv6-rib-restart-stats {
      config false;
      description
        "FIB Counters related to RIB restartability ";
      uses rib-restart-stats;
    }
    container ipv6-dpal-publish-stats {
      config false;
      description
        "FIB Counters related to DPAL publish ";
      uses dpal-publish-stats;
    }
  }

  grouping path-ctx-cmn {
    description
      "Path  information";
    leaf path-type {
      type fib-path-type;
      description
        " Indicates Path type ";
    }
    leaf nh-tableid {
      type uint32;
    }
    leaf nh-type {
      type nexthop-type;
      description
        "Type of nexthop";
    }
    leaf next-hop {
      type nexthop-value-type;
      description
        "The nexthop IP address that is to be used for the route";
    }
    leaf ifindex {
      type uint64;
    }
    leaf flags {
      type bits {
        bit ADJ_UNRESOLVED {
          position 0;
        }
        bit RNH_UNRESOLVED {
          position 1;
        }
        bit IMPLICIT_NULL {
          position 2;
        }
        bit MPLS {
          position 3;
        }
        bit MPLS_UNRESOLVED {
          position 4;
        }
        bit SRV6 {
          position 5;
        }
        bit SRV6_UNRESOLVED {
          position 6;
        }
        bit BACKUP {
          position 7;
        }
        bit SAME_GATEWAY {
          position 8;
        }
        bit UNNUMBERED {
          position 9;
        }
      }
      description "Path Flags";
    }
    leaf reference-count {
      type uint32;
      description
        "Indicates number of nexthops using this path";
    }
  }

  grouping ipv4-path-ctx {
    container ipv4-path-ctx {
      config false;
      list path {
        description
          "List of Paths present in fib table";
        key "path-id";
        leaf path-id {
          type uint32;
          description
            "Indicates the ID of the path";
        }
        uses path-ctx-cmn;
      }
    }
  }

  grouping ipv6-path-ctx {
    container ipv6-path-ctx {
      config false;
      list path {
        description
          "List of Paths present in fib table";
        key "path-id";
        leaf path-id {
          type uint32;
          description
            "Indicates the ID of the path";
        }
        uses path-ctx-cmn;
      }
    }
  }

  grouping ids-cmn {
    description
      "Container ID information";
    leaf id-type {
      type string;
      description
        "Specifies if the ID allocated is for path or NH ";
    }
    leaf reference-count {
      type uint32;
      description
        "Refcount for  the ID";
    }
    leaf path-type {
      type fib-path-type;
      description
        "Indicates Path type  if the ID corresponds to a path";
    }
    leaf-list pathid {
      type uint32;
    }
    leaf ip-address {
      type inet:ip-address-no-zone;
      description
        "Specifies the NH address corresponding to the path
         if applicable";
    }
  }

  grouping ipv4-container-ids {
    container ipv4-container-ids {
      config false;
      list container-id {
        description
          "Container ID Information for FIB table";
        key "id";
        leaf id {
          type uint32;
          description
            "Container ID allocated by FIB";
        }
        uses ids-cmn;
      }
    }
  }

  grouping ipv6-container-ids {
    container ipv6-container-ids {
      config false;
      list container-id {
        description
          "Container ID Information for FIB table";
        key "id";
        leaf id {
          type uint32;
          description
            "Container ID allocated by FIB";
        }
        uses ids-cmn;
      }
    }
  }

  grouping ipv4-eos0-nh-container-ids {
    container ipv4-eos0-nh-container-ids {
      config false;
      list container-id {
        description
          "Container ID Information for FIB table";
        key "id";
        leaf id {
          type uint32;
          description
            "Container ID allocated by FIB";
        }
        uses ids-cmn;
      }
    }
  }

  grouping ipv6-eos0-nh-container-ids {
    container ipv6-eos0-nh-container-ids {
      config false;
      list container-id {
        description
          "Container ID Information for FIB table";
        key "id";
        leaf id {
          type uint32;
          description
            "Container ID allocated by FIB";
        }
        uses ids-cmn;
      }
    }
  }

  grouping ipv4-tunnels {
    description
      "Grouping for tunnel entries by lookup keys";
    container tunnels {
      config false;
      list tunnel {
        key "tunnel-id";
        description
          "tunnel-id used for lookup";
        leaf tunnel-id {
          type uint32;
          description
            "tunnel-ID associated with this tunnel";
        }
        leaf ltep-ip-address {
          type inet:ip-address-no-zone;
          description
            "local tunnel-endpoint ip address";
        }
        leaf rtep-ip-address {
          type inet:ip-address-no-zone;
          description
            "remote tunnel-endpoint ip address";
        }
        leaf tunnel-table-id {
          type uint32;
          description
            "underlay table-id for this tunnel";
        }
        leaf l4-src-port {
          type uint16;
          description
            "UDP source port for this tunnel";
        }
        leaf l4-dst-port {
          type uint16;
          description
            "UDP destination port for this tunnel";
        }
        leaf tunnel-encap {
          type enumeration {
            enum "VXLAN" {
              description
                "VXLAN tunnel encapsulation";
            }
            enum "LI" {
              description
                "Lawful Intercept tunnel encapsulation";
            }
          }
          description
            "tunnel encapsulation";
        }
        leaf session-id {
          type uint32;
          description
            "Lawful Intercept tunnel jmirror Session ID";
        }
        leaf intercept-id {
          type uint32;
          description
            "Lawful Intercept tunnel jmirror Intercept ID";
        }
        leaf jmirror-header {
          type boolean;
          description
            "Lawful Intercept tunnel jmirror header status";
        }
        uses pub-info;
      }
    }
  }

  grouping fib-top {
    description
      "Top level grouping for fib control plane routes";
    container fib {
      config false;

      container network-instances {
        list network-instance {
          key "name";
          description
            "The L3 forwarding instances that are configured on the local system";

          leaf name {
            type oc-netinst:network-instance-ref;
            description
              "A unique name identifying the network-instance";
          }

          container address-families {
            list address-family {
              key "address-family";
              description
                "The forwarding table associated with an address family.";

              leaf address-family {
                type identityref {
                  base oc-types:ADDRESS_FAMILY;
                }
                mandatory true;
              }
              uses ipv4-prefix-entries {
                when "address-family = 'oc-types:IPV4'";
              }
              uses ipv4-rnh-entries {
                when "address-family = 'oc-types:IPV4'";
              }
              uses ipv4-nht-entries {
                when "address-family = 'oc-types:IPV4'";
              }
              uses ipv4-nexthops {
                when "address-family = 'oc-types:IPV4'";
              }
              uses ipv4-label-entries {
                when "address-family = 'oc-types:IPV4'";
              }
              uses ipv4-interface-adjacencies {
                when "address-family = 'oc-types:IPV4'";
              }
              uses ipv4-path-ctx {
                when "address-family = 'oc-types:IPV4'";
              }
              uses ipv4-container-ids {
                when "address-family = 'oc-types:IPV4'";
              }
              uses ipv4-eos0-nh-container-ids {
                when "address-family = 'oc-types:IPV4'";
              }
              uses ipv4-tunnels {
                when "address-family = 'oc-types:IPV4'";
              }
              uses ipv4-stats-entries {
                when "address-family = 'oc-types:IPV4'";
              }
              uses ipv6-prefix-entries {
                when "address-family = 'oc-types:IPV6'";
              }
              uses ipv6-rnh-entries {
                when "address-family = 'oc-types:IPV6'";
              }
              uses ipv6-nht-entries {
                when "address-family = 'oc-types:IPV6'";
              }
              uses ipv6-nexthops {
                when "address-family = 'oc-types:IPV6'";
              }
              uses ipv6-label-entries {
                when "address-family = 'oc-types:IPV6'";
              }
              uses ipv6-interface-adjacencies {
                when "address-family = 'oc-types:IPV6'";
              }
              uses ipv6-path-ctx {
                when "address-family = 'oc-types:IPV6'";
              }
              uses ipv6-container-ids {
                when "address-family = 'oc-types:IPV6'";
              }
              uses ipv6-eos0-nh-container-ids {
                when "address-family = 'oc-types:IPV6'";
              }
              uses ipv6-stats-entries {
                when "address-family = 'oc-types:IPV6'";
              }
            }
          }
        }
      }
    }
  }

  augment "/arc-runtime:runtime-instances" +
          "/arc-runtime:runtime-instance" {
    uses fib-top;
  }
}
