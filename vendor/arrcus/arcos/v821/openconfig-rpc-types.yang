module openconfig-rpc-types {

  yang-version "1";

  // namespace
  namespace "http://openconfig.net/yang/rpc-types";

  prefix "oc-rpc-types";

  import openconfig-extensions { prefix oc-ext; }


  // meta
  organization "OpenConfig working group";

  contact
    "OpenConfig working group
    www.openconfig.net";

  description
    "This module defines type and identities used by the OpenConfig
    reference RPC API specification.";

  oc-ext:openconfig-version "0.2.0";

  revision "2016-04-05" {
    description
      "OpenConfig public release";
    reference "0.2.0";
  }



  // identity statements

  identity OPENCONFIG_RPC_RESPONSE_TYPES {
    description
      "Base identity for RPC response codes.

      The derived identities are examples of possible messages or
      error conditions.  Note that some RPC implementations may use
      their own canonical error codes -- in those cases these message
      types may be used to provide additional information.";
  }

  identity DATA_ENCODING_METHOD {
    description
      "Base identity for supported encoding for configuration and
      operational state data";
  }

  identity ENC_XML {
    base DATA_ENCODING_METHOD;
    description
      "XML encoding";
  }

  identity ENC_JSON_IETF {
    base DATA_ENCODING_METHOD;
    description
      "JSON encoded based on IETF draft standard";
    reference
      "draft-ietf-netmod-yang-json";
  }

  identity ENC_PROTO3 {
    base DATA_ENCODING_METHOD;
    description
      "Protocol buffers v3";
    reference
      "https://developers.google.com/protocol-buffers/docs/overview";
  }

  identity STREAM_PROTOCOL {
    description "Base identity for a telemetry stream protocol";
  }

  identity STREAM_SSH {
    base "STREAM_PROTOCOL";
    description
      "Telemetry stream is carried over a SSH connection";
  }

  identity STREAM_GRPC {
    base "STREAM_PROTOCOL";
    description
      "Telemetry stream is carried over via the gRPC framework";
  }

  identity STREAM_JSON_RPC {
    base "STREAM_PROTOCOL";
      description
        "Telemetry stream is carried via the JSON-RPC framework";
  }

  identity STREAM_THRIFT_RPC {
    base "STREAM_PROTOCOL";
      description
        "Telemetry stream is carried via the Apache Thrift framework";
  }

  identity STREAM_WEBSOCKET_RPC {
    base "STREAM_PROTOCOL";
      description
        "Telemetry stream is carried by the WebSocket framework";
  }

  identity GET_MODEL_TYPE {
    description
      "Base type to describe the type of information returned in a
      get-models RPC";
  }

  identity MODULE {
    base GET_MODEL_TYPE;
    description
      "Metadata describes a single YANG module";
  }

  identity BUNDLE {
    base GET_MODEL_TYPE;
    description
      "Metatdata describes a YANG model bundle, typically a
      versioned collection of YANG modules.";
  }

  identity AUGMENTATION {
    base GET_MODEL_TYPE;
    description
      "Metadata describes a YANG augmentation module";
  }

  identity DEVIATION {
    base GET_MODEL_TYPE;
    description
      "Metadata describes a YANG deviation module";
  }

  identity MODEL_REQUEST_TYPE {
    description
      "Base type to indicate what type of response is desired by
      the client for the get-models RPC.";
  }

  identity SUMMARY {
    base MODEL_REQUEST_TYPE;
    description
      "Indicates the get-models RPC should return only summary,
      i.e., metadata information about the supported models.";
  }

  identity DETAIL {
    base MODEL_REQUEST_TYPE;
    description
      "Indicates the get-models RPC should return metadata as well
      as the module code (YANG code) for the supported models.";
  }


  identity SET_CONFIG_COMMANDS {
    description
      "Base identity for subcommands for the set RPC.";
  }

  identity UPDATE_CONFIG {
    base SET_CONFIG_COMMANDS;
    description
      "Updates the configuration of the target device at the
      specified path(s). Data in the request is added to the current
      device configuration (this is referred to as 'merge' in
      NETCONF, for example).  If the specified data exists, it is
      overwritten by the contents of the message.  If the path
      specifies a list node, the configuration data is considered an
      addition (append) to the list with the new element.";
  }

  identity REPLACE_CONFIG {
    base SET_CONFIG_COMMANDS;
    description
      "Replaces the configuration at the target device at the
      specified path(s). If the specified data exists, it is
      overwritten by the contents of the message.  Configuration data
      in the model subtree that is not specified is deleted by the
      server.";
  }

  identity DELETE_CONFIG {
    base SET_CONFIG_COMMANDS;
    description
      "Deletes the configuration at the target device. If the
      specified data does not exist at the specified path, the
      device should return an error indicating and invalid path.";
  }

  identity GET_TYPE {
    description
      "Base identity for subcommands for the get RPC";
  }

  identity GET_ALL {
    base GET_TYPE;
    description
      "Return all data at the specified path (config: true and
      config: false data nodes)";
  }

  identity GET_CONFIG {
    base GET_TYPE;
    description
      "Return configuration data at the specified path (config:
      true nodes)";
  }

  identity GET_STATE {
    base GET_TYPE;
    description
      "Return operational state data at the specified path (config:
      false nodes)";
  }

  identity GET_OPERATIONAL {
    base GET_TYPE;
    description
      "Return operational state data at the specified path excluding
      the applied configuration  (i.e., config: false nodes
      excluding the nodes representing configuration data)";
  }

  // Example messages in rpc responses

  identity OK {
    base OPENCONFIG_RPC_RESPONSE_TYPES;
    description
      "Indicates successful completion of the RPC command";
  }

  identity NOK {
    base OPENCONFIG_RPC_RESPONSE_TYPES;
    description
      "Indicates unsuccessful RPC operation.  This is a generic
      NACK from the target device; should be used only if another
      more descriptive response code is not available.  The
      message string should provide enough information to the
      operator to understand why the command failed.";
  }

  identity UNSUPPORTED_PATH {
    base OPENCONFIG_RPC_RESPONSE_TYPES;
    description
      "The path specified in the RPC request is not known or not
      supported on the target.  For subscription requests, this
      response indicates that the requested path is not supported
      for streaming telemetry.";
  }

  identity INVALID_PATH {
    base OPENCONFIG_RPC_RESPONSE_TYPES;
    description
      "The specified path in the RPC request is not found, was
      unrecognized, or could not be parsed.";
  }

  identity INVALID_CONFIGURATION {
    base OPENCONFIG_RPC_RESPONSE_TYPES;
    description
      "The specified configuration value or corresponding command
      are invalid";
  }

  identity UNSUPPORTED_INTERVAL {
    base OPENCONFIG_RPC_RESPONSE_TYPES;
    description
      "The requested sampling interval for telemetry is not supported
      for the corresponding path.";
  }

  identity INVALID_SUBSCRIPTION_ID {
    base OPENCONFIG_RPC_RESPONSE_TYPES;
    description
      "The supplied subscription ID was invalid, or could not be
      matched to a subscription ID on the target.";
  }

  identity UNSUPPORTED_ENCODING {
    base OPENCONFIG_RPC_RESPONSE_TYPES;
    description
      "The requested data encoding is not supported by the target.";
  }

  // typedef statements

  typedef openconfig-path {
    type string;
    description
      "Path specification for elements of OpenConfig data models are
      expected to use an XPATH-like syntax.
      Some examples of path specifications include:

        /interfaces/interface[name=Ethernet1/2/3]/state/counters --
        all of the counters on the named interface

        /interfaces/interface[name=*]/state/oper-status --
        operational status for all of the interfaces

        /bgp/neighbors -- contents of neighbor list

        /bgp/neighbors/neighbor[neighbor-address=172.24.3.10] --
        all data for the corresponding BGP neighbor (i.e. the
        entire subtree)

        /interfaces/interface[name=eth0]//state -- all state
        containers for interface eth0

      ";
  }


}
