module arcos-adjmgr {
  yang-version 1.1;
  namespace "http://yang.arrcus.com/arcos/adjmgr";
  prefix arc-adjmgr;

  import ietf-inet-types {
    prefix inet;
  }

  import openconfig-interfaces {
    prefix oc-if;
  }

  import openconfig-types {
    prefix oc-types;
  }

  import ietf-yang-types {
    prefix yang;
  }

  organization
    "Arrcus, Inc.";

  contact
    "Arrcus, Inc.
     2077 Gateway Place
     Suite 400
     San Jose, CA 95110

     E-mail: yang-support@arrcus.com";

  description
    "This module contains definitions for the
     native ArcOS ADJMGR domain.

     Copyright (c) 2024 by Arrcus, Inc.
     All rights reserved.";

  revision 2024-11-04 {
    description
      "Initial revision to support counters";
  }

  identity ADJMGR_PRODUCER_CONSUMER_TYPE {
    description
      "Base type for entities which can either install neighbors into or
      receive neighbors from ADJMGR";
  }

  identity NONE {
    base ADJMGR_PRODUCER_CONSUMER_TYPE;
    description "No Protocol";
  }

  identity STATIC {
    base ADJMGR_PRODUCER_CONSUMER_TYPE;
    description "Neighbor from Local STATIC producer";
  }

  identity BGP {
    base ADJMGR_PRODUCER_CONSUMER_TYPE;
    description "Neighbor from BGP producer";
  }

  identity KERNEL {
    base ADJMGR_PRODUCER_CONSUMER_TYPE;
    description "Neighbor from KERNEL producer/consumer";
  }

  identity L2RIB {
    base ADJMGR_PRODUCER_CONSUMER_TYPE;
    description "L2RIB consumer";
  }

  grouping producer-stats {
    description
      "ADJMGR producer stats counters";

    leaf neighbor-v4-add {
      type yang:counter64;
      description
        "Neighbor (v4) add counter";
    }

    leaf neighbor-v4-upd {
      type yang:counter64;
      description
        "Neighbor (v4) update counter";
    }

    leaf neighbor-v4-del {
      type yang:counter64;
      description
        "Neighbor (v4) del counter";
    }

    leaf neighbor-v6-add{
      type yang:counter64;
      description
        "Neighbor (v6) add counter";
    }

    leaf neighbor-v6-upd {
      type yang:counter64;
      description
        "Neighbor (v4) update counter";
    }

    leaf neighbor-v6-del {
      type yang:counter64;
      description
        "Neighbor (v6) del counter";
    }

    leaf addr-err {
      type yang:counter64;
      description
        "Address event error counter";
    }

    leaf addr-v4-add {
      type yang:counter64;
      description
        "Address (v4) event add counter";
    }

    leaf  addr-v4-upd {
      type yang:counter64;
      description
        "Address (v4) event update counter";
    }

    leaf addr-v4-del {
      type yang:counter64;
      description
        "Address (v4) event delete counter";
    }

    leaf addr-v4-err {
      type yang:counter64;
      description
        "Address (v6) event error counter";
    }

    leaf addr-v6-add {
      type yang:counter64;
      description
        "Address (v6) event add counter";
    }

    leaf addr-v6-upd {
      type yang:counter64;
      description
        "Address (v6) event update counter";
    }

    leaf addr-v6-del {
      type yang:counter64;
      description
        "Address (v6) event delete counter";
    }

    leaf addr-v6-err {
      type yang:counter64;
      description
        "Address (v6) event error counter";
    }

    leaf link-upd {
      type yang:counter64;
      description
        "Link event update counter";
    }

    leaf link-upd-flush {
      type yang:counter64;
      description
        "Link event flush neighbor counter";
    }

    leaf link-add {
      type yang:counter64;
      description
        "Link event add counter";
    }

    leaf link-del {
      type yang:counter64;
      description
        "Link event del counter";
    }

    leaf link-add-err {
      type yang:counter64;
      description
        "Link event add error counter";
    }

    leaf flush-v4-all-neighbor {
      type yang:counter64;
      description
        "Flush neighbor (v4 all) counter";
    }

    leaf flush-v4-per-intf-neighbor {
      type yang:counter64;
      description
        "Flush neighbor (v4 per intf) counter";
    }

    leaf flush-v4-neighbor {
      type yang:counter64;
      description
        "Flush neighbor (v4 single) counter";
    }

    leaf flush-v6-all-neighbor {
      type yang:counter64;
      description
        "Flush neighbor (v6 all) counter";
    }

    leaf flush-v6-per-intf-neighbor {
      type yang:counter64;
      description
        "Flush neighbor (v6 per intf) counter";
    }

    leaf flush-v6-neighbor {
      type yang:counter64;
      description
        "Flush neighbor (v6 single) counter";
    }
  }

  grouping kernel-stats {
    description
      "ADJMGR KERNEL consumer stats counters";

    leaf neighbor-v4-upd {
      type yang:counter64;
      description
        "Neighbor (v4) add publish counter";
    }
    leaf neighbor-v4-del {
      type yang:counter64;
      description
        "Neighbor (v4) del publish counter";
    }
    leaf neighbor-v4-upd-err {
      type yang:counter64;
      description
        "Neighbor (v4) error update publish counter";
    }
    leaf neighbor-v4-del-err {
      type yang:counter64;
      description
        "Neighbor (v4) error del publish counter";
    }
    leaf neighbor-v6-upd {
      type yang:counter64;
      description
        "Neighbor (v6) update publish counter";
    }
    leaf neighbor-v6-del {
      type yang:counter64;
      description
        "Neighbor (v6) del publish counter";
    }
    leaf neighbor-v6-upd-err {
      type yang:counter64;
      description
        "Neighbor (v6) err publish counter";
    }
    leaf neighbor-v6-del-err {
      type yang:counter64;
      description
        "Neighbor (v6) add publish counter";
    }
  }

  grouping l2rib-stats {
    description
      "ADJMGR L2RIB consumer stats counters";

    leaf neighbor-v4-pub-add {
      type yang:counter64;
      description
        "Neighbor (v4) add publish counter";
    }
    leaf neighbor-v4-pub-del {
      type yang:counter64;
      description
        "Neighbor (v4) del publish counter";
    }
    leaf neighbor-v4-pub-err {
      type yang:counter64;
      description
        "Neighbor (v4) err publish counter";
    }
    leaf neighbor-v6-pub-add {
      type yang:counter64;
      description
        "Neighbor (v6) add publish counter";
    }
    leaf neighbor-v6-pub-del {
      type yang:counter64;
      description
        "Neighbor (v6) del publish counter";
    }
    leaf neighbor-v6-pub-err {
      type yang:counter64;
      description
        "Neighbor (v6) err publish counter";
    }
  }

  grouping consumer-stats {
    uses l2rib-stats;
    uses kernel-stats;
  }

  grouping statistics {
    description
      "grouping for ADJMGR statistics";

    container statistics {
      description
        "ADJMGR statistics";

      list producers {
        key "name";
        description
          "ADJMGR producer application";

        leaf name {
          type identityref {
            base "ADJMGR_PRODUCER_CONSUMER_TYPE";
          }
          description
            "Name of ADJMGR producer";
        }
        uses producer-stats;
      }

      list consumers {
        key "name";
        description
          "ADJMGR consumer application";

        leaf name {
          type identityref {
            base "ADJMGR_PRODUCER_CONSUMER_TYPE";
          }
          description
            "Name of ADJMGR consumer";
        }
        uses consumer-stats;
      }
    }
  }

  grouping adjmgr-top {
    description
      "Top-level grouping for ADJMGR";

    container adjmgr {
      description
        "Global level state for the Layer 2 Routing Information Base";

      config false;
      uses statistics;
    }
  }
  uses adjmgr-top;

}
