module arcos-ztp {
  yang-version "1.1";
  namespace "http://yang.arrcus.com/arcos/ztp";
  prefix "arc-ztp";

  revision "2020-04-25" {
    description
      "Initial version";
  }

  grouping ztp-config {
    leaf enabled {
      type boolean;
      default true;
      description
        "Enables/Disables ZTP.";
    }
  }

  grouping ztp-top {
    description
      "ZTP Configuration";

    container ztp {
      container config {
        description
          "ZTP Configuration";

        uses ztp-config;
      }
    }
  }

  uses ztp-top;

}
