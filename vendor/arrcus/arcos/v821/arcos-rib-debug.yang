module arcos-rib-debug {
  yang-version 1.1;
  namespace "http://yang.arrcus.com/arcos/rib/debug";
  prefix arc-rib-dbg;

  import arcos-debug {
    prefix arc-dbg;
  }

  organization
    "Arrcus, Inc.";

  contact
    "Arrcus, Inc.
     Customer Service
     Postal: 2077 Gateway Place
     San Jose, CA 95110
     Tel: +1 1XXX XXX-XXXX
     E-mail: xxx@arrcus.com";

  description
    "This module defines debug statements for Arrcus
     implemention of RIB.";

  revision 2023-11-09 {
    description "Adding RIB debugs under debug command";
  }

  typedef rib-debug-state {
    type enumeration { 
      enum on {
        description
          "Enable debug";
      }
      enum off {
        description
          "Disable debug";
      }
    }
  }

  typedef rib-debug-type {
    type enumeration { 
      enum route {
        description
          "Control route/prefix debugs";
      }
      enum path {
        description
          "Control path debugs";
      }
      enum rnh {
        description
          "Control rnh core debugs";
      }
      enum err {
        description
          "Control error debugs";
      }
      enum ds {
        description
          "Control DS API debugs";
      }
      enum rnh-ds {
        description
          "Control DS RNH API debugs";
      }
      enum mpsc {
        description
          "Control MPSC interaction debugs";
      }
      enum ptrack-event {
        description
          "Control prefix tracker event debugs";
      }
      enum ptrack-client {
        description
          "Control prefix tracker client debugs";
      }
      enum client {
        description
          "Control client event debugs";
      }
      enum oper {
        description
          "Control Oper command debugs";
      }
      enum ilm {
        description
          "Control ILM debugs";
      }
      enum all {
        description
          "Control All debugs";
      }
    }
  }

  container rib-debug {
    description
      "RIB debug control";
    action ipv4 {
      input {
        leaf debug {
          type rib-debug-type;
          mandatory true;
          description
            "Debug to be controlled";
        }
        leaf op {
          type rib-debug-state;
          mandatory true;
          description
            "turn on/off operation";
        }
      }
      output {
        leaf result {
          type string;
          description
            "The status of operation";
        }
      }
    }
    action ipv6 {
      input {
        leaf debug {
        type rib-debug-type;
        mandatory true;
          description
          "Debug to be controlled";
        }
        leaf op {
          type rib-debug-state;
          mandatory true;
          description
            "turn on/off debug";
        }
      }
      output {
        leaf result {
          type string;
          description
            "The status of operation";
        }
      }
    }
  }

  grouping rib-ipv6-debug-top {
    container rib-ipv6 {
      config false;
      uses arc-dbg:debug-component-top;
      description
        "IPv6 RIB debug";
    }
  }

  grouping rib-ipv4-debug-top {
    container rib-ipv4 {
      config false;
      uses arc-dbg:debug-component-top;
      description
        "IPv4 RIB debug";
    }
  }

  augment "/arc-dbg:debug/arc-dbg:debug-attach-points" {
    uses rib-ipv4-debug-top {
      when "arc-dbg:component = 'rib-ipv4'" {
        description
          "Include RIB V4 debug information under global debug attach-point list";
      }
    }
    uses rib-ipv6-debug-top {
      when "arc-dbg:component = 'rib-ipv6'" {
        description
          "Include RIB V6 debug information under global debug attach-point list";
      }
    }
    description
      "RIB debug";
  }
}
