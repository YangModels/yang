module arcos-openconfig-alarms-deviations {
  yang-version 1.1;
  namespace "http://yang.arrcus.com/arcos/openconfig/alarms/deviations";
  prefix arc-oc-alarms-dev;

  import openconfig-alarms {
    prefix oc-alarms;
  }

  import openconfig-platform {
    prefix oc-platform;
  }

  organization
    "Arrcus, Inc.";

  contact
    "Arrcus, Inc.
     2077 Gateway Place
     Suite 400
     San Jose, CA 95110

     E-mail: yang-support@arrcus.com";

  description
    "This module defines deviations to the openconfig alarms model.

     Copyright (c) 2022 by Arrcus, Inc.
     All rights reserved.";

  revision 2022-11-08 {
    description
    "Initial revision";
  }

  deviation "/oc-platform:components/oc-platform:component/" +
            "oc-platform:state/oc-alarms:equipment-failure" {
    deviate not-supported;
    description "Not supported in this release";
  }

  deviation "/oc-platform:components/oc-platform:component/" +
            "oc-platform:state/oc-alarms:equipment-mismatch" {
    deviate not-supported;
    description "Not supported in this release";
  }
}
