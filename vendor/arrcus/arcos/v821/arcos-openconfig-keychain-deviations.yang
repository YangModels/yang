module arcos-openconfig-keychain-deviations {
  yang-version 1.1;
  namespace "http://yang.arrcus.com/arcos/openconfig/keychain/deviations";
  prefix arc-oc-kc-dev;

  import openconfig-keychain {
    prefix oc-kc;
  }

  import openconfig-keychain-types {
    prefix oc-kc-types;
  }

  import ietf-yang-types {
    prefix yang;
  }

  import arcos-system-types {
    prefix arc-sys-types;
  }

  organization
    "Arrcus, Inc.";

  contact
    "Arrcus, Inc.
     2077 Gateway Place
     Suite 400
     San Jose, CA 95110
     E-mail: yang-support@arrcus.com";

  description
    "This module defines deviation statements for Arrcus
     implemention of the openconfig keychain module.
     Copyright (c) 2022-2023 by Arrcus, Inc.
     All rights reserved.";

  revision 2022-12-15 {
    description
      "Initial Revision";
  }

  deviation "/oc-kc:keychains/oc-kc:keychain" +
            "/oc-kc:keys/oc-kc:key/oc-kc:send-lifetime/oc-kc:config" +
            "/oc-kc:start-time" {
    deviate replace {
      type yang:date-and-time;
    }
  }

  deviation "/oc-kc:keychains/oc-kc:keychain" +
            "/oc-kc:keys/oc-kc:key/oc-kc:send-lifetime/oc-kc:state" +
            "/oc-kc:start-time" {
    deviate replace {
      type yang:date-and-time;
    }
  }

  deviation "/oc-kc:keychains/oc-kc:keychain" +
            "/oc-kc:keys/oc-kc:key/oc-kc:send-lifetime/oc-kc:config" +
            "/oc-kc:end-time" {
    deviate replace {
      type yang:date-and-time;
    }
  }

  deviation "/oc-kc:keychains/oc-kc:keychain" +
            "/oc-kc:keys/oc-kc:key/oc-kc:send-lifetime/oc-kc:state" +
            "/oc-kc:end-time" {
    deviate replace {
      type yang:date-and-time;
    }
  }

  deviation "/oc-kc:keychains/oc-kc:keychain" +
            "/oc-kc:keys/oc-kc:key/oc-kc:receive-lifetime/oc-kc:config" +
            "/oc-kc:start-time" {
    deviate replace {
      type yang:date-and-time;
    }
  }

  deviation "/oc-kc:keychains/oc-kc:keychain" +
            "/oc-kc:keys/oc-kc:key/oc-kc:receive-lifetime/oc-kc:state" +
            "/oc-kc:start-time" {
    deviate replace {
      type yang:date-and-time;
    }
  }

  deviation "/oc-kc:keychains/oc-kc:keychain" +
            "/oc-kc:keys/oc-kc:key/oc-kc:receive-lifetime/oc-kc:config" +
            "/oc-kc:end-time" {
    deviate replace {
      type yang:date-and-time;
    }
  }

  deviation "/oc-kc:keychains/oc-kc:keychain" +
            "/oc-kc:keys/oc-kc:key/oc-kc:receive-lifetime/oc-kc:state" +
            "/oc-kc:end-time" {
    deviate replace {
      type yang:date-and-time;
    }
  }

  deviation "/oc-kc:keychains/oc-kc:keychain" +
            "/oc-kc:keys/oc-kc:key/oc-kc:config/oc-kc:crypto-algorithm" {
    deviate add {
      must "current() != 'oc-kc-types:MD5' and " +
           "current() != 'oc-kc-types:CRYPTO_NONE' and " +
           "current() != 'oc-kc-types:SHA_1' and " +
           "current() != 'oc-kc-types:HMAC_SHA_1_12' and " +
           "current() != 'oc-kc-types:HMAC_SHA_1_20' and " +
           "current() != 'oc-kc-types:HMAC_SHA_1_96' and " +
           "current() != 'oc-kc-types:AES_28_CMAC_96'" {
        error-message "crypto-algorithm is not supported";
      }
    }
  }

  deviation "/oc-kc:keychains/oc-kc:keychain" +
            "/oc-kc:keys/oc-kc:key/oc-kc:config/oc-kc:secret-key" {
    deviate replace {
      type arc-sys-types:encrypted-string;
    }
  }

  deviation "/oc-kc:keychains/oc-kc:keychain" +
            "/oc-kc:keys/oc-kc:key/oc-kc:state/oc-kc:secret-key" {
    deviate replace {
      type arc-sys-types:encrypted-string;
    }
  }

  deviation "/oc-kc:keychains/oc-kc:keychain" +
            "/oc-kc:config/oc-kc:tolerance" {
    deviate replace {
      type uint32;
    }
  }

  deviation "/oc-kc:keychains/oc-kc:keychain" +
            "/oc-kc:keys/oc-kc:key/oc-kc:receive-lifetime" {
    deviate not-supported;
  }

  deviation "/oc-kc:keychains/oc-kc:keychain" +
            "/oc-kc:keys/oc-kc:key" +
            "/oc-kc:send-lifetime/oc-kc:config/oc-kc:send-and-receive" {
    deviate not-supported;
  }
}
