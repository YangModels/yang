module arcos-qos-classifier {
  yang-version 1.1;
  namespace "http://yang.arrcus.com/arcos/qos/classifier";
  prefix arc-qos-cfr;

  import arcos-classifier {
    prefix arc-cfr;
  }
  import arcos-classifier-filter {
    prefix arc-cfr-fltr;
  }
  import arcos-classifier-filter-types {
    prefix arc-cfr-fltr-types;
  }
  import arcos-qos {
    prefix arc-qos;
  }
  import arcos-platform {
    prefix arc-platform;
  }
  import openconfig-system {
    prefix oc-sys;
  }
  import arcos-openconfig-system-augments {
    prefix arc-oc-sys-aug;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for qos classifier definitions.
     Expanded from the generic classifier data model (classifier.yang)
     
     Copyright (c) 2016-2023 by Arrcus, Inc.
     All rights reserved.";

  revision 2024-11-07 {
    description "Modified the 'when' clause to enable CLI configuration on VM";
  }
  revision 2023-05-05 {
    description
      "Enabled ANY filter type to be used as a classifier filter for DNX only";
  }

  augment "/arc-qos:qos/classifiers/classifier/filters/filter/config" {
    uses arc-cfr-fltr:acl-top {
      when "(../type = 'arc-cfr-fltr-types:ACL')";
    }
  }

  augment "/arc-qos:qos/classifiers/classifier/filters/filter/state" {
    uses arc-cfr-fltr:acl-top {
      when "(../type = 'arc-cfr-fltr-types:ACL')";
    }
  }


  augment "/arc-qos:qos/classifiers/classifier/filters/filter/config" {
    uses arc-cfr-fltr:dscp-top {
      when "../type = 'arc-cfr-fltr-types:DSCP'";
    }
  }

  augment "/arc-qos:qos/classifiers/classifier/filters/filter/state" {
    uses arc-cfr-fltr:dscp-top {
      when "../type = 'arc-cfr-fltr-types:DSCP'";
    }
  }

  augment "/arc-qos:qos/classifiers/classifier/filters/filter/config" {
    uses arc-cfr-fltr:mpls-tc-top {
      when "../type = 'arc-cfr-fltr-types:MPLS_TC'";
    }
  }

  augment "/arc-qos:qos/classifiers/classifier/filters/filter/state" {
    uses arc-cfr-fltr:mpls-tc-top {
      when "../type = 'arc-cfr-fltr-types:MPLS_TC'";
    }
  }

  augment "/arc-qos:qos/classifiers/classifier/filters/filter/config" {
    uses arc-cfr-fltr:qos-class-top {
      when "../type = 'arc-cfr-fltr-types:SRC_QOS_CLASS' or " +  
           "../type = 'arc-cfr-fltr-types:DST_QOS_CLASS'"; 
    } 
  }

  augment "/arc-qos:qos/classifiers/classifier/filters/filter/state" {
    uses arc-cfr-fltr:qos-class-top {
      when "../type = 'arc-cfr-fltr-types:SRC_QOS_CLASS' or " +  
           "../type = 'arc-cfr-fltr-types:DST_QOS_CLASS'";
    }
  }

  augment "/arc-qos:qos/classifiers/classifier/filters/filter/config" {
    uses arc-cfr-fltr:local-tc-top {
      when "../type = 'arc-cfr-fltr-types:LOCAL_TC'";
      refine "local-tc-value" {
        max-elements 1;
      }
    }
  }

  augment "/arc-qos:qos/classifiers/classifier/filters/filter/state" {
    uses arc-cfr-fltr:local-tc-top {
      when "../type = 'arc-cfr-fltr-types:LOCAL_TC'";
    }
  }

  grouping qos-classifier-top {
    description
      "Top-level grouping for QoS specific classifier database";
    uses arc-cfr:classifiers-top {
      refine "classifiers/classifier/filters/filter" {
        min-elements 1;
        max-elements 1;
      }
      refine "classifiers/classifier/filters/filter/type" {
        must "current() = 'arc-cfr-fltr-types:LOCAL_TC' or "
           + "((current() = 'arc-cfr-fltr-types:ANY') and "
           + " ((/arc-platform:platform/arc-platform:family = 'arc-platform:BROADCOM_DNX') or "
           + " (/arc-platform:platform/arc-platform:deployment-type = 'arc-platform:DISTRIBUTED') or "
           + " (/oc-sys:system/arc-oc-sys-aug:cli/arc-oc-sys-aug:config/arc-oc-sys-aug:unhide-unsupported-cli = 'true'))) or"
           + "((current() = 'arc-cfr-fltr-types:MPLS_TC' or "
           + "  current() = 'arc-cfr-fltr-types:DSCP' or "
           + "  current() = 'arc-cfr-fltr-types:SRC_QOS_CLASS' or "
           + "  current() = 'arc-cfr-fltr-types:DST_QOS_CLASS' or "
           + "  current() = 'arc-cfr-fltr-types:ACL') and "
           + " ((/arc-platform:platform/arc-platform:family = 'arc-platform:BROADCOM_DNX') or"
           + "  (/arc-platform:platform/arc-platform:family = 'arc-platform:BROADCOM_XGS') or "
           + "  (/arc-platform:platform/arc-platform:deployment-type = 'arc-platform:DISTRIBUTED') or "
           + "  (/oc-sys:system/arc-oc-sys-aug:cli/arc-oc-sys-aug:config/arc-oc-sys-aug:unhide-unsupported-cli = 'true')))" {
          error-message "filter type not supported for qos";
        }
      }
    }
  }

  augment "/arc-qos:qos" {
    uses qos-classifier-top;
  }
}
