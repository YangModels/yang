module arcos-datapath-rsvd-vlan {
  yang-version 1.1;
  namespace "http://yang.arrcus.com/arcos/datapath/rsvd/vlan";
  prefix arcos-rsvd-vlan;

  import openconfig-vlan-types {
    prefix oc-vlan-types;
  }

  import openconfig-interfaces {
    prefix oc-if;
  }

  organization
    "Arrcus, Inc.";

  contact
    "Arrcus, Inc.
    2077 Gateway Place
    Suite 400
    San Jose, CA 95110
    E-mail: yang-support@arrcus.com";

  description
    "This module defines the dynamically mapped
    vlan to an L3 interface.
    Copyright (c) 2023 by Arrcus, Inc.
    All rights reserved.";

  revision "2023-12-19" {
    description
      "Added the yang module to display the
       reserved Vlan ID mapped to an L3 Interface.";
  }

  grouping rsvd-vlan-top {
    description
      "Grouping for Reserved vlan";

    container sys-rsvd-vlan {
      config false;
      list interfaces {
        key "interface";

        leaf interface {
          type leafref {
            path "/oc-if:interfaces/oc-if:interface/oc-if:config/oc-if:name";
          }
          description
            "Interface Name";
        }

        leaf reserved-vlan {
          type oc-vlan-types:vlan-id;
          description
            "Internal vlan for the given L3 Interface.";
        }
      }
    }
  }
}
