module arcos-openconfig-bgp-types {
  yang-version 1.1;
  namespace "http://yang.arrcus.com/arcos/openconfig/bgp/types";

  prefix arc-oc-bgp-types;

  import openconfig-types {
    prefix oc-types;
  }

  import openconfig-bgp-types {
    prefix oc-bgp-types;
  }

  import openconfig-inet-types {
    prefix oc-inet;
  }

  import ietf-inet-types {
    prefix inet;
  }

  organization
    "Arrcus, Inc.";

  contact
    "Arrcus, Inc.
     2077 Gateway Place
     Suite 400
     San Jose, CA 95110
     E-mail: yang-support@arrcus.com";

  description
    "This module defines augmentation for Arrcus
     implementation of the openconfig BGP types module.";

  revision 2024-02-22 {
    description "Change color flags to be specified as decimal instead of binary";
  }

  revision 2024-01-22 {
    description
      "Add lower-case BGP AFi-SAFI types";
  }

  revision 2023-12-17 {
    description
      "Allow all values for 4 byte ASN extended community values";
  }

  revision 2023-06-02 {
    description "Add MUP architecture identity";
  }

  revision 2022-12-06 {
    description "Added peer-as-range type";
  }

  revision 2022-08-10 {
    description "* Added MUP SAFI support
                 * Added raw extended community";
  }

  revision 2022-07-07 {
    description
      "Add bgp route type - local/internal/external";
  }

  revision 2018-06-14 {
    description
      "Initial Revision
       * Add bgp large community
      ";

    reference
      "RFC 6020: YANG - A Data Modeling Language for the
       Network Configuration Protocol (NETCONF)";
  }

  identity ADD_PATHS_OPTIONS {
    description
      "Base identity for add-paths options";
  }

  identity ALL {
    base ADD_PATHS_OPTIONS;
    description
      "Advertise all paths";
  }

  identity SECOND_BEST {
    base ADD_PATHS_OPTIONS;
    description
      "Advertise second-best path - may be a multipath";
  }

  identity BACKUP {
    base ADD_PATHS_OPTIONS;
    description
      "Advertise backup path - excluding multipaths";
  }

  identity BEST_EXTERNAL {
    base ADD_PATHS_OPTIONS;
    description
      "Advertise best-external path";
  }

  identity MULTIPATHS {
    base ADD_PATHS_OPTIONS;
    description
      "Advertise paths that are selected by multipath selection algorithm";
  }

  identity SRV6_OAM_STATES {
    description
      "Base identity for SRv6 OAM states";
  }

  identity OAM_NOT_REPORTED {
    base SRV6_OAM_STATES;
    description
      "OAM has not reported state, we assume it is good";
  }

  identity OAM_ELIGIBLE {
    base SRV6_OAM_STATES;
    description
      "OAM reported state is ELIGIBLE";
  }

  identity OAM_INELIGIBLE {
    base SRV6_OAM_STATES;
    description
      "OAM reported state is INELIGIBLE";
  }

  identity EXTENDED_NEXTHOP_ENCODING {
    base oc-bgp-types:BGP_CAPABILITY;
    description
      "Extended Next Hop Encoding functionality";
  }

  identity RTFILTER {
    base oc-bgp-types:AFI_SAFI_TYPE;
    description
      "Route Target Filter (AFI,SAFI = 1,132)";
    reference "RFC4684";
  }

  typedef rtfilter-prefix {
    type union {
      type string {
        // (4-octet ASN):(2-octet global value):(4-octet local value)[/length]
        pattern
          '(429496729[0-5]|42949672[0-8][0-9]|4294967[0-1][0-9]{2}'    +
          '|429496[0-6][0-9]{3}|42949[0-5][0-9]{4}|4294[0-8][0-9]{5}|' +
          '429[0-3][0-9]{6}|42[0-1][0-9]{7}||4[0-1][0-9]{8}|'          +
          '[1-3][0-9]{9}|[1-9][0-9]{1,8}|[0-9]):'                      +
          '(6553[0-5]|655[0-2][0-9]|654[0-9]{2}|65[0-4][0-9]{2}'       +
          '|6[0-4][0-9]{3}|[1-5][0-9]{4}|[1-9][0-9]{1,3}|[0-9]):'      +
          '(429496729[0-5]|42949672[0-8][0-9]|4294967[0-1][0-9]{2}'    +
          '|429496[0-6][0-9]{3}|42949[0-5][0-9]{4}|4294[0-8][0-9]{5}|' +
          '429[0-3][0-9]{6}|42[0-1][0-9]{7}||4[0-1][0-9]{8}|'          +
          '[1-3][0-9]{9}|[1-9][0-9]{1,8}|[0-9])(|/(9[0-6]|'            +
          '[1-8][0-9]|[0-9]))';
      }
      type string {
        // (4-octet ASN):(IPv4 address):(2-octet local value)[/length]
        pattern
          '(429496729[0-5]|42949672[0-8][0-9]|4294967[0-1][0-9]{2}'    +
          '|429496[0-6][0-9]{3}|42949[0-5][0-9]{4}|4294[0-8][0-9]{5}|' +
          '429[0-3][0-9]{6}|42[0-1][0-9]{7}||4[0-1][0-9]{8}|'          +
          '[1-3][0-9]{9}|[1-9][0-9]{1,8}|[0-9]):'                      +
          '(([0-9]|[1-9][0-9]|1[0-9][0-9]|2[0-4][0-9]|'                +
          '25[0-5])\.){3}([0-9]|[1-9][0-9]|1[0-9][0-9]|'               +
          '2[0-4][0-9]|25[0-5]):'                                      +
          '(6553[0-5]|655[0-2][0-9]|654[0-9]{2}|65[0-4][0-9]{2}'       +
          '|6[0-4][0-9]{3}|[1-5][0-9]{4}|[1-9][0-9]{1,3}|[0-9])'       +
          '(|/(9[0-6]|[1-8][0-9]|[0-9]))';
      }
      type string {
        // (4-octet ASN):(4-octet global value):(2-octet local value)[/length]
        pattern
          '(429496729[0-5]|42949672[0-8][0-9]|4294967[0-1][0-9]{2}'    +
          '|429496[0-6][0-9]{3}|42949[0-5][0-9]{4}|4294[0-8][0-9]{5}|' +
          '429[0-3][0-9]{6}|42[0-1][0-9]{7}||4[0-1][0-9]{8}|'          +
          '[1-3][0-9]{9}|[1-9][0-9]{1,8}|[0-9]):'                      +
          '(429496729[0-5]|42949672[0-8][0-9]|4294967[0-1][0-9]{2}'    +
          '|429496[0-6][0-9]{3}|42949[0-5][0-9]{4}|4294[0-8][0-9]{5}|' +
          '429[0-3][0-9]{6}|42[0-1][0-9]{7}||4[0-1][0-9]{8}|'          +
          '[1-3][0-9]{9}|[1-9][0-9]{1,8}|[0-9]):'                      +
          '(6553[0-5]|655[0-2][0-9]|654[0-9]{2}|65[0-4][0-9]{2}'       +
          '|6[0-4][0-9]{3}|[1-5][0-9]{4}|[1-9][0-9]{1,3}|[0-9])'       +
          '(|/(9[0-6]|[1-8][0-9]|[0-9]))';
      }
    }
    description
      "RTFILTER prefix consists of a 4-octet originating ASN followed by an
       8-octet Route Target Extended Community. It is specified as
       <asn>:<global value>:<local value>.";
    reference "RFC4684";
  }

  typedef bgp-std-large-community-type {
    /*
     * rfc8092#section-5
     * (4 byte global):(4 byte local 1):(4 byte local 2)
     */
    type string {
      pattern '(429496729[0-5]|42949672[0-8][0-9]|4294967[0-1][0-9]{2}'    +
              '|429496[0-6][0-9]{3}|42949[0-5][0-9]{4}|4294[0-8][0-9]{5}|' +
              '429[0-3][0-9]{6}|42[0-1][0-9]{7}||4[0-1][0-9]{8}|'          +
              '[1-3][0-9]{9}|[1-9][0-9]{1,8}|[0-9]):'                      +
              '(429496729[0-5]|42949672[0-8][0-9]|4294967[0-1][0-9]{2}'    +
              '|429496[0-6][0-9]{3}|42949[0-5][0-9]{4}|4294[0-8][0-9]{5}|' +
              '429[0-3][0-9]{6}|42[0-1][0-9]{7}||4[0-1][0-9]{8}|'          +
              '[1-3][0-9]{9}|[1-9][0-9]{1,8}|[0-9]):'                      +
              '(429496729[0-5]|42949672[0-8][0-9]|4294967[0-1][0-9]{2}'    +
              '|429496[0-6][0-9]{3}|42949[0-5][0-9]{4}|4294[0-8][0-9]{5}|' +
              '429[0-3][0-9]{6}|42[0-1][0-9]{7}||4[0-1][0-9]{8}|'          +
              '[1-3][0-9]{9}|[1-9][0-9]{1,8}|[0-9])';
    }
    description
      "Type definition for standard large community attribute represented as
      string of the form X:Y:Z where
      X = Global Administrator:  A four-octet namespace identifier.
      Y = Local Data Part 1:  A four-octet operator-defined value.
      Z = Local Data Part 2:  A four-octet operator-defined value.";
    reference "RFC 8092 - BGP Large Communities Attribute";
  }

  typedef bgp-large-community-regexp-type {
    type oc-types:std-regexp;
    description
      "Type definition for communities specified as regular
      expression patterns";
  }

  typedef bgp-large-community-type {
    /*
     * rfc8092#section-5
     * (4 byte global):(4 byte local 1):(4 byte local 2)
     */
    type string {
      pattern '^(429496729[0-5]|42949672[0-8][0-9]|4294967[0-1][0-9]{2}'   +
              '|429496[0-6][0-9]{3}|42949[0-5][0-9]{4}|4294[0-8][0-9]{5}|' +
              '429[0-3][0-9]{6}|42[0-1][0-9]{7}||4[0-1][0-9]{8}|'          +
              '[1-3][0-9]{9}|[1-9][0-9]{1,8}|[0-9]):'                      +
              '(429496729[0-5]|42949672[0-8][0-9]|4294967[0-1][0-9]{2}'    +
              '|429496[0-6][0-9]{3}|42949[0-5][0-9]{4}|4294[0-8][0-9]{5}|' +
              '429[0-3][0-9]{6}|42[0-1][0-9]{7}||4[0-1][0-9]{8}|'          +
              '[1-3][0-9]{9}|[1-9][0-9]{1,8}|[0-9]):'                      +
              '(429496729[0-5]|42949672[0-8][0-9]|4294967[0-1][0-9]{2}'    +
              '|429496[0-6][0-9]{3}|42949[0-5][0-9]{4}|4294[0-8][0-9]{5}|' +
              '429[0-3][0-9]{6}|42[0-1][0-9]{7}||4[0-1][0-9]{8}|'          +
              '[1-3][0-9]{9}|[1-9][0-9]{1,8}|[0-9])$';
    }
    description
      "Type definition for standard large community attribute represented as
      string of the form X:Y:Z where
      X = Global Administrator:  A four-octet namespace identifier.
      Y = Local Data Part 1:  A four-octet operator-defined value.
      Z = Local Data Part 2:  A four-octet operator-defined value.";
    reference "RFC 8092 - BGP Large Communities Attribute";
  }

  typedef bgp-route-type {
    type enumeration {
      enum INTERNAL {
        description "route type is internal";
      }
      enum EXTERNAL {
        description "route type is external";
      }
      enum LOCAL {
        description "route type is local";
      }
    }
  }

  typedef session-state-type {
    type enumeration {
      enum IDLE {
        description
          "neighbor is down, and in the Idle state of the
          FSM";
      }
      enum CONNECT {
        description
          "neighbor is down, and the session is waiting for
          the underlying transport session to be established";
      }
      enum ACTIVE {
        description
          "neighbor is down, and the local system is awaiting
          a conncetion from the remote peer";
      }
      enum OPENSENT {
        description
          "neighbor is in the process of being established.
          The local system has sent an Open message";
      }
      enum OPENCONFIRM {
        description
          "neighbor is in the process of being established.
          The local system is awaiting a Notification or
          Keepalive message";
      }
      enum ESTABLISHED {
        description
          "neighbor is up - the BGP session with the peer is
          established";
      }
      enum CLOSING {
        description
          "neighbor is down - the BGP session with the peer is
          is in Closing state trying to free up resources";
      }
      enum DELETING {
        description
          "neighbor is down - the BGP session with the peer is
          is in Deleting state trying to delete session";
      }
      enum INCOMPLETE {
        description
          "neighbor is down - the BGP session with the peer is
          is in Incomplete mandatory config state";
      }
      enum SHUTDOWN {
        description
          "neighbor is down - the BGP session with the peer is
          in Shutdown state";
      }
    }
  }

  identity IPV4_FLOWSPEC {
    base oc-bgp-types:AFI_SAFI_TYPE;
    description
      "Dissemination of IPv4 Unicast flow specification rules (AFI,SAFI = 1,133)";
    reference "RFC8955";
  }

  identity IPV6_FLOWSPEC {
    base oc-bgp-types:AFI_SAFI_TYPE;
    description
	  "Dissemination of IPv6 Unicast flow specification rules (AFI,SAFI = 2,133)";
    reference "RFC8956";
  }

  identity L3VPN_IPV4_FLOWSPEC {
    base oc-bgp-types:AFI_SAFI_TYPE;
    description
      "Dissemination of L3VPN IPv4 flow specification rules (AFI,SAFI = 1,134)";
    reference "RFC8955";
  }

  identity L3VPN_IPV6_FLOWSPEC {
    base oc-bgp-types:AFI_SAFI_TYPE;
    description
	   "Dissemination of L3VPN IPv6 flow specification rules (AFI,SAFI = 2,134)";
    reference "RFC8956";
  }

  identity IPV4_MUP {
    base oc-bgp-types:AFI_SAFI_TYPE;
    description
      "IPv4 Mobile User Plane (MUP) (AFI,SAFI = 1,85)";
    reference "draft-mpmz-bess-mup-safi-01.txt";
  }

  identity IPV6_MUP {
    base oc-bgp-types:AFI_SAFI_TYPE;
    description
      "IPv6 Mobile User Plane (MUP) (AFI,SAFI = 2,85)";
    reference "draft-mpmz-bess-mup-safi-01.txt";
  }

  typedef bgp-afi-safi-type {
    type identityref {
      base oc-bgp-types:AFI_SAFI_TYPE;
    }
  }

  /*
   * This is a lower case version of the BGP AFI-SAFI enum
   */
  typedef bgp-afi-safi-lc-type {
    type enumeration {
      enum ipv4-unicast {
        description
          "IPV4_UNICAST";
      }
      enum ipv6-unicast {
        description
          "IPV6_UNICAST";
      }
      enum ipv4-labeled-unicast {
        description
          "IPV4_LABELED_UNICAST";
      }
      enum ipv6-labeled-unicast {
        description
          "IPV6_LABELED_UNICAST";
      }
      enum ipv4-flowspec {
        description
          "IPV4_FLOWSPEC";
      }
      enum ipv6-flowspec {
        description
          "IPV6_FLOWSPEC";
      }
      enum ipv4-mup {
        description
          "IPV4_MUP";
      }
      enum ipv6-mup {
        description
          "IPV6_MUP";
      }
      enum l3vpn-ipv4-unicast {
        description
          "L3VPN_IPV4_UNICAST";
      }
      enum l3vpn-ipv6-unicast {
        description
          "L3VPN_IPV6_UNICAST";
      }
      enum l3vpn-ipv4-multicast {
        description
          "L3VPN_IPV4_MULTICAST";
      }
      enum l3vpn-ipv6-multicast {
        description
          "L3VPN_IPV6_MULTICAST";
      }
      enum evpn {
        description
          "L2VPN_EVPN";
      }
      enum vpls {
        description
          "L2VPN_VPLS";
      }
      enum rtfilter {
        description
          "RTFILTER";
      }
      enum srte-policy-ipv4 {
        description
          "SRTE_POLICY_IPV4";
      }
      enum srte-policy-ipv6 {
        description
          "SRTE_POLICY_IPV6";
      }
    }
  }

  typedef bgp-as-path-type {
     type string {
      pattern '[\d+,]+\d+';
    }
    description
      "A string consisting of a AS-Path numbers.";
  }

  typedef bgp-prefix-type {
    type union {
      type inet:ip-prefix;
      type string;
    }
  }

  /*
   * Similar to oc-netinst-type:LABEL_ALLOCATION_MODE
   */
  identity SID_ALLOCATION_MODE {
    description
      "Base identity to be used to express types of SRv6 segment ID
			allocation strategies to be used within a network instance";
  }

  identity PER_NEXTHOP {
    base SID_ALLOCATION_MODE;
    description
      "A segment ID is to be allocated per nexthop entry in the RIB for
      the network instance";
  }

  identity INSTANCE_SID {
    base SID_ALLOCATION_MODE;
    description
      "A single segment ID is to be used for the instance";
  }

  identity PER_NEXTHOP_NO_TRANSPOSITION {
    base SID_ALLOCATION_MODE;
    description
      "A segment ID is to be allocated per nexthop entry in the RIB for
      the network instance";
  }

  identity INSTANCE_SID_NO_TRANSPOSITION {
    base SID_ALLOCATION_MODE;
    description
      "A single segment ID is to be used for the instance";
  }

  // We use this to replace the openconfig's bgp-ext-community-type
  typedef bgp-extcomm-type {
    type union {
      type string {
        // bandwidth with Type 1
        // bandwidth:(ASN):(4-bytes)
        pattern 'bandwidth:'                                                 +
                '(6553[0-5]|655[0-2][0-9]|654[0-9]{2}|65[0-4][0-9]{2}'       +
                '|6[0-4][0-9]{3}|[1-5][0-9]{4}|[1-9][0-9]{1,3}|[0-9]):'      +
                '(429496729[0-5]|42949672[0-8][0-9]|4294967[0-1][0-9]{2}'    +
                '|429496[0-6][0-9]{3}|42949[0-5][0-9]{4}|4294[0-8][0-9]{5}|' +
                '429[0-3][0-9]{6}|42[0-8][0-9]{7}|4[0-1][0-9]{8}|'           +
                '[1-3][0-9]{9}|[1-9][0-9]{1,8}|[0-9])';
      }
      type string {
        // cost:(type):(4-bytes)
        pattern 'cost:'                                                      +
                '(6553[0-5]|655[0-2][0-9]|654[0-9]{2}|65[0-4][0-9]{2}'       +
                '|6[0-4][0-9]{3}|[1-5][0-9]{4}|[1-9][0-9]{1,3}|[0-9]):'      +
                '(429496729[0-5]|42949672[0-8][0-9]|4294967[0-1][0-9]{2}'    +
                '|429496[0-6][0-9]{3}|42949[0-5][0-9]{4}|4294[0-8][0-9]{5}|' +
                '429[0-3][0-9]{6}|42[0-8][0-9]{7}|4[0-1][0-9]{8}|'           +
                '[1-3][0-9]{9}|[1-9][0-9]{1,8}|[0-9])';
       }
       type string {
        // rmac:xxxx.xxxx.xxxx
        pattern 'rmac:'                                                      +
                '[0-9a-f]{4}(.[0-9a-f]{4}){2}';
       }
       type string {
        // route-target with Type 1
        // route-target:(ASN):(local-part)
        pattern 'route\-target:'                                             +
                '(6553[0-5]|655[0-2][0-9]|654[0-9]{2}|65[0-4][0-9]{2}'       +
                '|6[0-4][0-9]{3}|[1-5][0-9]{4}|[1-9][0-9]{1,3}|[0-9]):'      +
                '(429496729[0-5]|42949672[0-8][0-9]|4294967[0-1][0-9]{2}'    +
                '|429496[0-6][0-9]{3}|42949[0-5][0-9]{4}|4294[0-8][0-9]{5}|' +
                '429[0-3][0-9]{6}|42[0-8][0-9]{7}|4[0-1][0-9]{8}|'           +
                '[1-3][0-9]{9}|[1-9][0-9]{1,8}|[0-9])';
      }
      type string {
        // route-target with Type 2
        // route-target:(IPv4):(local-part)
        pattern 'route\-target:'                                             +
                '(([0-9]|[1-9][0-9]|1[0-9][0-9]|2[0-4][0-9]|'                +
                '25[0-5])\.){3}([0-9]|[1-9][0-9]|1[0-9][0-9]|'               +
                '2[0-4][0-9]|25[0-5]):'                                      +
                '(6553[0-5]|655[0-2][0-9]|654[0-9]{2}|65[0-4][0-9]{2}'       +
                '|6[0-4][0-9]{3}|[1-5][0-9]{4}|[1-9][0-9]{1,3}|[0-9])';
      }
      type string {
        // 4-byte AS Type 1 route-target
        pattern 'route\-target:'                                             +
                '(429496729[0-5]|42949672[0-8][0-9]|4294967[0-1][0-9]{2}'    +
                '|429496[0-6][0-9]{3}|42949[0-5][0-9]{4}|4294[0-8][0-9]{5}|' +
                '429[0-3][0-9]{6}|42[0-8][0-9]{7}|4[0-1][0-9]{8}|'           +
                '[1-3][0-9]{9}|[1-9][0-9]{1,8}|[0-9]):'                      +
                '(6553[0-5]|655[0-2][0-9]|654[0-9]{2}|65[0-4][0-9]{2}'       +
                '|6[0-4][0-9]{3}|[1-5][0-9]{4}|[1-9][0-9]{1,3}|[0-9])';
      }
      type string {
        // route-origin with Type 1
        pattern 'route\-origin:'                                             +
                '(6553[0-5]|655[0-2][0-9]|654[0-9]{2}|65[0-4][0-9]{2}'       +
                '|6[0-4][0-9]{3}|[1-5][0-9]{4}|[1-9][0-9]{1,3}|[0-9]):'      +
                '(429496729[0-5]|42949672[0-8][0-9]|4294967[0-1][0-9]{2}'    +
                '|429496[0-6][0-9]{3}|42949[0-5][0-9]{4}|4294[0-8][0-9]{5}|' +
                '429[0-3][0-9]{6}|42[0-8][0-9]{7}|4[0-1][0-9]{8}|'           +
                '[1-3][0-9]{9}|[1-9][0-9]{1,8}|[0-9])';
      }
      type string {
        // route-origin with Type 2
        pattern 'route\-origin:'                                             +
                '(([0-9]|[1-9][0-9]|1[0-9][0-9]|2[0-4][0-9]|'                +
                '25[0-5])\.){3}([0-9]|[1-9][0-9]|1[0-9][0-9]|'               +
                '2[0-4][0-9]|25[0-5]):'                                      +
                '(6553[0-5]|655[0-2][0-9]|654[0-9]{2}|65[0-4][0-9]{2}'       +
                '|6[0-4][0-9]{3}|[1-5][0-9]{4}|[1-9][0-9]{1,3}|[0-9])';
      }
      type string {
        // 4-byte AS Type 1 route-origin
        pattern 'route\-origin:'                                             +
                '(429496729[0-5]|42949672[0-8][0-9]|4294967[0-1][0-9]{2}'    +
                '|429496[0-6][0-9]{3}|42949[0-5][0-9]{4}|4294[0-8][0-9]{5}|' +
                '429[0-3][0-9]{6}|42[0-8][0-9]{7}|4[0-1][0-9]{8}|'           +
                '[1-3][0-9]{9}|[1-9][0-9]{1,8}|[0-9]):'                      +
                '(6553[0-5]|655[0-2][0-9]|654[0-9]{2}|65[0-4][0-9]{2}'       +
                '|6[0-4][0-9]{3}|[1-5][0-9]{4}|[1-9][0-9]{1,3}|[0-9])';
      }
      type string {
        // Extended Color Community
        pattern 'color:'                                                     +
                '[0-3]:'                                                  +
                '(429496729[0-5]|42949672[0-8][0-9]|4294967[0-1][0-9]{2}'    +
                '|429496[0-6][0-9]{3}|42949[0-5][0-9]{4}|4294[0-8][0-9]{5}|' +
                '429[0-3][0-9]{6}|42[0-8][0-9]{7}|4[0-1][0-9]{8}|'           +
                '[1-3][0-9]{9}|[1-9][0-9]{1,8}|[0-9])';
      }
      type string {
        // Extended ROV Community
        pattern 'rov:'                                                       +
                '[0-2]';
      }
      type string {
        // (ASN):(local-part)
        pattern 'mup:'                                                       +
                '(6553[0-5]|655[0-2][0-9]|654[0-9]{2}|65[0-4][0-9]{2}'       +
                '|6[0-4][0-9]{3}|[1-5][0-9]{4}|[1-9][0-9]{1,3}|[0-9]):'      +
                '(429496729[0-5]|42949672[0-8][0-9]|4294967[0-1][0-9]{2}'    +
                '|429496[0-6][0-9]{3}|42949[0-5][0-9]{4}|4294[0-8][0-9]{5}|' +
                '429[0-3][0-9]{6}|42[0-8][0-9]{7}|4[0-1][0-9]{8}|'           +
                '[1-3][0-9]{9}|[1-9][0-9]{1,8}|[0-9])';
      }
      type string {
        // (IPv4):(local-part)
        pattern 'mup:'                                                       +
                '(([0-9]|[1-9][0-9]|1[0-9][0-9]|2[0-4][0-9]|'                +
                '25[0-5])\.){3}([0-9]|[1-9][0-9]|1[0-9][0-9]|'               +
                '2[0-4][0-9]|25[0-5]):'                                      +
                '(6553[0-5]|655[0-2][0-9]|654[0-9]{2}|65[0-4][0-9]{2}'       +
                '|6[0-4][0-9]{3}|[1-5][0-9]{4}|[1-9][0-9]{1,3}|[0-9])';
      }
      type string {
        // (4-byte AS):(local-part)
        pattern 'mup:'                                                       +
                '(429496729[0-5]|42949672[0-8][0-9]|4294967[0-1][0-9]{2}'    +
                '|429496[0-6][0-9]{3}|42949[0-5][0-9]{4}|4294[0-8][0-9]{5}|' +
                '429[0-3][0-9]{6}|42[0-8][0-9]{7}|4[0-1][0-9]{8}|'           +
                '[1-3][0-9]{9}|[1-9][0-9]{1,8}|[0-9]):'                      +
                '(6553[0-5]|655[0-2][0-9]|654[0-9]{2}|65[0-4][0-9]{2}'       +
                '|6[0-4][0-9]{3}|[1-5][0-9]{4}|[1-9][0-9]{1,3}|[0-9])';
      }
      type string {
        // Extended Community in raw format
        pattern 'raw:'                                                       +
                '([0-9A-F][0-9A-F]:){7}[0-9A-F][0-9A-F]';
      }
    }
    description
      "Type definition for extended community attributes. In the case that
      common communities are utilised, they are represented as a string
      of the form:
        - bandwidth:<2b AS>:<4b value> per draft-ietf-idr-link-bandwidth-07 section 2
        - cost:<2b type>:<4b value> per draft-ietf-idr-custom-decision-08 section 3
        - color:<2b flags>:<4b value> per RFC9012 section 4.3
        - raw:XX:XX:XX:XX:XX:XX:XX:XX per draft-ietf-idr-bgp-model-14 section 7.2
        - rmac:<mac> where <mac> in the format of xxxx.xxxx.xxxx, x:0-9a-f
        - route-target:<2b AS>:<4b value> per RFC4360 section 4
        - route-target:<4b AS>:<2b value> per RFC4360 section 4
        - route-target:<4b IPv4>:<2b value> per RFC4360 section 4
        - route-origin:<2b ASN>:<4b value> per RFC4360 section 5
        - route-origin:<4b ASN>:<2b value> per RFC4360 section 5
        - route-origin:<4b IPv4>:<2b value> per RFC4360 section 5
        - rov:<0|1|2> per RFC8097 section 2
        - mup:<2b ASN>:<4b value>
        - mup:<4b IPv4>:<2b value>
        - mup:<4b ASN>:<2b value>";
    reference
      "RFC 4360 - BGP Extended Communities Attribute
       RFC 5668 - 4-Octet AS Specific BGP Extended Community
       draft-ietf-idr-segment-routing-te-policy
       RFC 9012 - The BGP Tunnel Encapsulation Attribute
       draft-mpmz-bess-mup-safi-01";
  }

  typedef as-range {
    type string {
      // range specified as [lower]..[upper]
      pattern '(429496729[0-5]|42949672[0-8][0-9]|4294967[0-1][0-9]{2}'        +
              '|429496[0-6][0-9]{3}|42949[0-5][0-9]{4}|4294[0-8][0-9]{5}|'     +
              '429[0-3][0-9]{6}|42[0-8][0-9]{7}|4[0-1][0-9]{8}|[1-3][0-9]{9}|' +
              '[1-9][0-9]{1,8}|[1-9])\.\.'                                     +
              '(429496729[0-5]|42949672[0-8][0-9]|4294967[0-1][0-9]{2}'        +
              '|429496[0-6][0-9]{3}|42949[0-5][0-9]{4}|4294[0-8][0-9]{5}|'     +
              '429[0-3][0-9]{6}|42[0-8][0-9]{7}|4[0-1][0-9]{8}|[1-3][0-9]{9}|' +
              '[1-9][0-9]{1,8}|[1-9])';
    }
    description
      "Type definition representing a range of peer-as that
       BGP can form session with. Range is specified as x..y
       where x and y are valid AS number (1 <= peer-as <= 4294967295).
       The range is assumed to be inclusive, such that any peer-as matching
       x <= peer-as <= y falls within the range.";
  }

  typedef peer-as-range {
    type union {
      type oc-inet:as-number;
      type arc-oc-bgp-types:as-range;
    }
    description
      "Type definition representing peer as range configuartion
         <peer-as>       Peer AS number
         <peer-as-range> Peer AS number in range";
  }

  identity MUP_ARCHITECTURE_TYPE {
    description
      "Base identity for Architecture Type.";
    reference
      "I-D.mpmz-bess-mup-safi: BGP Extensions for the Mobile
                               User Plane (MUP) SAFI.";
  }

  identity THREE_GPP_5G {
    base MUP_ARCHITECTURE_TYPE;
    description
      "Third generation partnership project (3GPP)
       system with 5G Mobile Technology.";
    reference
      "I-D.mpmz-bess-mup-safi: BGP Extensions for the Mobile
                               User Plane (MUP) SAFI.";
  }

  identity MUP_SEGMENT_TYPE {
    description
      "Mobile user plane network segment type";
  }
  identity DIRECT {
    base MUP_SEGMENT_TYPE;
    description
      "Direct segment type";
  }
  identity INTERWORK {
    base MUP_SEGMENT_TYPE;
    description
      "Interwork segment type";
  }
  identity FORWARDING_ACTION {
    description
      "Base identity for forwarding actions of flowspec rules";
  }

  identity DROP {
    base FORWARDING_ACTION;
    description
      "Drop Action";
  }

  identity ACCEPT {
    base FORWARDING_ACTION;
    description
      "Redirect to VRF action";
  }

  typedef bgp-mup-ext-community-type {
    type union {
      type string {
        // (ASN):(local-part)
        pattern '(6553[0-5]|655[0-2][0-9]|654[0-9]{2}|65[0-4][0-9]{2}'       +
                '|6[0-4][0-9]{3}|[1-5][0-9]{4}|[1-9][0-9]{1,3}|[0-9]):'      +
                '(429496729[0-5]|42949672[0-8][0-9]|4294967[0-1][0-9]{2}'    +
                '|429496[0-6][0-9]{3}|42949[0-5][0-9]{4}|4294[0-8][0-9]{5}|' +
                '429[0-3][0-9]{6}|42[0-8][0-9]{7}|4[0-1][0-9]{8}|'           +
                '[1-3][0-9]{9}|[1-9][0-9]{1,8}|[0-9])';
      }
      type string {
        // (IPv4):(local-part)
        pattern '(([0-9]|[1-9][0-9]|1[0-9][0-9]|2[0-4][0-9]|'                +
                '25[0-5])\.){3}([0-9]|[1-9][0-9]|1[0-9][0-9]|'               +
                '2[0-4][0-9]|25[0-5]):'                                      +
                '(6553[0-5]|655[0-2][0-9]|654[0-9]{2}|65[0-4][0-9]{2}'       +
                '|6[0-4][0-9]{3}|[1-5][0-9]{4}|[1-9][0-9]{1,3}|[0-9])';
      }
      type string {
        // (4-byte AS):(local-part)
        pattern '(429496729[0-5]|42949672[0-8][0-9]|4294967[0-1][0-9]{2}'    +
                '|429496[0-6][0-9]{3}|42949[0-5][0-9]{4}|4294[0-8][0-9]{5}|' +
                '429[0-3][0-9]{6}|42[0-8][0-9]{7}|4[0-1][0-9]{8}|'           +
                '[1-3][0-9]{9}|[1-9][0-9]{1,8}|[0-9]):'                      +
                '(6553[0-5]|655[0-2][0-9]|654[0-9]{2}|65[0-4][0-9]{2}'       +
                '|6[0-4][0-9]{3}|[1-5][0-9]{4}|[1-9][0-9]{1,3}|[0-9])';
      }
    }
    description
      "A type definition utilised to define the extended community
      in routes of mobile user plane SAFI";
  }

  identity RT_REDIRECT_NEXT_HOPS {
    description
      "Base identity for Flowpsec RT Rediect Next Hop Types.";
  }

  identity DEFAULT {
    base RT_REDIRECT_NEXT_HOPS;
    description
      "Use Next Hop of default route in the VRF corresponding to RT Redirect";
  }

  identity BGP_NLRI {
    base RT_REDIRECT_NEXT_HOPS;
    description
      "Use the MP Reach Next Hop from the BGP Flowspec NLRI";
  }
}
