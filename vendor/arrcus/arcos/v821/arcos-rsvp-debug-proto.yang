module arcos-rsvp-debug-proto {
  yang-version "1";
  namespace "http://yang.arrcus.com/arcos/rsvp/debug/proto";
  prefix arc-rsvp-dbg-proto;

  import openconfig-policy-types {
    prefix oc-pol-types;
  }

  import arcos-openconfig-policy-types {
    prefix arc-oc-pol-types;
  }

  import arcos-debug {
    prefix arc-dbg;
  }

  organization
    "Arrcus, Inc";

  contact
    "Arrcus, Inc.
     2077 Gateway Place
     Suite 400
     San Jose, CA 95110

     E-mail: yang-support@arrcus.com";

  description
    "This module defines debug statements for Arrcus 
     implementation of RSVP.";

  revision "2022-05-31" {
    description
      "Initial version.";
  }

  grouping rsvp-debug-proto-top {
    container rsvp {
      description
        "This container defines instance-specific RSVP debug information.";
      config false;

      uses arc-dbg:debug-component-top;
    }
  }

  augment "/arc-dbg:debug/arc-dbg:network-instances/arc-dbg:network-instance" +
          "/arc-dbg:protocols/arc-dbg:protocol" {
    uses rsvp-debug-proto-top {
      when "arc-dbg:identifier = 'arc-oc-pol-types:RSVP'" {
        description
          "Include RSVP debug information when the protocol is of type RSVP";
      }
      description
        "Debug information related to a specific instance of RSVP";
    }
  }
}
