module arcos-openconfig-policy-types {
  yang-version 1.1;
  namespace "http://yang.arrcus.com/arcos/openconfig/policy-types";
  prefix arc-oc-pol-types;

  import openconfig-policy-types {
    prefix oc-pol-types;
  }

  contact
    "Arrcus, Inc.
     2077 Gateway Place
     Suite 400
     San Jose, CA 95110
     E-mail: yang-support@arrcus.com";

  description
    "Arrcus augmentation for openconfig-policy-types

     Copyright (c) 2016-2023 by Arrcus, Inc.
     All rights reserved.";

  organization
    "Arrcus, Inc.";

  revision 2025-03-25 {
    description
      "Add EXT_RIB_IPFIX as a protocol to support redistribution of LOCAL CONNECTED routes";
  }

  revision 2024-04-30 {
    description
      "Add LI as protocol source of RNH and tunnel entries";
  }

  revision 2024-04-23 {
    description
      "Adding EVPN_VPWS as a protocol type to support label statistics for VPWS ingress label.";
  }
  
  revision 2024-04-19 {
    description
      "Add SR-Policy as protocol source";
  }

  revision 2024-02-29 {
    description
      "Adding VRRP as rib route type";
  }

  revision 2023-11-28 {
    description
      "Add identifer for BGP MUP SAFI";
  }

  revision 2022-12-12 {
    description
      "* Add L2FM protocol type to support static vxlan.";
  }

  identity BGP_MUP {
    base oc-pol-types:INSTALL_PROTOCOL_TYPE;
    description
      "BGP MUP route";
  }

  identity ADJACENCY {
    base oc-pol-types:INSTALL_PROTOCOL_TYPE;
    description
      "Adjacency route";
  }

  identity LDP {
    base oc-pol-types:INSTALL_PROTOCOL_TYPE;
    description
      "LDP";
  }

  identity SIDMGR {
    base oc-pol-types:INSTALL_PROTOCOL_TYPE;
    description
      "SIDMGR";
  }

  identity LAG {
    base oc-pol-types:INSTALL_PROTOCOL_TYPE;
    description
      "Link Aggregation";
  }

  identity RSVP {
    base oc-pol-types:INSTALL_PROTOCOL_TYPE;
    description
      "RSVP Protocol";
  }

  identity INTERNAL {
    base oc-pol-types:INSTALL_PROTOCOL_TYPE;
    description
      "Internal route";
  }

  identity L2FM {
    base oc-pol-types:INSTALL_PROTOCOL_TYPE;
    description
      "L2FM route";
  }

  identity VRRP {
    base oc-pol-types:INSTALL_PROTOCOL_TYPE;
    description
      "VRRP route";
  }

  identity EVPN_VPWS {
    base oc-pol-types:INSTALL_PROTOCOL_TYPE;
    description "L2RIB installed EVPN_VPWS (label) route.";
  }
  
  identity SR_POLICY {
    base oc-pol-types:INSTALL_PROTOCOL_TYPE;
    description
      "SR-Policy route";
  }

  identity LI {
    base oc-pol-types:INSTALL_PROTOCOL_TYPE;
    description
      "Lawful Intercept RNH/Tunnel entry";
  }

  identity EXT_RIB_IPFIX {
    base oc-pol-types:INSTALL_PROTOCOL_TYPE;
    description
      "Extended RIB IPFIX";
  }
}
