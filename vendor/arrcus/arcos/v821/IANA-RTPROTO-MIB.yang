/*
 * Generated by confdc --mib2yang
 * Source: IANA-RTPROTO-MIB.mib
 */
module IANA-RTPROTO-MIB {
  namespace "http://tail-f.com/ns/mibs/IANA-RTPROTO-MIB/200009260000Z";
  prefix IANA_RTPROTO_MIB;
  tailf:id "";
  tailf:snmp-mib-module-name "IANA-RTPROTO-MIB";
  import tailf-common {
    prefix tailf;
  }

  revision 2000-09-26 {
    description
      "";
  }

  typedef IANAipRouteProtocol {
    type enumeration {
      enum "other" {
        value 1;
      }
      enum "local" {
        value 2;
      }
      enum "netmgmt" {
        value 3;
      }
      enum "icmp" {
        value 4;
      }
      enum "egp" {
        value 5;
      }
      enum "ggp" {
        value 6;
      }
      enum "hello" {
        value 7;
      }
      enum "rip" {
        value 8;
      }
      enum "isIs" {
        value 9;
      }
      enum "esIs" {
        value 10;
      }
      enum "ciscoIgrp" {
        value 11;
      }
      enum "bbnSpfIgp" {
        value 12;
      }
      enum "ospf" {
        value 13;
      }
      enum "bgp" {
        value 14;
      }
      enum "idpr" {
        value 15;
      }
      enum "ciscoEigrp" {
        value 16;
      }
      enum "dvmrp" {
        value 17;
      }
    }
  }

  typedef IANAipMRouteProtocol {
    type enumeration {
      enum "other" {
        value 1;
      }
      enum "local" {
        value 2;
      }
      enum "netmgmt" {
        value 3;
      }
      enum "dvmrp" {
        value 4;
      }
      enum "mospf" {
        value 5;
      }
      enum "pimSparseDense" {
        value 6;
      }
      enum "cbt" {
        value 7;
      }
      enum "pimSparseMode" {
        value 8;
      }
      enum "pimDenseMode" {
        value 9;
      }
      enum "igmpOnly" {
        value 10;
      }
      enum "bgmp" {
        value 11;
      }
      enum "msdp" {
        value 12;
      }
    }
  }
}
