module arcos-openconfig-bgp-augments-arcrr-deviations {
  yang-version 1.1;
  namespace "http://yang.arrcus.com/arcos/openconfig/bgp/augments/arcrr/deviations";
  prefix arc-oc-bgp-aug-arcrr-dev;

  import openconfig-network-instance {
    prefix oc-ni;
  }

  import arcos-openconfig-bgp-augments {
    prefix arc-oc-bgp-aug;
  }


  deviation "/oc-ni:network-instances/oc-ni:network-instance" +
            "/oc-ni:protocols/oc-ni:protocol" +
            "/oc-ni:bgp" +
            "/oc-ni:global/oc-ni:config" +
            "/arc-oc-bgp-aug:disable-rib-install" {
    deviate add {
      default true;
    }
    description "Disable BGP route installation in RIB.";
  }
}
