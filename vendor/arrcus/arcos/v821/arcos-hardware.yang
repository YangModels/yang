module arcos-hardware {
  yang-version 1.1;
  namespace "http://yang.arrcus.com/arcos/hardware";
  prefix arc-hw;

  include arcos-hardware-units;
  include arcos-hardware-common;
  include arcos-hardware-platform;
  include arcos-hardware-ecmp;
  include arcos-hardware-scale;

  revision "2024-08-08" {
    description
      "removing augment for arcos-runtime and 
        importing hardware in arcos-runtime for VDR";
  }

  grouping hardware-config {
    description
      "hardware configuration parameters";

    container common {
      uses hardware-common;
    }

    container platform {
      uses hardware-platform;
    }
  }

  grouping hardware-state {
    description
    "Operational state data for harware";
  }

  grouping hardware-top {
    description
       "Top-level grouping for hardware configuration";
    container hardware {
      description
        "Configure and view hardware resources";
      container config {
        description
         "Configuration for hardware";
        uses hardware-config;
      }
      container state {
        config false;

        uses hardware-config;
        uses hardware-state;
      }
      container units {
        config false;
        uses hardware-units;
      }
    }
  }
  uses hardware-top;

}
