/*
 * Generated by confdc --mib2yang-std
 * Source: ARRCUS-IF-MIB.mib
 */
/*
 * This YANG module has been generated by smidump 0.5.0:
 *
 *      smidump -f yang ARRCUS-IF-MIB
 *
 * Do not edit. Edit the source file instead!
 */

module ARRCUS-IF-MIB {

  namespace "urn:ietf:params:xml:ns:yang:smiv2:ARRCUS-IF-MIB";
  prefix "arrcus-if";

  import ietf-yang-smiv2 {
    prefix "smiv2";
  }

  import ietf-yang-types {
    prefix "yang";
  }

  organization
   "@ARRCUS";

  contact
   "@arrcus.com";

  description
   "This module defines the model for viewing Arrcus specific interface information";

  revision 2020-07-27 {
    description
     "@REVISION-DESCRIPTION";
  }

  typedef InterfaceIndex {
    type int32 {
      range "1..2147483647";
    }
    description
     "A unique value, greater than zero, for each interface or
      interface sub-layer in the managed system.  It is
      recommended that values are assigned contiguously starting
      from 1.  The value for each interface sub-layer must remain
      constant at least from one re-initialization of the entity's
      network management system to the next re-initialization.";
    smiv2:display-hint "d";
  }


  container ARRCUS-IF-MIB {
    config false;

    container interfaces {
      smiv2:oid "1.3.6.1.4.1.51604.3.4.1";

      leaf ifNumber {
        type int32;
        description
         "The number of network interfaces (regardless of their
          current state) present on this system.";
        smiv2:max-access "read-only";
        smiv2:oid "1.3.6.1.4.1.51604.3.4.1.1";
      }
    }

    container arrcusIfTable {
      description
       "A list of interface entries.  The number of entries is
        given by the value of ifNumber.";
      smiv2:oid "1.3.6.1.4.1.51604.3.4.1.2";

      list ifEntry {
        key "ifIndex";
        description
         "An entry containing management information applicable to a
          particular interface.";
        smiv2:oid "1.3.6.1.4.1.51604.3.4.1.2.1";

        leaf ifIndex {
          type arrcus-if:InterfaceIndex;
          description
           "A unique value, greater than zero, for each interface.  It
            is recommended that values are assigned contiguously
            starting from 1.  The value for each interface sub-layer
            must remain constant at least from one re-initialization of
            the entity's network management system to the next re-
            initialization.";
          smiv2:max-access "read-only";
          smiv2:oid "1.3.6.1.4.1.51604.3.4.1.2.1.1";
        }

        leaf ifCarrierTransitionCount {
          type yang:counter64;
          description
           "Number of times the interface state has transitioned between up and
            down since the time the device restarted or the last-clear time,
            whichever is most recent.";
          smiv2:max-access "read-only";
          smiv2:oid "1.3.6.1.4.1.51604.3.4.1.2.1.2";
        }

        leaf ifQueueDropPackets {
          type yang:counter64;
          description
           "Queue Drop Packets";
          smiv2:max-access "read-only";
          smiv2:oid "1.3.6.1.4.1.51604.3.4.1.2.1.3";
        }
      }
    }
  }

  smiv2:alias "aRRCUS-IF-MIB" {
    smiv2:oid "1.3.6.1.4.1.51604.3.4";
  }

  smiv2:alias "interfaces" {
    smiv2:oid "1.3.6.1.4.1.51604.3.4.1";
  }

}
