module arcos-qos-tablemap-deviations {
  yang-version 1.1;
  namespace "http://yang.arrcus.com/arcos/qos/tablemap/deviations";
  prefix arc-qos-tbl-dev;

  import arcos-qos {
    prefix arc-qos;
  }
  import arcos-qos-tablemap-types {
    prefix arc-qos-tbl-types;
  }
  import arcos-qos-tablemap {
    prefix arc-qos-tbl;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for qos tablemap annotations";

  deviation "/arc-qos:qos/arc-qos-tbl:tablemaps/arc-qos-tbl:tablemap"
          + "/arc-qos-tbl:config" {
    deviate add {
      must "(boolean(arc-qos-tbl:from-type = 'arc-qos-tbl-types:LOCAL_TC') or
             boolean(arc-qos-tbl:to-type = 'arc-qos-tbl-types:LOCAL_TC'))" {
          error-message "from or to type has to be local-tc";
      }
    }
  }

  deviation "/arc-qos:qos/arc-qos-tbl:tablemaps/arc-qos-tbl:tablemap"
          + "/arc-qos-tbl:config" {
    deviate add {
      must "(boolean(arc-qos-tbl:from-type != 'arc-qos-tbl-types:LOCAL_TC') or
             boolean(arc-qos-tbl:to-type != 'arc-qos-tbl-types:LOCAL_TC'))" {
          error-message "from or to type,one of them has to be other than local-tc";
      }
    }
  }
}
