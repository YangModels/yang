module arcos-policy-action-types {
  yang-version 1.1;
  namespace "http://yang.arrcus.com/arcos/policy/action/types";
  prefix arc-pol-actn-types;

  organization
    "Arrcus, Inc.";

  contact
    "Arrcus, Inc.
     2077 Gateway Place
     Suite 400
     San Jose, CA 95110

     E-mail: yang-support@arrcus.com";

  description
    "YANG data-model for policy action types

    Copyright (c) 2016-2023 by Arrcus, Inc.
    All rights reserved.";

   revision 2023-06-27 {
    description
      "Initial revision.";
  }

  identity ACTION_TYPE {
    description
      "This is an identity of base action-type";
  }

  identity DROP {
    base ACTION_TYPE;
    description
      "drop action type extended from the base action type";
  }

  identity TRANSMIT {
    base ACTION_TYPE;
    description
      "drop action type extended from the base action type";
  }

  identity MARK {
    base ACTION_TYPE;
    description
      "marking action type extended from the base action type";
  }

  identity POLICE {
    base ACTION_TYPE;
    description
      "police action type";
  }
}
