module arcos-trace {
  yang-version 1.1;
  namespace "http://yang.arrcus.com/arcos/trace";
  prefix arc-trace;

  container trace {
    config false;

    container sessions {
      action create {
	      input {
	        leaf name {
	          type string;
	          mandatory true;
	        }
	      }
	      output {
	        leaf response {
	          type string;
	          mandatory true;
	        }
        }
      }

      list sessions {
        key name;

        leaf name {
          type string;
        }

        action destroy {
          output {
            leaf response {
              type string;
              mandatory true;
            }
          }
        }

        action select {
          output {
            leaf response {
              type string;
              mandatory true;
            }
          }
        }
      }
    }

    container points {
      list points {
        key name;

        leaf name {
          type string;
        }

        action enable {
          output {
            leaf response {
              type string;
              mandatory true;
            }
          }
        }

        action disable {
          output {
            leaf response {
              type string;
              mandatory true;
            }
          }
        }
      }
    }
  }
}
