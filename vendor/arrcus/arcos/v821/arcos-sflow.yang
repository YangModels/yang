module arcos-sflow {
  yang-version 1.1;
  namespace "http://yang.arrcus.com/arcos/sflow";
  prefix arc-sflow;

  import ietf-inet-types {
    prefix inet;
  }
  import iana-if-type {
    prefix ianaift;
  }
  import openconfig-interfaces {
    prefix oc-if;
  }
  import openconfig-network-instance {
    prefix oc-netinst;
  }
  import arcos-platform {
    prefix arc-platform;
  }
  import openconfig-system {
    prefix oc-sys;
  }
  import arcos-openconfig-system-augments {
    prefix arc-oc-sys-aug;
  }

  organization
    "Arrcus, Inc.";

  contact
    "Arrcus, Inc.
     2077 Gateway Place
     Suite 400
     San Jose, CA 95110

     E-mail: yang-support@arrcus.com";

  description
    "This module contains definitions for the sflow feature in ArcOS

     Copyright (c) 2016-2024 by Arrcus, Inc.
     All rights reserved.";

  revision 2025-09-18 {
    description "Added validation to avoid configuration of sflow on 
        bond member interfaces";
  }

  revision 2025-01-22 {
    description "Added extension to support the addition of
        BGP and IP Router fields to the FLOWSAMPLES";
  }

  revision 2024-01-11 {
    description "Use sampling type instead of direction
        to support different types of sampling in the future";
  }
  revision 2023-09-12 {
    description "Display sflow interface node based on interface name";
  }

  grouping sflow-packet-sampling-rate {
    description
      "Grouping for sflow packet sampling rate parameters";
    leaf packet-sampling-rate {
      type uint32;
      description
        "default packet sampling rate for each interface/direction";
    }
  }

  grouping sflow-collector-common-fields {
    description
      "Grouping for sflow collector specific optional fields";
    leaf port {
      type uint16;
      default 6343;
      description
        "Destination Layer 4 port number of sflow datagram (default- 6343)";
    }
  }

  grouping sflow-ipv4-top {
    description
      "Grouping for sflow ipv4 global configurations";
    container ipv4 {
      description
        "Parameters for the IPv4 sflow datagrams";
      leaf agent-ip {
        type inet:ipv4-address-no-zone;
        description
          "Agent IP address of SFLOW datagrams (default- ma1 address)";
      }
      list collector {
        key "address";
        max-elements 6;
        description
          "List of collectors for sflow datagrams";
        leaf address {
          mandatory true;
          type inet:ipv4-address-no-zone;
          description
            "Destination address of sflow datagram";
        }
        uses sflow-collector-common-fields;
      }
    }
  }

  grouping sflow-ipv6-top {
    description
      "Grouping for sflow ipv6 global configurations";
    container ipv6 {
      description
        "Parameters for the IPv6 sflow datagrams";
      leaf agent-ip {
        type inet:ipv6-address-no-zone;
        description
          "Agent IP address of SFLOW datagrams (default- ma1 address)";
      }
      list collector {
        key "address";
        description
          "List of collectors for sflow datagrams";
        leaf address {
          mandatory true;
          type inet:ipv6-address-no-zone;
          description
            "Destination address of sflow datagram";
        }
        uses sflow-collector-common-fields;
      }
    }
  }

  grouping sflow-bgp-extension-top {
    description
      "sflow global extension - extracting BGP information";
    container extension-gateway {
      description
        "sflow global extension - extracting BGP information";
      leaf enabled {
        type boolean;
        default false;
        description
          "When set to true, sflow extension gateway is enabled";
     }
    }
  }

  grouping sflow-global-state-top {
    description
      "Defines for sflow specific statistics";
    leaf counter-samples {
      type uint64;
      description
        "Total valid counter samples sent";
    }
    leaf packet-samples {
      type uint64;
      description
        "Total valid packet samples sent";
    }
  }

  grouping sflow-global-top {
    description
      "Defines for sflow specific global configurations";
    leaf counter-sampling-interval {
      type uint16 {
        range "10..300";
      }
      description
        "Polling interval in seconds (default- 60 seconds)";
    }
    uses sflow-packet-sampling-rate;
    leaf agent-ip-interface {
      type leafref {
        path "/oc-if:interfaces/oc-if:interface/oc-if:config/oc-if:name";
      }
      description
        "Sflow Agent interface (default- ma1 interface)";
    }
    leaf network-instance {
      type leafref {
        path "/oc-netinst:network-instances/oc-netinst:network-instance/oc-netinst:config/oc-netinst:name";
      }
      description
        "Name of a l3vrf network-instance (default instance if not specified)";
    }
    uses sflow-ipv4-top {
      when "(not(boolean(./ipv6/agent-ip)) and "
         + " not(boolean(./ipv6/collector/address)))";
    }
    uses sflow-ipv6-top {
      when "(not(boolean(./ipv4/agent-ip)) and "
         + " not(boolean(./ipv4/collector/address)))";
    }
    uses sflow-bgp-extension-top;
  }

  grouping sflow-interface-top {
    description
      "Defines for sflow specific interface level configurations";
    leaf name {
      type leafref {
        path "/oc-if:interfaces/oc-if:interface/oc-if:config/oc-if:name";
      }
      description
        "Reference to the sflow interface";
      must "(starts-with(/oc-if:interfaces/oc-if:interface[oc-if:name=current()]/oc-if:name, 'swp')) or
            (starts-with(/oc-if:interfaces/oc-if:interface[oc-if:name=current()]/oc-if:name, 'bond')) or (
            (starts-with(/oc-if:interfaces/oc-if:interface[oc-if:name=current()]/oc-if:name, 'vlan')) and
            (/arc-platform:platform/arc-platform:family = 'arc-platform:BROADCOM_DNX'))";
    }
    leaf direction {
      type enumeration {
        enum ingress {
          description
            "sflow sampling for incoming traffic";
        }
        enum egress {
          description
            "sflow sampling for outgoing traffic";
        }
        enum egress-access-port {
          description
            "sflow sampling for outgoing traffic on an Vxlan Access Port";
        }
      }
    }
    uses sflow-packet-sampling-rate {
      when "((/arc-platform:platform/arc-platform:asic = 'arc-platform:BROADCOM_TRIDENT4') or
            (/arc-platform:platform/arc-platform:asic = 'arc-platform:BROADCOM_TRIDENT3') or
            (/arc-platform:platform/arc-platform:asic = 'arc-platform:BROADCOM_TRIDENT2') or
            (/arc-platform:platform/arc-platform:asic = 'arc-platform:BROADCOM_TOMAHAWK') or
            (/arc-platform:platform/arc-platform:asic = 'arc-platform:BROADCOM_TOMAHAWK3') or
            (/arc-platform:platform/arc-platform:asic = 'arc-platform:BROADCOM_HELIX4') or
            (/arc-platform:platform/arc-platform:family = 'arc-platform:BROADCOM_DNX_JPLUS') or
            (/arc-platform:platform/arc-platform:family = 'arc-platform:BROADCOM_DNX') or
            (/arc-platform:platform/arc-platform:deployment-type = 'arc-platform:DISTRIBUTED') or
            (boolean(/arc-platform:platform/arc-platform:asic) != 'true')) and
            (not(current()/../arc-sflow:direction = 'egress-access-port'))";
    }
  }

  grouping sflow-top {
    description
      "Top-level grouping for sflow feature";
    container sflow {
      description
        "sflow feature specific configurations and state";
      container global {
        description
          "Global config/state parameters for sflow";
        container config {
          description
            "Global configuration parameters for sflow";
          uses sflow-global-top;
        }
        container state {
          description
            "Global state parameters for sflow";
          config false;
          uses sflow-global-top;
          uses sflow-global-state-top;
        }
      }
      container interfaces {
        description
          "Interface config/state parameters for sflow";
        list interface {
          key "name direction";
          description
            "List of interfaces on which sFlow is enabled";
          leaf name {
            type leafref {
              path "../config/name";
            }

            must "(not(boolean(/oc-if:interfaces/oc-if:interface[oc-if:name=current()]/oc-eth:ethernet/oc-eth:config/oc-lag:aggregate-id)))" {
              error-message "Invalid configuration : sFlow cannot be enabled on bond member interfaces";
            }
          }
          leaf direction {
            type leafref {
              path "../config/direction";
            }
          }
          container config {
            description
              "Interface configuration parameters for sflow";
            uses sflow-interface-top {
              refine direction {
                must "(not ((current() = 'egress') and "
                  +"(derived-from-or-self(/arc-platform:platform/arc-platform:asic, 'arc-platform:BROADCOM_JERICHOPLUS')))) or "
                  +"((current() = 'egress-access-port') and not (derived-from-or-self(/arc-platform:platform/arc-platform:asic, 'arc-platform:BROADCOM_TRIDENT3')))" {
                    error-message "Sampling type not supported on this platform";
                  }
              }
            }
          }
          container state {
            description
              "Interface configuration parameters for sflow";
            config false;
            uses sflow-interface-top;
          }
        }
      }
    }
  }

  uses sflow-top {
    when "(/arc-platform:platform/arc-platform:asic = 'arc-platform:BROADCOM_TRIDENT4') or
          (/arc-platform:platform/arc-platform:asic = 'arc-platform:BROADCOM_TRIDENT3') or
          (/arc-platform:platform/arc-platform:asic = 'arc-platform:BROADCOM_TRIDENT2') or
          (/arc-platform:platform/arc-platform:asic = 'arc-platform:BROADCOM_TOMAHAWK') or
          (/arc-platform:platform/arc-platform:asic = 'arc-platform:BROADCOM_TOMAHAWK3') or
          (/arc-platform:platform/arc-platform:asic = 'arc-platform:BROADCOM_HELIX4') or
          (/arc-platform:platform/arc-platform:family = 'arc-platform:BROADCOM_DNX') or
          (/arc-platform:platform/arc-platform:family = 'arc-platform:BROADCOM_DNX_JPLUS') or
          (/arc-platform:platform/arc-platform:deployment-type = 'arc-platform:DISTRIBUTED') or
          (boolean(/arc-platform:platform/arc-platform:asic) != 'true') or 
          (/oc-sys:system/arc-oc-sys-aug:cli/arc-oc-sys-aug:config/arc-oc-sys-aug:unhide-unsupported-cli = 'true')";
  }
}
