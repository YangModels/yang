submodule arcos-datapath-aft-ipv6 {
  yang-version "1.1";

  belongs-to "arcos-datapath-aft" {
    prefix "arcos-dp-aft";
  }

  import ietf-inet-types { prefix "inet"; }

  // Include common cross-AFT groupings from the common submodule.
  include arcos-datapath-aft-common;

  organization
    "XXXXX";

  contact
    "XXXXX";

  description
    "Submodule containing definitions of groupings for the abstract
    forwarding tables for IPv6.";

  grouping aft-ipv6-unicast-flat-structural {
    description
      "Structural grouping defining the schema for the flattened IPv6 unicast
      abstract forwarding table.";

    action v6-route {
      description
        "IPv6 route lookup";
      input {
        leaf prefix {
          type inet:ipv6-prefix;
          mandatory true;
          description
            "The IPv6 address to be looked up from RIB";
        }
      }
      output {
        leaf prefix {
          type inet:ipv6-prefix;
          description
            "The IPv6 address to be looked up from RIB";
        }
        uses aft-ipv6-unicast-entry-flat-state;
      }
    }
  }

  grouping aft-ipv6-unicast-entry-flat-state {
    description
      "Operational state parameters for the IPv6 unicast entry.";
    uses aft-common-entry-flat-state;
  }

  grouping aft-ipv6-unicast-structural {
    description
      "Structural grouping defining the schema for the IPv6 unicast
      abstract forwarding table.";

    list ipv6-entry {
      key "prefix";

      description
        "List of the IPv6 unicast entries within the abstract
        forwarding table. This list is keyed by the destination IPv6
        prefix.";

      leaf prefix {
        type leafref {
          path "../state/prefix";
        }
        description
          "Reference to the IPv6 unicast destination prefix which
          must be matched to utilise the AFT entry.";
      }

      container state {
        description
          "Operational state parameters for the IPv6 unicast AFT
          entry.";
        uses aft-ipv6-unicast-entry-config;
        uses aft-ipv6-unicast-entry-state;
      }

    }
  }

  grouping aft-ipv6-unicast-entry-config {
    description
      "Configuration parameters for the IPv6 unicast entry.";

    leaf prefix {
        type inet:ipv6-prefix;
        description
          "The IPv6 destination prefix that should be matched to
          utilise the AFT entry.";
    }
  }

  grouping aft-ipv6-unicast-entry-state {
    description
      "Operational state parameters for the IPv6 unicast entry.";
    uses aft-common-entry-state;
  }
}
