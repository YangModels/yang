/*
 * Generated by confdc --mib2yang-std
 * Source: UCD-SNMP-MIB.mib
 */
/*
 * This YANG module has been generated by smidump 0.5.0:
 *
 *      smidump -f yang UCD-SNMP-MIB
 *
 * Do not edit. Edit the source file instead!
 */

module UCD-SNMP-MIB {

  namespace "urn:ietf:params:xml:ns:yang:smiv2:UCD-SNMP-MIB";
  prefix "ucd-snmp";

  import SNMPv2-TC {
    prefix "snmpv2-tc";
  }

  import ietf-yang-smiv2 {
    prefix "smiv2";
  }

  import ietf-yang-types {
    prefix "yang";
  }

  organization
   "University of California, Davis";

  contact
   "This mib is no longer being maintained by the University of
    California and is now in life-support-mode and being
    maintained by the net-snmp project.  The best place to write
    for public questions about the net-snmp-coders mailing list
    at net-snmp-coders@lists.sourceforge.net.
    
    postal:   Wes Hardaker
             P.O. Box 382
             Davis CA  95617
    
    email:    net-snmp-coders@lists.sourceforge.net";

  description
   "This file defines the private UCD SNMP MIB extensions.";

  revision 2011-05-14 {
    description
     "New objects for monitoring CPU Steal, Guest and Nice values";
  }

  revision 2009-01-19 {
    description
     "[Revision added by libsmi due to a LAST-UPDATED clause.]";
  }

  revision 2009-01-19 {
    description
     "New 64-bit objects for monitoring large disk usage";
  }

  revision 2006-11-22 {
    description
     "Clarify behaviour of objects in the memory & systemStats groups
      (including updated versions of malnamed mem*Text objects).
      Define suitable TCs to describe error reporting/fix behaviour.";
  }

  revision 2004-04-07 {
    description
     "Added ssCpuRawSoftIRQ for Linux (2.6) and forgotten raw swap counters.";
  }

  revision 2002-09-05 {
    description
     "Deprecate the non-raw objects.";
  }

  revision 2001-09-20 {
    description
     "Group to monitor log files";
  }

  revision 2001-01-17 {
    description
     "Added raw CPU and IO counters.";
  }

  revision 1999-12-09 {
    description
     "SMIv2 version converted from older MIB definitions.";
  }

  typedef UCDErrorFlag {
    type enumeration {
      enum "noError" {
        value "0";
      }
      enum "error" {
        value "1";
      }
    }
    description
     "Represents a possible error condition";
  }

  typedef UCDErrorFix {
    type enumeration {
      enum "noError" {
        value "0";
      }
      enum "runFix" {
        value "1";
      }
    }
    description
     "Represents a 'push-button' object, to invoke a suitable
      configured action.  Will always return 0 when read.";
  }


  container UCD-SNMP-MIB {
    config false;

    container memory {
      smiv2:oid "1.3.6.1.4.1.2021.4";

      leaf memIndex {
        type int32;
        description
         "Bogus Index.  This should always return the integer 0.";
        smiv2:max-access "read-only";
        smiv2:oid "1.3.6.1.4.1.2021.4.1";
      }

      leaf memErrorName {
        type snmpv2-tc:DisplayString;
        description
         "Bogus Name. This should always return the string 'swap'.";
        smiv2:max-access "read-only";
        smiv2:oid "1.3.6.1.4.1.2021.4.2";
      }

      leaf memTotalSwap {
        type int32;
        units "kB";
        description
         "The total amount of swap space configured for this host.";
        smiv2:max-access "read-only";
        smiv2:oid "1.3.6.1.4.1.2021.4.3";
      }

      leaf memAvailSwap {
        type int32;
        units "kB";
        description
         "The amount of swap space currently unused or available.";
        smiv2:max-access "read-only";
        smiv2:oid "1.3.6.1.4.1.2021.4.4";
      }

      leaf memTotalReal {
        type int32;
        units "kB";
        description
         "The total amount of real/physical memory installed
          on this host.";
        smiv2:max-access "read-only";
        smiv2:oid "1.3.6.1.4.1.2021.4.5";
      }

      leaf memAvailReal {
        type int32;
        units "kB";
        description
         "The amount of real/physical memory currently unused
          or available.";
        smiv2:max-access "read-only";
        smiv2:oid "1.3.6.1.4.1.2021.4.6";
      }

      leaf memTotalSwapTXT {
        type int32;
        units "kB";
        description
         "The total amount of swap space or virtual memory allocated
          for text pages on this host.
          
          This object will not be implemented on hosts where the
          underlying operating system does not distinguish text
          pages from other uses of swap space or virtual memory.";
        smiv2:max-access "read-only";
        smiv2:oid "1.3.6.1.4.1.2021.4.7";
      }

      leaf memAvailSwapTXT {
        type int32;
        units "kB";
        status deprecated;
        description
         "The amount of swap space or virtual memory currently
          being used by text pages on this host.
          
          This object will not be implemented on hosts where the
          underlying operating system does not distinguish text
          pages from other uses of swap space or virtual memory.
          
          Note that (despite the name), this value reports the
          amount used, rather than the amount free or available
          for use.  For clarity, this object is being deprecated
          in favour of 'memUsedSwapTXT(16).";
        smiv2:max-access "read-only";
        smiv2:oid "1.3.6.1.4.1.2021.4.8";
      }

      leaf memTotalRealTXT {
        type int32;
        units "kB";
        description
         "The total amount of real/physical memory allocated
          for text pages on this host.
          
          This object will not be implemented on hosts where the
          underlying operating system does not distinguish text
          pages from other uses of physical memory.";
        smiv2:max-access "read-only";
        smiv2:oid "1.3.6.1.4.1.2021.4.9";
      }

      leaf memAvailRealTXT {
        type int32;
        units "kB";
        status deprecated;
        description
         "The amount of real/physical memory currently being
          used by text pages on this host.
          
          This object will not be implemented on hosts where the
          underlying operating system does not distinguish text
          pages from other uses of physical memory.
          
          Note that (despite the name), this value reports the
          amount used, rather than the amount free or available
          for use.  For clarity, this object is being deprecated
          in favour of 'memUsedRealTXT(17).";
        smiv2:max-access "read-only";
        smiv2:oid "1.3.6.1.4.1.2021.4.10";
      }

      leaf memTotalFree {
        type int32;
        units "kB";
        description
         "The total amount of memory free or available for use on
          this host.  This value typically covers both real memory
          and swap space or virtual memory.";
        smiv2:max-access "read-only";
        smiv2:oid "1.3.6.1.4.1.2021.4.11";
      }

      leaf memMinimumSwap {
        type int32;
        units "kB";
        description
         "The minimum amount of swap space expected to be kept
          free or available during normal operation of this host.
          
          If this value (as reported by 'memAvailSwap(4)') falls
          below the specified level, then 'memSwapError(100)' will
          be set to 1 and an error message made available via
          'memSwapErrorMsg(101)'.";
        smiv2:max-access "read-only";
        smiv2:oid "1.3.6.1.4.1.2021.4.12";
      }

      leaf memShared {
        type int32;
        units "kB";
        description
         "The total amount of real or virtual memory currently
          allocated for use as shared memory.
          
          This object will not be implemented on hosts where the
          underlying operating system does not explicitly identify
          memory as specifically reserved for this purpose.";
        smiv2:max-access "read-only";
        smiv2:oid "1.3.6.1.4.1.2021.4.13";
      }

      leaf memBuffer {
        type int32;
        units "kB";
        description
         "The total amount of real or virtual memory currently
          allocated for use as memory buffers.
          
          This object will not be implemented on hosts where the
          underlying operating system does not explicitly identify
          memory as specifically reserved for this purpose.";
        smiv2:max-access "read-only";
        smiv2:oid "1.3.6.1.4.1.2021.4.14";
      }

      leaf memCached {
        type int32;
        units "kB";
        description
         "The total amount of real or virtual memory currently
          allocated for use as cached memory.
          
          This object will not be implemented on hosts where the
          underlying operating system does not explicitly identify
          memory as specifically reserved for this purpose.";
        smiv2:max-access "read-only";
        smiv2:oid "1.3.6.1.4.1.2021.4.15";
      }

      leaf memUsedSwapTXT {
        type int32;
        units "kB";
        description
         "The amount of swap space or virtual memory currently
          being used by text pages on this host.
          
          This object will not be implemented on hosts where the
          underlying operating system does not distinguish text
          pages from other uses of swap space or virtual memory.";
        smiv2:max-access "read-only";
        smiv2:oid "1.3.6.1.4.1.2021.4.16";
      }

      leaf memUsedRealTXT {
        type int32;
        units "kB";
        description
         "The amount of real/physical memory currently being
          used by text pages on this host.
          
          This object will not be implemented on hosts where the
          underlying operating system does not distinguish text
          pages from other uses of physical memory.";
        smiv2:max-access "read-only";
        smiv2:oid "1.3.6.1.4.1.2021.4.17";
      }

      leaf memSwapError {
        type ucd-snmp:UCDErrorFlag;
        description
         "Indicates whether the amount of available swap space
          (as reported by 'memAvailSwap(4)'), is less than the
          desired minimum (specified by 'memMinimumSwap(12)').";
        smiv2:max-access "read-only";
        smiv2:oid "1.3.6.1.4.1.2021.4.100";
      }

      leaf memSwapErrorMsg {
        type snmpv2-tc:DisplayString;
        description
         "Describes whether the amount of available swap space
          (as reported by 'memAvailSwap(4)'), is less than the
          desired minimum (specified by 'memMinimumSwap(12)').";
        smiv2:max-access "read-only";
        smiv2:oid "1.3.6.1.4.1.2021.4.101";
      }
    }

    container systemStats {
      smiv2:oid "1.3.6.1.4.1.2021.11";

      leaf ssIndex {
        type int32;
        description
         "Bogus Index.  This should always return the integer 1.";
        smiv2:max-access "read-only";
        smiv2:oid "1.3.6.1.4.1.2021.11.1";
      }

      leaf ssErrorName {
        type snmpv2-tc:DisplayString;
        description
         "Bogus Name. This should always return the string 'systemStats'.";
        smiv2:max-access "read-only";
        smiv2:oid "1.3.6.1.4.1.2021.11.2";
      }

      leaf ssSwapIn {
        type int32;
        units "kB";
        description
         "The average amount of memory swapped in from disk,
          calculated over the last minute.";
        smiv2:max-access "read-only";
        smiv2:oid "1.3.6.1.4.1.2021.11.3";
      }

      leaf ssSwapOut {
        type int32;
        units "kB";
        description
         "The average amount of memory swapped out to disk,
          calculated over the last minute.";
        smiv2:max-access "read-only";
        smiv2:oid "1.3.6.1.4.1.2021.11.4";
      }

      leaf ssIOSent {
        type int32;
        units "blocks/s";
        status deprecated;
        description
         "The average amount of data written to disk or other
          block device, calculated over the last minute.
          
           This object has been deprecated in favour of
          'ssIORawSent(57)', which can be used to calculate
          the same metric, but over any desired time period.";
        smiv2:max-access "read-only";
        smiv2:oid "1.3.6.1.4.1.2021.11.5";
      }

      leaf ssIOReceive {
        type int32;
        units "blocks/s";
        status deprecated;
        description
         "The average amount of data read from disk or other
          block device, calculated over the last minute.
          
           This object has been deprecated in favour of
          'ssIORawReceived(58)', which can be used to calculate
          the same metric, but over any desired time period.";
        smiv2:max-access "read-only";
        smiv2:oid "1.3.6.1.4.1.2021.11.6";
      }

      leaf ssSysInterrupts {
        type int32;
        units "interrupts/s";
        status deprecated;
        description
         "The average rate of interrupts processed (including
          the clock) calculated over the last minute.
          
           This object has been deprecated in favour of
          'ssRawInterrupts(59)', which can be used to calculate
          the same metric, but over any desired time period.";
        smiv2:max-access "read-only";
        smiv2:oid "1.3.6.1.4.1.2021.11.7";
      }

      leaf ssSysContext {
        type int32;
        units "switches/s";
        status deprecated;
        description
         "The average rate of context switches,
          calculated over the last minute.
          
           This object has been deprecated in favour of
          'ssRawContext(60)', which can be used to calculate
          the same metric, but over any desired time period.";
        smiv2:max-access "read-only";
        smiv2:oid "1.3.6.1.4.1.2021.11.8";
      }

      leaf ssCpuUser {
        type int32;
        status deprecated;
        description
         "The percentage of CPU time spent processing
          user-level code, calculated over the last minute.
          
           This object has been deprecated in favour of
          'ssCpuRawUser(50)', which can be used to calculate
          the same metric, but over any desired time period.";
        smiv2:max-access "read-only";
        smiv2:oid "1.3.6.1.4.1.2021.11.9";
      }

      leaf ssCpuSystem {
        type int32;
        status deprecated;
        description
         "The percentage of CPU time spent processing
          system-level code, calculated over the last minute.
          
           This object has been deprecated in favour of
          'ssCpuRawSystem(52)', which can be used to calculate
          the same metric, but over any desired time period.";
        smiv2:max-access "read-only";
        smiv2:oid "1.3.6.1.4.1.2021.11.10";
      }

      leaf ssCpuIdle {
        type int32;
        status deprecated;
        description
         "The percentage of processor time spent idle,
          calculated over the last minute.
          
           This object has been deprecated in favour of
          'ssCpuRawIdle(53)', which can be used to calculate
          the same metric, but over any desired time period.";
        smiv2:max-access "read-only";
        smiv2:oid "1.3.6.1.4.1.2021.11.11";
      }

      leaf ssCpuRawUser {
        type yang:counter32;
        description
         "The number of 'ticks' (typically 1/100s) spent
          processing user-level code.
          
          On a multi-processor system, the 'ssCpuRaw*'
          counters are cumulative over all CPUs, so their
          sum will typically be N*100 (for N processors).";
        smiv2:max-access "read-only";
        smiv2:oid "1.3.6.1.4.1.2021.11.50";
      }

      leaf ssCpuRawNice {
        type yang:counter32;
        description
         "The number of 'ticks' (typically 1/100s) spent
          processing reduced-priority code.
          
          This object will not be implemented on hosts where
          the underlying operating system does not measure
          this particular CPU metric.
          
          On a multi-processor system, the 'ssCpuRaw*'
          counters are cumulative over all CPUs, so their
          sum will typically be N*100 (for N processors).";
        smiv2:max-access "read-only";
        smiv2:oid "1.3.6.1.4.1.2021.11.51";
      }

      leaf ssCpuRawSystem {
        type yang:counter32;
        description
         "The number of 'ticks' (typically 1/100s) spent
          processing system-level code.
          
          On a multi-processor system, the 'ssCpuRaw*'
          counters are cumulative over all CPUs, so their
          sum will typically be N*100 (for N processors).
          
          This object may sometimes be implemented as the
          combination of the 'ssCpuRawWait(54)' and
          'ssCpuRawKernel(55)' counters, so care must be
          taken when summing the overall raw counters.";
        smiv2:max-access "read-only";
        smiv2:oid "1.3.6.1.4.1.2021.11.52";
      }

      leaf ssCpuRawIdle {
        type yang:counter32;
        description
         "The number of 'ticks' (typically 1/100s) spent
          idle.
          
          On a multi-processor system, the 'ssCpuRaw*'
          counters are cumulative over all CPUs, so their
          sum will typically be N*100 (for N processors).";
        smiv2:max-access "read-only";
        smiv2:oid "1.3.6.1.4.1.2021.11.53";
      }

      leaf ssCpuRawWait {
        type yang:counter32;
        description
         "The number of 'ticks' (typically 1/100s) spent
          waiting for IO.
          
          This object will not be implemented on hosts where
          the underlying operating system does not measure
          this particular CPU metric.  This time may also be
          included within the 'ssCpuRawSystem(52)' counter.
          
          On a multi-processor system, the 'ssCpuRaw*'
          counters are cumulative over all CPUs, so their
          sum will typically be N*100 (for N processors).";
        smiv2:max-access "read-only";
        smiv2:oid "1.3.6.1.4.1.2021.11.54";
      }

      leaf ssCpuRawKernel {
        type yang:counter32;
        description
         "The number of 'ticks' (typically 1/100s) spent
          processing kernel-level code.
          
          This object will not be implemented on hosts where
          the underlying operating system does not measure
          this particular CPU metric.  This time may also be
          included within the 'ssCpuRawSystem(52)' counter.
          
          On a multi-processor system, the 'ssCpuRaw*'
          counters are cumulative over all CPUs, so their
          sum will typically be N*100 (for N processors).";
        smiv2:max-access "read-only";
        smiv2:oid "1.3.6.1.4.1.2021.11.55";
      }

      leaf ssCpuRawInterrupt {
        type yang:counter32;
        description
         "The number of 'ticks' (typically 1/100s) spent
          processing hardware interrupts.
          
          This object will not be implemented on hosts where
          the underlying operating system does not measure
          this particular CPU metric.
          
          On a multi-processor system, the 'ssCpuRaw*'
          counters are cumulative over all CPUs, so their
          sum will typically be N*100 (for N processors).";
        smiv2:max-access "read-only";
        smiv2:oid "1.3.6.1.4.1.2021.11.56";
      }

      leaf ssIORawSent {
        type yang:counter32;
        description
         "Number of blocks sent to a block device";
        smiv2:max-access "read-only";
        smiv2:oid "1.3.6.1.4.1.2021.11.57";
      }

      leaf ssIORawReceived {
        type yang:counter32;
        description
         "Number of blocks received from a block device";
        smiv2:max-access "read-only";
        smiv2:oid "1.3.6.1.4.1.2021.11.58";
      }

      leaf ssRawInterrupts {
        type yang:counter32;
        description
         "Number of interrupts processed";
        smiv2:max-access "read-only";
        smiv2:oid "1.3.6.1.4.1.2021.11.59";
      }

      leaf ssRawContexts {
        type yang:counter32;
        description
         "Number of context switches";
        smiv2:max-access "read-only";
        smiv2:oid "1.3.6.1.4.1.2021.11.60";
      }

      leaf ssCpuRawSoftIRQ {
        type yang:counter32;
        description
         "The number of 'ticks' (typically 1/100s) spent
          processing software interrupts.
          
          This object will not be implemented on hosts where
          the underlying operating system does not measure
          this particular CPU metric.
          
          On a multi-processor system, the 'ssCpuRaw*'
          counters are cumulative over all CPUs, so their
          sum will typically be N*100 (for N processors).";
        smiv2:max-access "read-only";
        smiv2:oid "1.3.6.1.4.1.2021.11.61";
      }

      leaf ssRawSwapIn {
        type yang:counter32;
        description
         "Number of blocks swapped in";
        smiv2:max-access "read-only";
        smiv2:oid "1.3.6.1.4.1.2021.11.62";
      }

      leaf ssRawSwapOut {
        type yang:counter32;
        description
         "Number of blocks swapped out";
        smiv2:max-access "read-only";
        smiv2:oid "1.3.6.1.4.1.2021.11.63";
      }

      leaf ssCpuRawSteal {
        type yang:counter32;
        description
         "The number of 'ticks' (typically 1/100s) spent
          by the hypervisor code to run other VMs even
          though the CPU in the current VM had something runnable.
          
          This object will not be implemented on hosts where
          the underlying operating system does not measure
          this particular CPU metric.
          
          On a multi-processor system, the 'ssCpuRaw*'
          counters are cumulative over all CPUs, so their
          sum will typically be N*100 (for N processors).";
        smiv2:max-access "read-only";
        smiv2:oid "1.3.6.1.4.1.2021.11.64";
      }

      leaf ssCpuRawGuest {
        type yang:counter32;
        description
         "The number of 'ticks' (typically 1/100s) spent
          by the CPU to run a virtual CPU (guest).
          
          This object will not be implemented on hosts where
          the underlying operating system does not measure
          this particular CPU metric.
          
          On a multi-processor system, the 'ssCpuRaw*'
          counters are cumulative over all CPUs, so their
          sum will typically be N*100 (for N processors).";
        smiv2:max-access "read-only";
        smiv2:oid "1.3.6.1.4.1.2021.11.65";
      }

      leaf ssCpuRawGuestNice {
        type yang:counter32;
        description
         "The number of 'ticks' (typically 1/100s) spent
          by the CPU to run a niced virtual CPU (guest).
          
          This object will not be implemented on hosts where
          the underlying operating system does not measure
          this particular CPU metric.
          
          On a multi-processor system, the 'ssCpuRaw*'
          counters are cumulative over all CPUs, so their
          sum will typically be N*100 (for N processors).";
        smiv2:max-access "read-only";
        smiv2:oid "1.3.6.1.4.1.2021.11.66";
      }
    }

    container logMatch {
      smiv2:oid "1.3.6.1.4.1.2021.16";

      leaf logMatchMaxEntries {
        type int32;
        description
         "The maximum number of logmatch entries
          this snmpd daemon can support.";
        smiv2:max-access "read-only";
        smiv2:oid "1.3.6.1.4.1.2021.16.1";
      }
    }

    container version {
      smiv2:oid "1.3.6.1.4.1.2021.100";

      leaf versionIndex {
        type int32;
        description
         "Index to mib (always 0)";
        smiv2:max-access "read-only";
        smiv2:oid "1.3.6.1.4.1.2021.100.1";
      }

      leaf versionTag {
        type snmpv2-tc:DisplayString;
        description
         "CVS tag keyword";
        smiv2:max-access "read-only";
        smiv2:oid "1.3.6.1.4.1.2021.100.2";
      }

      leaf versionDate {
        type snmpv2-tc:DisplayString;
        description
         "Date string from RCS keyword";
        smiv2:max-access "read-only";
        smiv2:oid "1.3.6.1.4.1.2021.100.3";
      }

      leaf versionCDate {
        type snmpv2-tc:DisplayString;
        description
         "Date string from ctime() ";
        smiv2:max-access "read-only";
        smiv2:oid "1.3.6.1.4.1.2021.100.4";
      }

      leaf versionIdent {
        type snmpv2-tc:DisplayString;
        description
         "Id string from RCS keyword";
        smiv2:max-access "read-only";
        smiv2:oid "1.3.6.1.4.1.2021.100.5";
      }

      leaf versionClearCache {
        type int32;
        description
         "Set to 1 to clear the exec cache, if enabled";
        smiv2:max-access "read-write";
        smiv2:oid "1.3.6.1.4.1.2021.100.10";
      }

      leaf versionUpdateConfig {
        type int32;
        description
         "Set to 1 to read-read the config file(s).";
        smiv2:max-access "read-write";
        smiv2:oid "1.3.6.1.4.1.2021.100.11";
      }

      leaf versionRestartAgent {
        type int32;
        description
         "Set to 1 to restart the agent.";
        smiv2:max-access "read-write";
        smiv2:oid "1.3.6.1.4.1.2021.100.12";
      }

      leaf versionSavePersistentData {
        type int32;
        description
         "Set to 1 to force the agent to save it's persistent data immediately.";
        smiv2:max-access "read-write";
        smiv2:oid "1.3.6.1.4.1.2021.100.13";
      }

      leaf versionDoDebugging {
        type int32;
        description
         "Set to 1 to turn debugging statements on in the agent or 0
          to turn it off.";
        smiv2:max-access "read-write";
        smiv2:oid "1.3.6.1.4.1.2021.100.20";
      }
    }

    container snmperrs {
      smiv2:oid "1.3.6.1.4.1.2021.101";

      leaf snmperrIndex {
        type int32;
        description
         "Bogus Index for snmperrs (always 0).";
        smiv2:max-access "read-only";
        smiv2:oid "1.3.6.1.4.1.2021.101.1";
      }

      leaf snmperrNames {
        type snmpv2-tc:DisplayString;
        description
         "snmp";
        smiv2:max-access "read-only";
        smiv2:oid "1.3.6.1.4.1.2021.101.2";
      }

      leaf snmperrErrorFlag {
        type ucd-snmp:UCDErrorFlag;
        description
         "A Error flag to indicate trouble with the agent.  It
          goes to 1 if there is an error, 0 if no error.";
        smiv2:max-access "read-only";
        smiv2:oid "1.3.6.1.4.1.2021.101.100";
      }

      leaf snmperrErrMessage {
        type snmpv2-tc:DisplayString;
        description
         "An error message describing the problem (if one exists).";
        smiv2:max-access "read-only";
        smiv2:oid "1.3.6.1.4.1.2021.101.101";
      }
    }

    container prTable {
      description
       "A table containing information on running
        programs/daemons configured for monitoring in the
        snmpd.conf file of the agent.  Processes violating the
        number of running processes required by the agent's
        configuration file are flagged with numerical and
        textual errors.";
      smiv2:oid "1.3.6.1.4.1.2021.2";

      list prEntry {
        key "prIndex";
        description
         "An entry containing a process and its statistics.";
        smiv2:oid "1.3.6.1.4.1.2021.2.1";

        leaf prIndex {
          type int32 {
            range "0..65535";
          }
          description
           "Reference Index for each observed process.";
          smiv2:max-access "read-only";
          smiv2:oid "1.3.6.1.4.1.2021.2.1.1";
        }

        leaf prNames {
          type snmpv2-tc:DisplayString;
          description
           "The process name we're counting/checking on.";
          smiv2:max-access "read-only";
          smiv2:oid "1.3.6.1.4.1.2021.2.1.2";
        }

        leaf prMin {
          type int32;
          description
           "The minimum number of processes that should be
            running.  An error flag is generated if the number of
            running processes is < the minimum.";
          smiv2:max-access "read-only";
          smiv2:oid "1.3.6.1.4.1.2021.2.1.3";
        }

        leaf prMax {
          type int32;
          description
           "The maximum number of processes that should be
            running.  An error flag is generated if the number of
            running processes is > the maximum.";
          smiv2:max-access "read-only";
          smiv2:oid "1.3.6.1.4.1.2021.2.1.4";
        }

        leaf prCount {
          type int32;
          description
           "The number of current processes running with the name
            in question.";
          smiv2:max-access "read-only";
          smiv2:oid "1.3.6.1.4.1.2021.2.1.5";
        }

        leaf prErrorFlag {
          type ucd-snmp:UCDErrorFlag;
          description
           "A Error flag to indicate trouble with a process.  It
            goes to 1 if there is an error, 0 if no error.";
          smiv2:max-access "read-only";
          smiv2:oid "1.3.6.1.4.1.2021.2.1.100";
        }

        leaf prErrMessage {
          type snmpv2-tc:DisplayString;
          description
           "An error message describing the problem (if one exists).";
          smiv2:max-access "read-only";
          smiv2:oid "1.3.6.1.4.1.2021.2.1.101";
        }

        leaf prErrFix {
          type ucd-snmp:UCDErrorFix;
          description
           "Setting this to one will try to fix the problem if
            the agent has been configured with a script to call
            to attempt to fix problems automatically using remote
            snmp operations.";
          smiv2:max-access "read-write";
          smiv2:oid "1.3.6.1.4.1.2021.2.1.102";
        }

        leaf prErrFixCmd {
          type snmpv2-tc:DisplayString;
          description
           "The command that gets run when the prErrFix column is 
            set to 1.";
          smiv2:max-access "read-only";
          smiv2:oid "1.3.6.1.4.1.2021.2.1.103";
        }
      }
    }

    container extTable {
      description
       "A table of extensible commands returning output and
        result codes.  These commands are configured via the
        agent's snmpd.conf file.";
      smiv2:oid "1.3.6.1.4.1.2021.8";

      list extEntry {
        key "extIndex";
        description
         "An entry containing an extensible script/program and its output.";
        smiv2:oid "1.3.6.1.4.1.2021.8.1";

        leaf extIndex {
          type int32 {
            range "0..65535";
          }
          description
           "Reference Index for extensible scripts.  Simply an
            integer row number.";
          smiv2:max-access "read-only";
          smiv2:oid "1.3.6.1.4.1.2021.8.1.1";
        }

        leaf extNames {
          type snmpv2-tc:DisplayString;
          description
           "A Short, one name description of the extensible command.";
          smiv2:max-access "read-only";
          smiv2:oid "1.3.6.1.4.1.2021.8.1.2";
        }

        leaf extCommand {
          type snmpv2-tc:DisplayString;
          description
           "The command line to be executed.";
          smiv2:max-access "read-only";
          smiv2:oid "1.3.6.1.4.1.2021.8.1.3";
        }

        leaf extResult {
          type int32;
          description
           "The result code (exit status) from the executed command.";
          smiv2:max-access "read-only";
          smiv2:oid "1.3.6.1.4.1.2021.8.1.100";
        }

        leaf extOutput {
          type snmpv2-tc:DisplayString;
          description
           "The first line of output of the executed command.";
          smiv2:max-access "read-only";
          smiv2:oid "1.3.6.1.4.1.2021.8.1.101";
        }

        leaf extErrFix {
          type ucd-snmp:UCDErrorFix;
          description
           "Setting this to one will try to fix the problem if
            the agent has been configured with a script to call
            to attempt to fix problems automatically using remote
            snmp operations.";
          smiv2:max-access "read-write";
          smiv2:oid "1.3.6.1.4.1.2021.8.1.102";
        }

        leaf extErrFixCmd {
          type snmpv2-tc:DisplayString;
          description
           "The command that gets run when the extErrFix column is 
            set to 1.";
          smiv2:max-access "read-only";
          smiv2:oid "1.3.6.1.4.1.2021.8.1.103";
        }
      }
    }

    container dskTable {
      description
       "Disk watching information.  Partions to be watched
        are configured by the snmpd.conf file of the agent.";
      smiv2:oid "1.3.6.1.4.1.2021.9";

      list dskEntry {
        key "dskIndex";
        description
         "An entry containing a disk and its statistics.";
        smiv2:oid "1.3.6.1.4.1.2021.9.1";

        leaf dskIndex {
          type int32 {
            range "0..65535";
          }
          description
           "Integer reference number (row number) for the disk mib.";
          smiv2:max-access "read-only";
          smiv2:oid "1.3.6.1.4.1.2021.9.1.1";
        }

        leaf dskPath {
          type snmpv2-tc:DisplayString;
          description
           "Path where the disk is mounted.";
          smiv2:max-access "read-only";
          smiv2:oid "1.3.6.1.4.1.2021.9.1.2";
        }

        leaf dskDevice {
          type snmpv2-tc:DisplayString;
          description
           "Path of the device for the partition";
          smiv2:max-access "read-only";
          smiv2:oid "1.3.6.1.4.1.2021.9.1.3";
        }

        leaf dskMinimum {
          type int32;
          description
           "Minimum space required on the disk (in kBytes) before the
            errors are triggered.  Either this or dskMinPercent is
            configured via the agent's snmpd.conf file.";
          smiv2:max-access "read-only";
          smiv2:oid "1.3.6.1.4.1.2021.9.1.4";
        }

        leaf dskMinPercent {
          type int32;
          description
           "Percentage of minimum space required on the disk before the
            errors are triggered.  Either this or dskMinimum is
            configured via the agent's snmpd.conf file.";
          smiv2:max-access "read-only";
          smiv2:oid "1.3.6.1.4.1.2021.9.1.5";
        }

        leaf dskTotal {
          type int32;
          description
           "Total size of the disk/partion (kBytes).
            For large disks (>2Tb), this value will
            latch at INT32_MAX (2147483647).";
          smiv2:max-access "read-only";
          smiv2:oid "1.3.6.1.4.1.2021.9.1.6";
        }

        leaf dskAvail {
          type int32;
          description
           "Available space on the disk.
            For large lightly-used disks (>2Tb), this
            value will latch at INT32_MAX (2147483647).";
          smiv2:max-access "read-only";
          smiv2:oid "1.3.6.1.4.1.2021.9.1.7";
        }

        leaf dskUsed {
          type int32;
          description
           "Used space on the disk.
            For large heavily-used disks (>2Tb), this
            value will latch at INT32_MAX (2147483647).";
          smiv2:max-access "read-only";
          smiv2:oid "1.3.6.1.4.1.2021.9.1.8";
        }

        leaf dskPercent {
          type int32;
          description
           "Percentage of space used on disk";
          smiv2:max-access "read-only";
          smiv2:oid "1.3.6.1.4.1.2021.9.1.9";
        }

        leaf dskPercentNode {
          type int32;
          description
           "Percentage of inodes used on disk";
          smiv2:max-access "read-only";
          smiv2:oid "1.3.6.1.4.1.2021.9.1.10";
        }

        leaf dskTotalLow {
          type uint32;
          description
           "Total size of the disk/partion (kBytes).
            Together with dskTotalHigh composes 64-bit number.";
          smiv2:max-access "read-only";
          smiv2:oid "1.3.6.1.4.1.2021.9.1.11";
        }

        leaf dskTotalHigh {
          type uint32;
          description
           "Total size of the disk/partion (kBytes).
            Together with dskTotalLow composes 64-bit number.";
          smiv2:max-access "read-only";
          smiv2:oid "1.3.6.1.4.1.2021.9.1.12";
        }

        leaf dskAvailLow {
          type uint32;
          description
           "Available space on the disk (kBytes).
            Together with dskAvailHigh composes 64-bit number.";
          smiv2:max-access "read-only";
          smiv2:oid "1.3.6.1.4.1.2021.9.1.13";
        }

        leaf dskAvailHigh {
          type uint32;
          description
           "Available space on the disk (kBytes).
            Together with dskAvailLow composes 64-bit number.";
          smiv2:max-access "read-only";
          smiv2:oid "1.3.6.1.4.1.2021.9.1.14";
        }

        leaf dskUsedLow {
          type uint32;
          description
           "Used space on the disk (kBytes).
            Together with dskUsedHigh composes 64-bit number.";
          smiv2:max-access "read-only";
          smiv2:oid "1.3.6.1.4.1.2021.9.1.15";
        }

        leaf dskUsedHigh {
          type uint32;
          description
           "Used space on the disk (kBytes).
            Together with dskUsedLow composes 64-bit number.";
          smiv2:max-access "read-only";
          smiv2:oid "1.3.6.1.4.1.2021.9.1.16";
        }

        leaf dskErrorFlag {
          type ucd-snmp:UCDErrorFlag;
          description
           "Error flag signaling that the disk or partition is under
            the minimum required space configured for it.";
          smiv2:max-access "read-only";
          smiv2:oid "1.3.6.1.4.1.2021.9.1.100";
        }

        leaf dskErrorMsg {
          type snmpv2-tc:DisplayString;
          description
           "A text description providing a warning and the space left
            on the disk.";
          smiv2:max-access "read-only";
          smiv2:oid "1.3.6.1.4.1.2021.9.1.101";
        }
      }
    }

    container laTable {
      description
       "Load average information.";
      smiv2:oid "1.3.6.1.4.1.2021.10";

      list laEntry {
        key "laIndex";
        description
         "An entry containing a load average and its values.";
        smiv2:oid "1.3.6.1.4.1.2021.10.1";

        leaf laIndex {
          type int32 {
            range "0..3";
          }
          description
           "reference index/row number for each observed loadave.";
          smiv2:max-access "read-only";
          smiv2:oid "1.3.6.1.4.1.2021.10.1.1";
        }

        leaf laNames {
          type snmpv2-tc:DisplayString;
          description
           "The list of loadave names we're watching.";
          smiv2:max-access "read-only";
          smiv2:oid "1.3.6.1.4.1.2021.10.1.2";
        }

        leaf laLoad {
          type snmpv2-tc:DisplayString;
          description
           "The 1,5 and 15 minute load averages (one per row).";
          smiv2:max-access "read-only";
          smiv2:oid "1.3.6.1.4.1.2021.10.1.3";
        }

        leaf laConfig {
          type snmpv2-tc:DisplayString;
          description
           "The watch point for load-averages to signal an
            error.  If the load averages rises above this value,
            the laErrorFlag below is set.";
          smiv2:max-access "read-write";
          smiv2:oid "1.3.6.1.4.1.2021.10.1.4";
        }

        leaf laLoadInt {
          type int32;
          description
           "The 1,5 and 15 minute load averages as an integer.
            This is computed by taking the floating point
            loadaverage value and multiplying by 100, then
            converting the value to an integer.";
          smiv2:max-access "read-only";
          smiv2:oid "1.3.6.1.4.1.2021.10.1.5";
        }

        leaf laErrorFlag {
          type ucd-snmp:UCDErrorFlag;
          description
           "A Error flag to indicate the load-average has crossed
            its threshold value defined in the snmpd.conf file.
            It is set to 1 if the threshold is crossed, 0 otherwise.";
          smiv2:max-access "read-only";
          smiv2:oid "1.3.6.1.4.1.2021.10.1.100";
        }

        leaf laErrMessage {
          type snmpv2-tc:DisplayString;
          description
           "An error message describing the load-average and its
            surpased watch-point value.";
          smiv2:max-access "read-only";
          smiv2:oid "1.3.6.1.4.1.2021.10.1.101";
        }
      }
    }

    container fileTable {
      description
       "Table of monitored files.";
      smiv2:oid "1.3.6.1.4.1.2021.15";

      list fileEntry {
        key "fileIndex";
        description
         "Entry of file";
        smiv2:oid "1.3.6.1.4.1.2021.15.1";

        leaf fileIndex {
          type int32 {
            range "0..2147483647";
          }
          description
           "Index of file";
          smiv2:max-access "read-only";
          smiv2:oid "1.3.6.1.4.1.2021.15.1.1";
        }

        leaf fileName {
          type snmpv2-tc:DisplayString;
          description
           "Filename";
          smiv2:max-access "read-only";
          smiv2:oid "1.3.6.1.4.1.2021.15.1.2";
        }

        leaf fileSize {
          type int32;
          units "kB";
          description
           "Size of file (kB)";
          smiv2:max-access "read-only";
          smiv2:oid "1.3.6.1.4.1.2021.15.1.3";
        }

        leaf fileMax {
          type int32;
          units "kB";
          description
           "Limit of filesize (kB)";
          smiv2:max-access "read-only";
          smiv2:oid "1.3.6.1.4.1.2021.15.1.4";
        }

        leaf fileErrorFlag {
          type ucd-snmp:UCDErrorFlag;
          description
           "Limit exceeded flag";
          smiv2:max-access "read-only";
          smiv2:oid "1.3.6.1.4.1.2021.15.1.100";
        }

        leaf fileErrorMsg {
          type snmpv2-tc:DisplayString;
          description
           "Filesize error message";
          smiv2:max-access "read-only";
          smiv2:oid "1.3.6.1.4.1.2021.15.1.101";
        }
      }
    }

    container logMatchTable {
      description
       "Table of monitored files.";
      smiv2:oid "1.3.6.1.4.1.2021.16.2";

      list logMatchEntry {
        key "logMatchIndex";
        description
         "Entry of file";
        smiv2:oid "1.3.6.1.4.1.2021.16.2.1";

        leaf logMatchIndex {
          type int32 {
            range "1..2147483647";
          }
          description
           "Index of logmatch";
          smiv2:max-access "read-only";
          smiv2:oid "1.3.6.1.4.1.2021.16.2.1.1";
        }

        leaf logMatchName {
          type snmpv2-tc:DisplayString;
          description
           "logmatch instance name";
          smiv2:max-access "read-only";
          smiv2:oid "1.3.6.1.4.1.2021.16.2.1.2";
        }

        leaf logMatchFilename {
          type snmpv2-tc:DisplayString;
          description
           "filename to be logmatched";
          smiv2:max-access "read-only";
          smiv2:oid "1.3.6.1.4.1.2021.16.2.1.3";
        }

        leaf logMatchRegEx {
          type snmpv2-tc:DisplayString;
          description
           "regular expression";
          smiv2:max-access "read-only";
          smiv2:oid "1.3.6.1.4.1.2021.16.2.1.4";
        }

        leaf logMatchGlobalCounter {
          type yang:counter32;
          description
           "global count of matches";
          smiv2:max-access "read-only";
          smiv2:oid "1.3.6.1.4.1.2021.16.2.1.5";
        }

        leaf logMatchGlobalCount {
          type int32;
          description
           "Description.";
          smiv2:max-access "read-only";
          smiv2:oid "1.3.6.1.4.1.2021.16.2.1.6";
        }

        leaf logMatchCurrentCounter {
          type yang:counter32;
          description
           "Regex match counter. This counter will
            be reset with each logfile rotation.";
          smiv2:max-access "read-only";
          smiv2:oid "1.3.6.1.4.1.2021.16.2.1.7";
        }

        leaf logMatchCurrentCount {
          type int32;
          description
           "Description.";
          smiv2:max-access "read-only";
          smiv2:oid "1.3.6.1.4.1.2021.16.2.1.8";
        }

        leaf logMatchCounter {
          type yang:counter32;
          description
           "Regex match counter. This counter will
            be reset with each read";
          smiv2:max-access "read-only";
          smiv2:oid "1.3.6.1.4.1.2021.16.2.1.9";
        }

        leaf logMatchCount {
          type int32;
          description
           "Description.";
          smiv2:max-access "read-only";
          smiv2:oid "1.3.6.1.4.1.2021.16.2.1.10";
        }

        leaf logMatchCycle {
          type int32;
          description
           "time between updates (if not queried) in seconds";
          smiv2:max-access "read-only";
          smiv2:oid "1.3.6.1.4.1.2021.16.2.1.11";
        }

        leaf logMatchErrorFlag {
          type ucd-snmp:UCDErrorFlag;
          description
           "errorflag: is this line configured correctly?";
          smiv2:max-access "read-only";
          smiv2:oid "1.3.6.1.4.1.2021.16.2.1.100";
        }

        leaf logMatchRegExCompilation {
          type snmpv2-tc:DisplayString;
          description
           "message of regex precompilation";
          smiv2:max-access "read-only";
          smiv2:oid "1.3.6.1.4.1.2021.16.2.1.101";
        }
      }
    }

    container mrTable {
      description
       "A table displaying all the oid's registered by mib modules in
        the agent.  Since the agent is modular in nature, this lists
        each module's OID it is responsible for and the name of the module";
      smiv2:oid "1.3.6.1.4.1.2021.102";

      list mrEntry {
        key "mrIndex";
        smiv2:implied "mrIndex";
        description
         "An entry containing a registered mib oid.";
        smiv2:oid "1.3.6.1.4.1.2021.102.1";

        leaf mrIndex {
          type yang:object-identifier-128;
          description
           "The registry slot of a mibmodule.";
          smiv2:max-access "read-only";
          smiv2:oid "1.3.6.1.4.1.2021.102.1.1";
        }

        leaf mrModuleName {
          type snmpv2-tc:DisplayString;
          description
           "The module name that registered this OID.";
          smiv2:max-access "read-only";
          smiv2:oid "1.3.6.1.4.1.2021.102.1.2";
        }
      }
    }
  }

  notification ucdStart {
    description
     "This trap could in principle be sent when the agent start";
    smiv2:oid "1.3.6.1.4.1.2021.251.1";
  }

  notification ucdShutdown {
    description
     "This trap is sent when the agent terminates";
    smiv2:oid "1.3.6.1.4.1.2021.251.2";
  }

  smiv2:alias "ucdavis" {
    smiv2:oid "1.3.6.1.4.1.2021";
  }

  smiv2:alias "memory" {
    smiv2:oid "1.3.6.1.4.1.2021.4";
  }

  smiv2:alias "systemStats" {
    smiv2:oid "1.3.6.1.4.1.2021.11";
  }

  smiv2:alias "ucdInternal" {
    smiv2:oid "1.3.6.1.4.1.2021.12";
  }

  smiv2:alias "ucdExperimental" {
    smiv2:oid "1.3.6.1.4.1.2021.13";
  }

  smiv2:alias "logMatch" {
    smiv2:oid "1.3.6.1.4.1.2021.16";
  }

  smiv2:alias "version" {
    smiv2:oid "1.3.6.1.4.1.2021.100";
  }

  smiv2:alias "snmperrs" {
    smiv2:oid "1.3.6.1.4.1.2021.101";
  }

  smiv2:alias "ucdSnmpAgent" {
    smiv2:oid "1.3.6.1.4.1.2021.250";
  }

  smiv2:alias "hpux9" {
    smiv2:oid "1.3.6.1.4.1.2021.250.1";
  }

  smiv2:alias "sunos4" {
    smiv2:oid "1.3.6.1.4.1.2021.250.2";
  }

  smiv2:alias "solaris" {
    smiv2:oid "1.3.6.1.4.1.2021.250.3";
  }

  smiv2:alias "osf" {
    smiv2:oid "1.3.6.1.4.1.2021.250.4";
  }

  smiv2:alias "ultrix" {
    smiv2:oid "1.3.6.1.4.1.2021.250.5";
  }

  smiv2:alias "hpux10" {
    smiv2:oid "1.3.6.1.4.1.2021.250.6";
  }

  smiv2:alias "netbsd1" {
    smiv2:oid "1.3.6.1.4.1.2021.250.7";
  }

  smiv2:alias "freebsd" {
    smiv2:oid "1.3.6.1.4.1.2021.250.8";
  }

  smiv2:alias "irix" {
    smiv2:oid "1.3.6.1.4.1.2021.250.9";
  }

  smiv2:alias "linux" {
    smiv2:oid "1.3.6.1.4.1.2021.250.10";
  }

  smiv2:alias "bsdi" {
    smiv2:oid "1.3.6.1.4.1.2021.250.11";
  }

  smiv2:alias "openbsd" {
    smiv2:oid "1.3.6.1.4.1.2021.250.12";
  }

  smiv2:alias "win32" {
    smiv2:oid "1.3.6.1.4.1.2021.250.13";
  }

  smiv2:alias "hpux11" {
    smiv2:oid "1.3.6.1.4.1.2021.250.14";
  }

  smiv2:alias "aix" {
    smiv2:oid "1.3.6.1.4.1.2021.250.15";
  }

  smiv2:alias "macosx" {
    smiv2:oid "1.3.6.1.4.1.2021.250.16";
  }

  smiv2:alias "dragonfly" {
    smiv2:oid "1.3.6.1.4.1.2021.250.17";
  }

  smiv2:alias "unknown" {
    smiv2:oid "1.3.6.1.4.1.2021.250.255";
  }

  smiv2:alias "ucdTraps" {
    smiv2:oid "1.3.6.1.4.1.2021.251";
  }

}
