module arcos-te {
  yang-version 1.1;
  namespace "http://yang.arrcus.com/arcos/arcos-te";
  prefix "arc-te";

  import openconfig-network-instance {
    prefix oc-netinst;
  }
  import arcos-te-types {
    prefix arc-te-types;
  }

  organization "Arrcus, Inc";

  contact
    "Arrcus, Inc.
     2077 Gateway Place
     Suite 400
     San Jose, CA 95110

     E-mail: yang-support@arrcus.com";

  description
    "This module defines configuration and state information
     for Traffic Engineering (TE).

     Copyright (c) 2022 by Arrcus, Inc.
     All rights reserved.";

  revision "2025-07-31" {
    description
      "Restrict admin-group bit position to 0-255.";
  }
  revision "2025-01-10" {
    description
      "Update maximum srlg groups to 30.";
  }

  revision "2024-08-09" {
    description
      "Put defaults and tighter restrictions on SRLG config";
  }
  revision "2022-02-24" {
    description
      "Initial version.";
  }


  /*
   * TE SRLGs
   */
  grouping te-srlg-config {
    description
      "Grouping for srlg.";

    leaf name {
      type string {
        length "0..64";
      }
      description
        "A string name that uniquely identifies a TE
         interface named SRLG.";
    }

    leaf value {
      type uint32;
      mandatory true;
      description
        "An SRLG value.";
      reference
        "RFC 4203: OSPF Extensions in Support of Generalized
                   Multi-Protocol Label Switching (GMPLS)
         RFC 5307: IS-IS Extensions in Support of Generalized
                  Multi-Protocol Label Switching (GMPLS)";
    }

    leaf cost {
      type uint32 {
        range "0..16777215";
      }
      default 1000;
      description
        "SRLG associated cost. Used during path to append
         the path cost when traversing a link with this
         SRLG.";
    }
  }

  grouping te-srlg-structure {
    description
      "This grouping defines TE SRLG structure.";

    container srlgs {
      description
        "Named SRLGs container.";

      list srlg {
        key "name";
        unique config/value;
        description
          "A list of named SRLG groups.";
        max-elements 30;

        leaf name {
          type leafref {
            path "../config/name";
          }
        }

        container config {
          description
            "Container for SRLG configuration.";

          uses te-srlg-config;
        }

        container state {
          config false;
          description
            "Container for SRLS state data.";

          uses te-srlg-config;
        }
      }
    }
  }

  grouping te-srlg-oper-structure {
    description
      "This grouping defines TE SRLG structure for oper only.";

    container srlgs {
      config false;
      description
        "Named SRLGs container.";

      list srlg {
        key "name";
        description
          "A list of named SRLG groups.";

        leaf name {
          type leafref {
            path "../state/name";
          }
        }

        container state {
          description
            "Container for SRLS state data.";

          uses te-srlg-config;
        }
      }
    }
  }


  /*
   * TE Admin Groups
   */
  grouping te-admin-group-config {
    description
      "Grouping for admin-group configuration.";

    leaf name {
      type string;
      description
        "A string name that uniquely identifies an
         interface named admin-group.";
    }

    leaf bit-position {
      type uint32{
      range "0..255";
      }
      description
        "Bit position representing the administrative
         group.";
      reference
        "RFC3209: RSVP-TE: Extensions to RSVP for LSP Tunnels
         RFC7308: Extended Adminstrative Groups in MPLS
                  Traffic.";
    }
  }

  grouping te-admin-group-structure {
    description
      "This grouping defines TE Admin Group structure.";

    container admin-groups {
      description
        "Named admin groups container.";

      list admin-group {
        key "name";
        unique "config/bit-position";
        description
          "List of named admin-groups.";

        leaf name {
          type leafref {
            path "../config/name";
          }
        }

        container config {
          description
            "Container for admin-group configuration.";

          uses te-admin-group-config;
        }

        container state {
          config false;
          description
            "Container for admin-group state information.";

          uses te-admin-group-config;
        }
      }
    }
  }

  grouping te-admin-group-oper-structure {
    description
      "This grouping defines TE Admin Group structure for oper only.";

    container admin-groups {
      config false;
      description
        "Named admin groups container.";

      list admin-group {
        key "name";
        description
          "List of named admin-groups.";

        leaf name {
          type leafref {
            path "../state/name";
          }
        }

        container state {
          description
            "Container for admin-group state information.";

          uses te-admin-group-config;
        }
      }
    }
  }


  /*
   * TE Global - placeholder
   */
  grouping te-global-structure {
    description
      "This grouping defines TE global structure.";
  }


  /*
   * TE top level structure
   */
  grouping te-top {
    description
      "This grouping defines top level structure of TE.";

    container te {
      description
        "Top level container for TE configuration and state.";

      uses te-global-structure;
      uses te-admin-group-structure;
      uses te-srlg-structure;
    }
  }


  /*
   * Define TE under network-instance
   */
  augment "/oc-netinst:network-instances/oc-netinst:network-instance" {
    description
      "Traffic Engineering augmentations";

    uses te-top;
  }
}
