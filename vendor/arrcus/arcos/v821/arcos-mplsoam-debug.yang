module arcos-mplsoam-debug {
  yang-version 1.1;
  namespace "http://yang.arrcus.com/arcos/mplsoam/debug";
  prefix arc-mplsoam-dbg;

  import openconfig-policy-types {
    prefix oc-pol-types;
  }
  import arcos-debug {
    prefix arc-dbg;
  }

  organization
    "Arrcus, Inc.";

  contact
    "Arrcus, Inc.
     2077 Gateway Place
     Suite 400
     San Jose, CA 95110
     E-mail: yang-support@arrcus.com";

  description
    "This module defines debug for MPLS-OAM module

     Copyright (c) 2016-2024 by Arrcus, Inc.
     All rights reserved.";

  revision 2024-12-02 {
    description
      "Move MPLS-OAM debug to global list";
  }

  grouping mplsoam-debug-top {
    container mplsoam {
      description
        "This container defines MPLS-OAM debug information.";
      config false;

      uses arc-dbg:debug-component-top;
    }
  }

  augment "/arc-dbg:debug/arc-dbg:debug-attach-points" {
    uses mplsoam-debug-top {
      when "arc-dbg:component = 'mplsoamd'" {
        description
          "MPLS-OAM debug";
      }
      description
        "Debug information related to MPLS-OAM";
    }
  }
}
