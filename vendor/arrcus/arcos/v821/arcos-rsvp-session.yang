submodule arcos-rsvp-session {

  yang-version "1.1";

  belongs-to arcos-rsvp {
    prefix "arc-rsvp";
  }

  import ietf-yang-types {
    prefix ietf-yang;
  }
  import ietf-inet-types {
    prefix inet;
  }
  import openconfig-interfaces {
    prefix oc-if;
  }
  import arcos-rsvp-types {
    prefix arc-rsvp-types;
  }
  import openconfig-mpls-types {
    prefix oc-mplst;
  }

  description
    "This submodule provides a model for RSVP sessions";


  /*
   * RSVP Sessions
   */

  grouping rsvp-session-stats {
    description
      "This grouping defines RSVP session statistics.";

    leaf path-messages-sent {
      type ietf-yang:counter64;
      description
        "Total number of PATH messages sent";
    }

    leaf path-messages-received {
      type ietf-yang:counter64;
      description
        "Total number of PATH messages received";
    }

    leaf resv-messages-sent {
      type ietf-yang:counter64;
      description
        "Total number of RESV messages sent";
    }

    leaf resv-messages-received {
      type ietf-yang:counter64;
      description
        "Total number of RESV messages received";
    }

    leaf state-transitions {
      type ietf-yang:counter64;
      description
        "Total number of state transitions";
    }

    leaf path-changes {
      type ietf-yang:counter64;
      description
        "Total number of path changes";
    }

    leaf total-up-time {
      type uint32;
      description
        "Number of seconds the session is UP";
    }

    leaf instance-up-time {
      type uint32;
      description
        "Number of seconds this session instance is UP";
    }

    leaf instance-down-time {
      type uint32;
      description
        "Number of seconds this session instance is DOWN";
    }
  }

  grouping rsvp-session-rro-state {
    description
      "This grouping defines RSVP session RRO state.";

    leaf index {
      type uint32;

      description
        "Entry index";
    }

    leaf hop-type {
      type identityref {
        base "arc-rsvp-types:RSVP-RRO-HOP-TYPE";
      }

      description
        "Type of hop";
    }

    leaf ip-address {
      type inet:ip-address;

      description
        "IP address of the hop";
    }

    leaf asn {
      type uint32;

      description
        "AS Number of the hop";
    }

    leaf label {
      type oc-mplst:mpls-label;

      description
        "Label of the hop";
    }

    leaf interface-id {
      type uint32;

      description
        "Interface ID of the unnumbered interface of the hop";
    }
  }

  grouping rsvp-session-ero-state {
    description
      "This grouping defines RSVP session ERO state.";

    leaf index {
      type uint32;

      description
        "Entry index";
    }

    leaf hop-type {
      type identityref {
        base "arc-rsvp-types:RSVP-ERO-HOP-TYPE";
      }

      description
        "Type of hop";
    }

    leaf hop-route-type {
      type identityref {
        base "arc-rsvp-types:RSVP-HOP-ROUTE-TYPE";
      }


      description
        "Indicates if the hop is strict or loose";
    }

    leaf ip-prefix {
      type inet:ip-prefix;

      description
        "IP prefix of the hop";
    }

    leaf asn {
      type uint32;

      description
        "AS Number of the hop";
    }

    leaf label {
      type oc-mplst:mpls-label;

      description
        "Label of the hop";
    }

    leaf interface-id {
      type uint32;

      description
        "Interface ID of the unnumbered interface of the hop";
    }

    leaf is-self {
      type boolean;

      description
        "Indicates if this hop represents this router";
    }
  }

  grouping rsvp-session-constraints-state {
    description
      "This grouping defines RSVP session constraints state.";

    leaf bandwidth {
      type oc-mplst:bandwidth-mbps;

      description
        "Bandwidth";
    }

    leaf-list admin-groups-exclude-any {
      type string;

      description
        "List of admin-group names or bits any of which will make
         a link ineligible for selection";
    }

    leaf-list admin-groups-include-any {
      type string;

      description
        "List of admin-group names or bits any of which will make
         a link eligible for selection";
    }

    leaf-list admin-groups-include-all {
      type string;

      description
        "List of admin-group names or bits all of which must be
         present to make a link eligible";
    }
  }

  grouping rsvp-session-downstream-state {
    description
      "This grouping defines RSVP session upstream state.";

    leaf te-link-address {
      type inet:ip-address;
      description
        "Remote TE Link interface address";
    }

    leaf te-link-interface-id {
      type uint32;
      description
        "Remote TE Link Interface ID";
    }

    leaf neighbor-address {
      type inet:ip-address;
      description
        "Neighbor address";
    }

    leaf max-message-id {
      type uint32;
      description
        "Maximum message ID";
    }

    leaf out-path-ifindex {
      type uint32;
      description
        "Outgoing interface ifindex associated with PATH message";
    }

    leaf out-path-interface-name {
      type oc-if:interface-id;
      description
        "Outgoing interface associated with PATH message";
    }

    leaf out-path-message-id {
      type uint32;
      description
        "Outgoing PATH message ID";
    }

    leaf out-path-ttl {
      type uint8;
      description
        "PATH TTL remaining";
    }

    leaf out-path-refresh-interval {
      type uint32;
      description
        "PATH refresh interval in seconds";
    }

    leaf resv-state-expiry-timestamp {
      type string;
      description
        "Timestamp of RESV State Block expiry";
    }

    leaf in-resv-ifindex {
      type uint32;
      description
        "Incoming interface ifindex associated with RESV message";
    }

    leaf in-resv-interface-name {
      type oc-if:interface-id;
      description
        "Incoming interface associated with RESV message";
    }

    leaf in-resv-message-id {
      type uint32;
      description
        "Incoming RESV message ID";
    }

    leaf in-resv-hop-address {
      type inet:ip-address;
      description
        "RESV Hop address";
    }
  }

  grouping rsvp-session-upstream-state {
    description
      "This grouping defines RSVP session upstream state.";

    leaf te-link-address {
      type inet:ip-address;
      description
        "Remote TE Link Interface address";
    }

    leaf te-link-interface-id {
      type uint32;
      description
        "Remote TE Link Interface ID";
    }

    leaf neighbor-address {
      type inet:ip-address;
      description
        "Neighbor address";
    }

    leaf max-message-id {
      type uint32;
      description
        "Maximum message ID";
    }

    leaf in-path-ifindex {
      type uint32;
      description
        "Incoming interface ifindex associated with PATH message";
    }

    leaf in-path-interface-name {
      type oc-if:interface-id;
      description
        "Incoming interface associated with PATH message";
    }

    leaf in-path-message-id {
      type uint32;
      description
        "Incoming PATH message ID";
    }

    leaf in-path-ttl {
      type uint8;
      description
        "PATH TTL received";
    }

    leaf in-path-hop-address {
      type inet:ip-address;
      description
        "PATH Hop address";
    }

    leaf in-path-refresh-interval {
      type uint32;
      description
        "PATH refresh interval in seconds";
    }

    leaf out-resv-ifindex {
      type uint32;
      description
        "Outgoing interface ifindex associated with RESV message";
    }

    leaf out-resv-interface-name {
      type oc-if:interface-id;
      description
        "Outgoing interface associated with RESV message";
    }

    leaf out-resv-message-id {
      type uint32;
      description
        "Outgoing RESV message ID";
    }

    leaf out-resv-hop-address {
      type inet:ip-address;
      description
        "RESV Hop address";
    }

    leaf out-resv-refresh-interval {
      type uint32;
      description
        "RESV refresh interval in seconds";
    }

    leaf path-state-expiry-timestamp {
      type string;
      description
        "Timestamp of PATH State Block expiry";
    }
  }

  grouping rsvp-session-state {
    description
      "This grouping defines RSVP session state.";

    leaf source-ip {
      type inet:ip-address;

      description
        "Source IP address of this session";
    }

    leaf destination-ip {
      type inet:ip-address;

      description
        "Destination IP address of this session";
    }

    leaf tunnel-id {
      type uint16;

      description
        "Tunnel ID from the SESSION object";
    }

    leaf lsp-id {
      type uint16;

      description
        "LSP ID from the SENDER_TEMPLATE object";
    }

    leaf session-name {
      type string;

      description
        "Session name";
    }

    leaf oper-status {
      type identityref {
        base "arc-rsvp-types:RSVP-OPER-STATUS";
      }

      description
        "Session operational status";
    }

    leaf setup-priority {
      type uint8;

      description
        "Session setup priority";
    }

    leaf holding-priority {
      type uint8;
      description
        "Session holding priority";
    }

    leaf session-flags {
      type uint8;
      description
        "Flags specified in the SESSION object";
    }

    leaf lsp-role {
      type identityref {
        base oc-mplst:LSP_ROLE;
      }

      description
        "The LSP role of the RSVP session on this router";
    }

    leaf reservation-style {
      type identityref {
        base "arc-rsvp-types:RSVP-RESERVATION-STYLE";
      }

      description
        "Session reservation style";
    }

    leaf tunnel-ifindex {
      type uint32;
      description
        "ifindex of the associated tunnel interface";
    }

    leaf local-label {
      type oc-mplst:mpls-label;
      description
        "Local label allocated for this session";
    }

    leaf received-label {
      type oc-mplst:mpls-label;
      description
        "Label received in RESV message";
    }

    leaf creation-timestamp {
      type string;
      description
        "Timestamp of session creation";
    }

    leaf last-update-timestamp {
      type string;
      description
        "Timestamp of last update to the session";
    }

  }

  grouping rsvp-session-rro-structure {
    description
      "This grouping defines RSVP session RRO.";

    container rros {
      description
        "This container defines RSVP session RRO.";

      list rro {
        key "index";
        description
          "RSVP session RRO.";


        leaf index {
          type leafref {
            path "../state/index";
          }

          description
            "RRO list entry index";
        }

        container state {
          description
            "RSVP session RRO state";

          uses rsvp-session-rro-state;
        }
      }
    }
  }

  grouping rsvp-session-ero-structure {
    description
      "This grouping defines RSVP session ERO.";

    container eros {
      description
        "This container defines RSVP session ERO.";

      list ero {
        key "index";
        description
          "RSVP session ERO.";


        leaf index {
          type leafref {
            path "../state/index";
          }

          description
            "ERO list entry index";
        }

        container state {
          description
            "RSVP session ERO state";

          uses rsvp-session-ero-state;
        }
      }
    }
  }

  grouping rsvp-session-constraints-structure {
    description
      "This grouping defines RSVP session constraints.";

    container constraints {
      description
        "This container defines RSVP session constraints.";

      container state {
        description
          "RSVP session constraints state";

        uses rsvp-session-constraints-state;
      }
    }
  }

  grouping rsvp-session-downstream-structure {
    description
      "This grouping defines RSVP session downstream info.";

    container downstream {
      description
        "This container defines RSVP session downstream info.";

      container state {
        description
          "RSVP session downstream state";

        uses rsvp-session-downstream-state;
      }
    }
  }

  grouping rsvp-session-upstream-structure {
    description
      "This grouping defines RSVP session upstream info.";

    container upstream {
      description
        "This container defines RSVP session upstream info.";

      container state {
        description
          "RSVP session upstream state";

        uses rsvp-session-upstream-state;
      }
    }
  }

  grouping rsvp-session-structure {
    description
      "This grouping defines RSVP sessions.";

    container sessions {
      config false;
      description
        "This container defines RSVP sessions.";

      list session {
        key "source-ip destination-ip tunnel-id lsp-id";
        description
          "RSVP session.";


        leaf source-ip {
          type leafref {
            path "../state/source-ip";
          }

          description
            "Source IP address";
        }

        leaf destination-ip {
          type leafref {
            path "../state/destination-ip";
          }

          description
            "Destination IP address";
        }

        leaf tunnel-id {
          type leafref {
            path "../state/tunnel-id";
          }

          description
            "Tunnel ID";
        }

        leaf lsp-id {
          type leafref {
            path "../state/lsp-id";
          }

          description
            "LSP ID";
        }

        container state {
          description
            "RSVP session state";

          uses rsvp-session-state;
        }

        container statistics {
          description
            "RSVP session statistics";

          uses rsvp-session-stats;
        }

        uses rsvp-session-upstream-structure;
        uses rsvp-session-downstream-structure;
        uses rsvp-session-constraints-structure;
        uses rsvp-session-ero-structure;
        uses rsvp-session-rro-structure;
      }
    }
  }
}
