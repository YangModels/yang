module arcos-tailf-aaa-augments {
  yang-version 1.1;
  namespace "http://yang.arrcus.com/arcos/tailf/aaa/augments";
  prefix arc-tailf-aaa-aug;

  import tailf-aaa {
    prefix aaa;
  }

  organization
    "Arrcus, Inc.";

  contact
    "Arrcus, Inc.
     2077 Gateway Place
     Suite 400
     San Jose, CA 95110

     E-mail: yang-support@arrcus.com";

  description
    "This module defines augment statements for the
     tail-f AAA module.

     Copyright (c) 2023 by Arrcus, Inc.
     All rights reserved.";

  revision 2023-09-27 {
    description
      "Initial Revision";

    reference
      "RFC 6020: YANG - A Data Modeling Language for the
       Network Configuration Protocol (NETCONF)";
  }

  grouping alias-augments {
    leaf description {
      type string;
      description "Help string for alias";
    }
  }

  augment "/aaa:alias" {
    uses alias-augments;
  }
}
