module arcos-event {
  yang-version 1.1;
  namespace "http://yang.arrcus.com/arcos/event";
  prefix arc-evt;

  organization
    "Arrcus, Inc.";

  contact
    "Arrcus, Inc.
     2077 Gateway Place
     Suite 400
     San Jose, CA 95110

     E-mail: yang-support@arrcus.com";

  description
    "This module contains model for
     Arrcus specific event configuration.

     Copyright (c) 2018 by Arrcus, Inc.
     All rights reserved.";

  revision "2023-10-02" {
    description
      "Added support for ON_COMMIT trigger";
  }

  revision "2023-04-04" {
    description
      "Added relative delay to model";
  }

  revision "2018-02-02" {
    description
      "Initial version";
  }

  identity EVENT_TYPE {
    description
      "Base identity for types of EVENT sets";
  }

  identity ON_BOOT {
    base EVENT_TYPE;
    description
      "on start event";
  }

  identity ON_ARCOS_START {
    base EVENT_TYPE;
    description
      "on arcos start";
  }

  identity ON_CONFIG_START {
    base EVENT_TYPE;
    description
      "on config start";
  }

  identity ON_COMMIT {
    base EVENT_TYPE;
    description
      "On performing commit of any configuration";
  }

  grouping action-config {
    description
      "Config of action type";

    leaf execute {
      type string;
      mandatory true;
      description
        "Specifies the action";
    }
  }

  grouping action-top {
    description
      "EVENT action type top level container";

    container actions {
      description
        "Enclosing container for list of EVENT actions associated
        with an entry";

      container config {
        description
          "Config data for EVENT actions";

        uses action-config;
      }

      container state {
        config false;
        description
          "State information for EVENT actions";

        uses action-config;
      }
    }
  }

  grouping event-list-entries-config {
    description
      "Event List Entries config.";

    leaf sequence-id {
      type uint32;
      description
        "The sequence id determines the order in which EVENT entries
         are applied. The sequence id must be unique for each entry.";
    }

    leaf execute {
      type string;
      mandatory true;
      description
        "Specifies the action";
    }

    leaf relative-delay {
      type uint32;
      default 0;
      description
        "Specifies delay (secs) of execution relative to preceding entry.";
    }
  }

  grouping event-list-entries-top {
    description
      "Event list entries to level container";

    container event-entries {
      description
        "Event list entries container";

      list event-entry {
        key "sequence-id";
        max-elements 4;
        min-elements 1;
        description
          "List of EVENT entries comprising an Event set";

        leaf sequence-id {
          type leafref {
            path "../config/sequence-id";
          }
          description
            "references the list key";
        }

        container config {
          description
            "Event list entries config";
          uses event-list-entries-config;
        }

        container state {
          config false;
          description
            "State information for EVENT entries";
          uses event-list-entries-config;
        }
      }
    }
  }

  grouping event-set-config {
    description
      "Event Control List config";

    leaf description {
      type string;
      description
        "Description, or comment, for the EVENT set";
    }
  }

  grouping event-set-top {
    description
      "Event list entries variables top level container";

    container event-sets {
      description
        "Event list entries variables enclosing container";

      list event {
        key "type";
        description
          "List of EVENT sets, each comprising of a list of EVENT
           entries";

        leaf type {
          type identityref {
            base EVENT_TYPE;
          }
          description
            "Reference to the type list key";
        }

        container config {
          description
            "Event list config";
          uses event-set-config;
        }

        container state {
          config false;
          description
            "Event list state information";

          uses event-set-config;
        }
        uses event-list-entries-top;
      }
    }
  }

  grouping event-top {
    description
      "Top level grouping for EVENT data and structure";

    container event {
      description
        "Top level enclosing container for EVENT model config
        and operational state data";

      uses event-set-top;
    }
  }

  uses event-top;
}
