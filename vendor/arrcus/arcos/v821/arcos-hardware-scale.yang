submodule arcos-hardware-scale {
  yang-version 1.1;

  belongs-to arcos-hardware {
    prefix arc-hw;
  }

  import arcos-platform {
    prefix arc-platform;
  }

  grouping hardware-scale {
    description "HW Scale profile";
    leaf scale-profile {
      type enumeration {
        enum L3;
        enum L2;
        enum Balanced;
        enum Balanced-Exem;
        enum Kbp;
      }
      description "Scale profile name";
      when "/arc-platform:platform/arc-platform:family = 'arc-platform:BROADCOM_DNX'";
    }
  }
}
