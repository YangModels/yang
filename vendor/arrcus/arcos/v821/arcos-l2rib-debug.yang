module arcos-l2rib-debug {
  yang-version 1.1;
  namespace "http://yang.arrcus.com/arcos/l2rib/debug";
  prefix arc-l2rib-dbg;

  organization
    "Arrcus, Inc.";

  contact
    "Arrcus, Inc.
     2077 Gateway Place
     Suite 400
     San Jose, CA 95110

     E-mail: yang-support@arrcus.com";

  description
    "This module contains definitions for the
     native ArcOS Layer 2 RIB Debug domain.

     Note: This module is under deprecation and
     will be migrated to another module.

     Copyright (c) 2016-2019 by Arrcus, Inc.
     All rights reserved.";

  revision 2019-10-31 {
    description "Initial version";
  }

  typedef debug-action-type {
    type enumeration {
      enum dump-txlist {
        description
          "Dump the L2RIB internal TxList to a file";
      }
    }
  }

  typedef l2rib-debug-type {
    type enumeration {
      enum txlist {
        description
          "L2RIB txlist dump debugs";
      }
    }
  }

  typedef l2rib-debug-state {
    type enumeration {
      enum off {
        description
          "Disable debug";
      }
      enum on {
        description
          "Enable debug";
      }
    }
  }

  container l2rib-debug {
    description
      "Layer 2 RIB debug commands";
    action action {
      input {
        leaf type {
          type debug-action-type;
          mandatory true;
          description
            "Debug action to take";
        }
      }
      output {
        leaf result {
        type string;
          description
          "The status of operation";
        }
      }
    }

    action debug {
      input {
        leaf type {
        type l2rib-debug-type;
        mandatory true;
          description
          "Type of debug to be controlled";
        }
        leaf op {
        type l2rib-debug-state;
        mandatory true;
          description
          "turn on/off operation";
        }
      }
      output {
        leaf result {
        type string;
          description
          "The status of operation";
        }
      }
    }
  }
}
