module arcos-mpls-te-deviations {
  yang-version 1.1;
  namespace "http://yang.arrcus.com/arcos/mpls-te/deviations";
  prefix arc-mpls-te-dev;

  import openconfig-network-instance {
    prefix oc-netinst;
  }

  import arcos-mpls-te {
    prefix arc-mpls-te;
  }
  import tailf-common {
    prefix tailf;
  }

  organization 
    "Arrcus, Inc";

  contact
    "Arrcus, Inc.
     2077 Gateway Place
     Suite 400
     San Jose, CA 95110

     E-mail: yang-support@arrcus.com";

  description
    "This module lists the deviations for MPLS-TE module.

     Copyright (c) 2022 by Arrcus, Inc.
     All rights reserved.";

  revision 2022-05-25 {
    description
      "Initial version.";
  }

  deviation "/oc-netinst:network-instances/oc-netinst:network-instance" +
            "/oc-netinst:mpls/arc-mpls-te:mpls-te" +
            "/arc-mpls-te:global/arc-mpls-te:config" {
    deviate not-supported;
    description
      "Not supported in this release";
  }

  deviation "/oc-netinst:network-instances/oc-netinst:network-instance" +
            "/oc-netinst:mpls/arc-mpls-te:mpls-te" +
	    "/arc-mpls-te:igp-shortcut" {
    deviate not-supported;
    description
      "Not supported in this release";
  }

  deviation "/oc-netinst:network-instances/oc-netinst:network-instance" +
            "/oc-netinst:mpls/arc-mpls-te:mpls-te" +
	    "/arc-mpls-te:tunnels" {
    deviate not-supported;
    description
      "Not supported in this release";
  }

  deviation "/oc-netinst:network-instances/oc-netinst:network-instance" +
            "/oc-netinst:mpls/arc-mpls-te:mpls-te" +
            "/arc-mpls-te:interfaces/arc-mpls-te:interface" +
            "/arc-mpls-te:config/arc-mpls-te:admin-groups" {
    deviate not-supported;
    description
      "Not supported in this release";
  }
}
