module arcos-copp-classifier {
  yang-version 1.1;
  namespace "http://yang.arrcus.com/arcos/copp/classifier";
  prefix arc-copp-cfr;

  import arcos-classifier {
    prefix arc-cfr;
  }
  import arcos-classifier-filter {
    prefix arc-cfr-fltr;
  }
  import arcos-classifier-filter-types {
    prefix arc-cfr-fltr-types;
  }
  import arcos-copp {
    prefix arc-copp;
  }
  import openconfig-acl {
    prefix oc-acl;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for qos classifier definitions.
     Expanded from the generic classifier data model (classifier.yang)
     
     Copyright (c) 2016-2023 by Arrcus, Inc.
     All rights reserved.";

  revision 2023-06-27 {
    description
      "Initial revision.";
  }

  augment "/arc-copp:copp/classifiers/classifier/filters/filter/config" {
    uses arc-cfr-fltr:exception-top {
      when "../type = 'arc-cfr-fltr-types:EXCEPTION'";
    }
    description 
      "Augment COPP classifier's filter config to add exception-type leaf.";
  }

  augment "/arc-copp:copp/classifiers/classifier/filters/filter/config" {
    uses arc-cfr-fltr:acl-top {
      when "../type = 'arc-cfr-fltr-types:ACL'";
    }
    description 
      "Augment COPP classifier's filter config to add acl-type leaf";
  }

  augment "/arc-copp:copp/classifiers/classifier/filters/filter/state" {
    uses arc-cfr-fltr:exception-top;
    description 
      "Augment COPP classifier's filter state to add exception-type leaf";
  }

  augment "/arc-copp:copp/classifiers/classifier/filters/filter/state" {
    uses arc-cfr-fltr:acl-top;
    description 
      "Augment COPP classifier's filter state to add acl-type leaf";
  }

  augment "/arc-copp:copp/system-defined/classifiers/classifier/filters/filter/state" {
    uses arc-cfr-fltr:exception-top {
      when "./type = 'arc-cfr-fltr-types:EXCEPTION'";
    }
    description 
      "Augment system defined copp-classifier's filter state to add exception-type leaf";
  }

  augment "/arc-copp:copp/system-defined/classifiers/classifier/filters/filter/state" {
    uses arc-cfr-fltr:acl-top;
    description 
      "Augment system defined copp-classifier's filter state to add acl-type leaf";
  }

  grouping copp-classifier-top {
    description
      "Top-level container for COPP specific classifier database";
    uses arc-cfr:classifiers-top {
      refine "classifiers/classifier/filters/filter" {
        min-elements 1;
        max-elements 1;
      }
      refine "classifiers/classifier/filters/filter/type" {
        must "current() = 'arc-cfr-fltr-types:ACL' or "
           + "current() = 'arc-cfr-fltr-types:EXCEPTION'" {
          error-message "filter type not supported copp";
        }
      }
    }
    container system-defined {
      config false;
      description
        "Display system defined copp-classifiers.These classifiers can not be modified";
      uses arc-cfr:classifiers-top;
    }
  }

  augment "/arc-copp:copp" {
    uses copp-classifier-top;
    description 
      "Augment COPP to add classifiers";
  }
}
