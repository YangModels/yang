module Cisco-IOS-XE-spanning-tree {
  yang-version 1.1;
  namespace "http://cisco.com/ns/yang/Cisco-IOS-XE-spanning-tree";
  prefix ios-stp;

  import cisco-semver {
    prefix cisco-semver;
  }
  import Cisco-IOS-XE-native {
    prefix ios;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE Spanning Tree (stp) Yang Model.
     Copyright (c) 2016-2024 by Cisco Systems, Inc.
     All rights reserved.";

  revision 2025-07-01 {
    description
      "- Deprecated spanning-tree vlan list and introduced vlan-v2 list
       - Added a model for mst pvst transparent
       - Added FiftyGigabitEthernet interface support";
    cisco-semver:module-version "3.2.0";
  }
  revision 2024-07-01 {
    description
      "- Deprecated spanning-tree portfast container, converted leafs to choices and added missing options
       - Added vlan-ids for spanning-tree mst configuration instance, removed old node
       - Added missing leafs for spanning-tree portfast edge and spanning-tree portfast network
       - Added access leaf under interface spanning-tree portfast edge container to replace interface spanning-tree portfast edge leaf
       - Changed portfast-v2 portfast to be portfast-v2 access";
    cisco-semver:module-version "3.1.0";
  }
  revision 2024-03-01 {
    description
      "- Added support for spanning-tree bpdu delay-monitor and sender-conflict
       - Added Choice for spanning-tree mst priority, root
       - Added Choice for spanning-tree pathcost options long and short";
    cisco-semver:module-version "3.0.0";
  }
  revision 2023-11-01 {
    description
      "- Added error message for bridge-priority, port-priority";
    cisco-semver:module-version "2.0.0";
  }
  revision 2022-11-01 {
    description
      "- Update yang-version to 1.1";
    cisco-semver:module-version "1.2.0";
  }
  revision 2022-07-01 {
    description
      "- Added Support for PRP Interface";
    cisco-semver:module-version "1.1.0";
  }
  revision 2019-07-01 {
    description
      "- Establish semantic version baseline
       - Added Simulate options for Spanning tree mst";
    cisco-semver:module-version "1.0.0";
  }
  revision 2019-01-22 {
    description
      "Added leaf for App-hosting Gigabit Ethernet interface";
  }
  revision 2018-11-07 {
    description
      "Cleanup spelling errors in description statements";
  }
  revision 2017-11-27 {
    description
      "Added Change 25GE name";
  }
  revision 2017-11-14 {
    description
      "This revision has changes for new 100GE interface addition";
  }
  revision 2017-09-15 {
    description
      "This revision has changes for new 2gig interface addition";
  }
  revision 2017-08-22 {
    description
      "Fixed link-type to just keep P2P and shared because the cli changes.";
  }
  revision 2017-08-16 {
    description
      "This revision has changes for new 5gig and 25gig interfaces addition";
  }
  revision 2017-08-13 {
    description
      "Removed edge of bpduguard and bpdufilter due to cli change;Set rapid-pvst as default mode;Added spanning-tree under FortyGigabitEthernet";
  }
  revision 2017-07-10 {
    description
      "Added leaf assurance under bridge/Fixed bpdu for global STP/Fixed mst/vlan list instance under interface/Added spanning-tree under interface Vlan";
  }
  revision 2017-02-07 {
    description
      "Initial revision";
  }

  grouping config-spanning-tree-grouping {
    leaf backbonefast {
      description
        "Enable BackboneFast Feature";
      type empty;
    }
    container bridge {
      leaf priority {
        type uint8;
      }
      leaf ID {
        type string;
      }
      leaf assurance {
        description
          "Enable STP Bridge Assurance feature";
        type boolean;
        default "true";
      }
    }
    container etherchannel {
      description
        "Spanning tree etherchannel specific configuration";
      container guard {
        description
          "Configure guard features for etherchannel";
        leaf misconfig {
          description
            "Enable guard to protect against etherchannel misconfiguration";
          type boolean;
          default "true";
        }
      }
    }
    container extend {
      description
        "Spanning Tree 802.1t extensions";
      leaf system-id {
        description
          "Extend system-id into priority portion of the bridge id (PVST & Rapid PVST only)";
        type empty;
      }
    }
    container bpdu {
      description
        "Spanning tree bpdu options";
      leaf delay-monitor {
        description
          "Enable spanning-tree bpdu delay-monitor by default on all ports";
        type boolean;
        default "true";
      }
      leaf sender-conflict {
        description
          "Enable spanning-tree bpdu sender-conflict by default on all ports";
        type boolean;
        default "true";
      }
    }
    leaf logging {
      description
        "Enable Spanning tree logging";
      type empty;
    }
    container loopguard {
      description
        "Spanning tree loopguard options";
      leaf default {
        description
          "Enable loopguard by default on all ports";
        type empty;
      }
    }
    container mst {
      description
        "Multiple spanning tree configuration";
      list instance-range {
        key "id";
        leaf id {
          type union {
            type uint16;
            type string;
          }
        }
        container priority-root {
          description
            "Multiple spanning tree instance bridge priority configuration";
          choice mst-choice {
            case priority-case {
              leaf priority {
                description
                  "bridge priority for the spanning tree instance";
                type uint16 {
                  range "0..61440";
                }
                must '. mod 4096 = 0' {
                  error-message "Bridge Priority must be in increments of 4096";
                }
              }
            }
            case root-case {
              leaf root {
                description
                  "spanning-tree instance root configuration";
                type enumeration {
                  enum primary;
                  enum secondary;
                }
              }
            }
          }
        }
        leaf priority {
          status deprecated;
          description
            "DEPRECATED - Set the bridge priority for the spanning tree";
          type uint16 {
            range "0..61440";
          }
          must '. mod 4096 = 0' {
            error-message "Bridge Priority must be in increments of 4096";
          }
        }
        leaf root {
          status deprecated;
          description
            "DEPRECATED - Configure switch as root";
          type enumeration {
            enum primary;
            enum secondary;
          }
        }
      }
      container configuration {
        description
          "Enter MST configuration submode";
        leaf name {
          description
            "Set configuration name";
          type string;
        }
        list instance {
          description
            "Map vlans to an MST instance";
          key "id";
          leaf id {
            type uint16 {
              range "0..4094";
            }
          }
          leaf-list vlan-ids {
            description
              "Range of vlans to add to the instance mapping";
            type uint16 {
              range "1..4094";
            }
          }
          leaf-list vlan {
            status deprecated;
            description
              "DEPRECATED - Range of vlans to add to the instance mapping";
            type union {
              type uint16;
              type string;
            }
          }
        }
        container private-vlan {
          description
            "Set private-vlan synchronization";
          leaf synchronize {
            description
              "Synchronize vlans";
            type empty;
          }
        }
        leaf revision {
          description
            "Set configuration revision number";
          type uint16;
        }
      }
      leaf forward-time {
        description
          "number of seconds for the forward delay timer";
        type uint8 {
          range "4..30";
        }
      }
      leaf hello-time {
        description
          "number of seconds between generation of config BPDUs";
        type uint8 {
          range "1..10";
        }
      }
      leaf max-age {
        description
          "maximum number of seconds the information in a BPDU is valid";
        type uint8 {
          range "6..40";
        }
      }
      leaf max-hops {
        description
          "maximum number of hops a BPDU is valid";
        type uint8 {
          range "1..255";
        }
      }
      container simulate {
        description
          "Spanning tree simulation options";
        container pvst {
          description
            "Configure PVST simulation options for the spanning tree";
          leaf global {
            description
              "Enable PVST simulation for the spanning tree";
            type boolean;
          }
        }
      }
      container pvst {
        description
          "Configure PVST transparent options for the spanning tree";
        leaf transparent {
          description
            "Enable MST PVST transparent for the spanning tree";
          type empty;
        }
      }
    }
    container optimize {
      container bpdu {
        leaf transmission {
          type boolean;
        }
      }
    }
    container pathcost {
      description
        "Spanning tree pathcost options";
      container method {
        description
          "Method to calculate default port path cost";
        container long-short {
          description
            "Spanning tree pathcost long or short";
          choice pathcost-choice {
            description
              "Choice between the long and short pathcost options";
            leaf long {
              description
                "Use 32 bit based values for default port path costs";
              type empty;
            }
            leaf short {
              description
                "Use 16 bit based values for short path costs";
              type empty;
            }
          }
        }
        leaf long {
          status deprecated;
          description
            "Use 32 bit based values for default port path costs";
          type empty;
        }
        leaf short {
          status deprecated;
          type empty;
        }
      }
    }
    container portfast {
      description
        "Spanning tree portfast options";
      container bpdufilter {
        description
          "Enable portfast edge bpdu filter on this switch";
        leaf default {
          description
            "Enable bpdu filter by default on all portfast edge ports";
          type empty;
        }
      }
      container bpduguard {
        description
          "Enable portfast edge bpdu guard on this switch";
        leaf default {
          description
            "Enable bpdu guard by default on all portfast edge ports";
          type empty;
        }
      }
      container edge {
        container bpduguard {
          description
            "Enable portfast edge bpdu guard on this switch";
          leaf default {
            description
              "Enable bpdu guard by default on all portfast edge ports";
            type empty;
          }
        }
        container bpdufilter {
          description
            "Enable portfast edge bpdu filter on this switch";
          leaf default {
            description
              "Enable bpdu filter by default on all portfast edge ports";
            type empty;
          }
        }
        leaf default {
          description
            "Enable portfast edge by default on all access ports";
          type empty;
        }
      }
      container network {
        leaf default {
          description
            "Enable portfast network by default on all ports";
          type empty;
        }
      }
      leaf default {
        description
          "Enable portfast by default on all access ports";
        type empty;
      }
    }
    container transmit {
      description
        "STP transmit parameters";
      leaf hold-count {
        description
          "Value for txholdcount parameter";
        type uint8 {
          range "1..20";
        }
      }
    }
    container uplinkfast {
      description
        "Enable UplinkFast Feature";
      presence "true";
      leaf max-update-rate {
        description
          "Rate at which station address updates are sent";
        type uint32 {
          range "0..32000";
        }
      }
    }
    leaf mode {
      description
        "Spanning tree operating mode";
      type enumeration {
        enum mst;
        enum pvst;
        enum rapid-pvst;
      }
      default "rapid-pvst";
    }
    container vlan-v2 {
      list vlan-v2 {
        description
          "VLAN Switch Spanning Tree";
        key "id";
        leaf id {
          type uint16 {
            range "1..4094";
          }
        }
        leaf max-age {
          description
            "Set the max age interval for the spanning tree";
          type uint8 {
            range "6..40";
          }
        }
        leaf forward-time {
          description
            "Set the forward delay for the spanning tree";
          type uint8 {
            range "4..30";
          }
        }
        leaf hello-time {
          description
            "Set the hello interval for the spanning tree";
          type uint8 {
            range "1..10";
          }
        }
        leaf priority {
          description
            "Set the bridge priority for the spanning tree";
          type uint16 {
            range "0..61440";
          }
          must '. mod 4096 = 0' {
            error-message "Bridge Priority must be in increments of 4096";
          }
        }
        container root {
          description
            "Configure switch as root";
          container primary {
            description
              "Configure this switch as primary root for this spanning tree";
            leaf diameter {
              description
                "Network diameter of this spanning tree";
              type uint8 {
                range "2..7";
              }
            }
            leaf hello-time {
              description
                "Hello interval for this spanning tree";
              type uint8 {
                range "1..10";
              }
            }
          }
          container secondary {
            description
              "Configure switch as secondary root";
            leaf diameter {
              description
                "Network diameter of this spanning tree";
              type uint8 {
                range "2..7";
              }
            }
            leaf hello-time {
              description
                "Hello interval for this spanning tree";
              type uint8 {
                range "1..10";
              }
            }
          }
        }
      }
    }
    list vlan {
      description
        "VLAN Switch Spanning Tree (DEPRECATED, use vlan-v2)";
      status deprecated;
      key "id";
      leaf id {
        status deprecated;
        type string;
      }
      leaf max-age {
        description
          "Set the max age interval for the spanning tree";
        status deprecated;
        type uint8 {
          range "6..40";
        }
      }
      leaf forward-time {
        description
          "Set the forward delay for the spanning tree";
        status deprecated;
        type uint8 {
          range "4..30";
        }
      }
      leaf hello-time {
        description
          "Set the hello interval for the spanning tree";
        status deprecated;
        type uint8 {
          range "1..10";
        }
      }
      leaf priority {
        description
          "Set the bridge priority for the spanning tree";
        status deprecated;
        type uint16 {
          range "0..61440";
        }
        must '. mod 4096 = 0' {
          error-message "Bridge Priority must be in increments of 4096";
        }
      }
      container root {
        description
          "Configure switch as root";
        status deprecated;
        container primary {
          description
            "Configure this switch as primary root for this spanning tree";
          status deprecated;
          leaf diameter {
            description
              "Network diameter of this spanning tree";
            status deprecated;
            type uint8 {
              range "2..7";
            }
          }
          leaf hello-time {
            description
              "Hello interval for this spanning tree";
            status deprecated;
            type uint8 {
              range "1..10";
            }
          }
        }
        container secondary {
          description
            "Configure switch as secondary root";
          status deprecated;
          leaf diameter {
            description
              "Network diameter of this spanning tree";
            status deprecated;
            type uint8 {
              range "2..7";
            }
          }
          leaf hello-time {
            description
              "Hello interval for this spanning tree";
            status deprecated;
            type uint8 {
              range "1..10";
            }
          }
        }
      }
    }
  }

  grouping config-interface-spanning-tree {
    container spanning-tree {
      description
        "Spanning Tree Subsystem";
      leaf bpdufilter {
        description
          "Don't send or receive BPDUs on this interface";
        type enumeration {
          enum disable;
          enum enable;
        }
      }
      container bpduguard {
        description
          "Don't accept BPDUs on this interface";
        choice bpduguard-choice {
          leaf disable {
            description
              "Disable BPDU guard for this interface";
            type empty;
          }
          leaf enable {
            type empty;
            description
              "Enable BPDU guard for this interface";
          }
        }
      }
      leaf cost {
        description
          "To set the path cost of the interface";
        type uint32 {
          range "1..200000000";
        }
      }
      leaf guard {
        description
          "Change an interface's spanning tree guard mode";
        type enumeration {
          enum loop;
          enum none;
          enum root;
        }
      }
      leaf link-type {
        description
          "Specify a link type for spanning tree tree protocol use";
        type enumeration {
          enum point-to-point;
          enum shared;
        }
      }
      container portfast-v2 {
        description
          "Spanning tree portfast options";
        choice portfast-choice {
          case access-case {
            leaf access {
              description
                "Enable an interface to move directly to forwarding on link up";
              type empty;
            }
          }
          case disable {
            leaf disable {
              description
                "Disable portfast for this interface";
              type empty;
            }
          }
          case trunk {
            leaf trunk {
              description
                "Enable portfast on the interface even in trunk mode";
              type empty;
            }
          }
          case edge-case {
            container edge {
              choice edge-choice {
                case trunk-case {
                  leaf trunk {
                    description
                      "Enable portfast edge on the interface even in trunk mode";
                    type empty;
                  }
                }
                case access-case {
                  leaf access {
                    description
                      "Enable portfast edge on the interface in access mode";
                    type empty;
                  }
                }
              }
            }
          }
          case network {
            leaf network {
              description
                "Enable portfast network on the interface";
              type empty;
            }
          }
        }
      }
      container portfast {
        status deprecated;
        description
          "(DEPRECATED) Spanning tree portfast options";
        presence "true";
        leaf disable {
          status deprecated;
          description
            "(DEPRECATED) Disable portfast for this interface";
          type empty;
        }
        leaf trunk {
          status deprecated;
          description
            "(DEPRECATED) Enable portfast on the interface even in trunk mode";
          type empty;
        }
        leaf edge {
          status deprecated;
          description
            "(DEPRECATED) Enable portfast edge on the interface";
          type empty;
        }
      }
      leaf port-priority {
        description
          "Spanning tree port-priority options";
        type uint8 {
          range "0..240";
        }
        must '. mod 16 = 0' {
          error-message "Port Priority in increments of 16 is required";
        }
      }
      list vlan {
        description
          "VLAN Switch Spanning Tree";
        key "vlan-ids";
        leaf vlan-ids {
          description
            "vlan range, example: 1,3-5,7,9-11";
          type string;
        }
        leaf cost {
          description
            "<1-200000000> Spanning-tree cost";
          type uint32 {
            range "1..200000000";
          }
        }
        leaf port-priority {
          description
            "<0-240> port priority in increments of 16";
          type uint16 {
            range "0..240";
          }
          must '. mod 16 = 0' {
            error-message "Port Priority in increments of 16 is required";
          }
        }
      }
      container loopguard {
        description
          "Spanning tree loopguard options";
        leaf default {
          description
            "Enable loopguard by default on all ports";
          type empty;
        }
      }
      container mst {
        description
          "Per interface MST configurations";
        list mst-instance {
          key "instance";
          leaf instance {
            description
              "MST instance list, example 0,2-4,6,8-12";
            type string;
          }
          leaf cost {
            description
              "<1-200000000> Spanning-tree cost";
            type uint32 {
              range "1..200000000";
            }
          }
          leaf port-priority {
            description
              "<0-240> port priority in increments of 16";
            type uint16 {
              range "0..240";
            }
          }
        }
        leaf pre-standard {
          description
            "Force pre-standard MST BPDU transmission on port";
          type empty;
        }
      }
    }
  }

  augment "/ios:native/ios:spanning-tree" {
    uses config-spanning-tree-grouping;
  }

  augment "/ios:native/ios:interface/ios:FastEthernet" {
    uses config-interface-spanning-tree;
  }

  augment "/ios:native/ios:interface/ios:GigabitEthernet" {
    uses config-interface-spanning-tree;
  }

  augment "/ios:native/ios:interface/ios:TenGigabitEthernet" {
    uses config-interface-spanning-tree;
  }

  augment "/ios:native/ios:interface/ios:FortyGigabitEthernet" {
    uses config-interface-spanning-tree;
  }

  augment "/ios:native/ios:interface/ios:FiftyGigabitEthernet" {
    uses config-interface-spanning-tree;
  }

  augment "/ios:native/ios:interface/ios:FiveGigabitEthernet" {
    uses config-interface-spanning-tree;
  }

  augment "/ios:native/ios:interface/ios:AppGigabitEthernet" {
    uses config-interface-spanning-tree;
  }

  augment "/ios:native/ios:interface/ios:TwentyFiveGigE" {
    uses config-interface-spanning-tree;
  }

  augment "/ios:native/ios:interface/ios:TwoGigabitEthernet" {
    uses config-interface-spanning-tree;
  }

  augment "/ios:native/ios:interface/ios:HundredGigE" {
    uses config-interface-spanning-tree;
  }

  augment "/ios:native/ios:interface/ios:Port-channel" {
    uses config-interface-spanning-tree;
  }

  augment "/ios:native/ios:interface/ios:PRP-channel" {
    uses config-interface-spanning-tree;
  }

  augment "/ios:native/ios:interface/ios:Vlan" {
    uses config-interface-spanning-tree;
  }
}
