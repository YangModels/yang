module Cisco-IOS-XE-otv {
  yang-version 1.1;
  namespace "http://cisco.com/ns/yang/Cisco-IOS-XE-otv";
  prefix ios-otv;

  import cisco-semver {
    prefix cisco-semver;
  }
  import ietf-inet-types {
    prefix inet;
  }
  import Cisco-IOS-XE-native {
    prefix ios;
  }
  import Cisco-IOS-XE-interface-common {
    prefix ios-ifc;
  }
  import Cisco-IOS-XE-ethernet {
    prefix ios-eth;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Overlay Transport Virtualization (OTV) Yang model.
     Copyright (c) 2016 by Cisco Systems, Inc.
     All rights reserved.";

  revision 2022-11-01 {
    description
      "- Update yang-version to 1.1";
    cisco-semver:module-version "2.1.0";
  }
  revision 2022-03-01 {
    description
      "obsolete default container";
    cisco-semver:module-version "2.0.0";
  }
  revision 2019-07-01 {
    description
      "Establish semantic version baseline";
    cisco-semver:module-version "1.0.0";
  }
  revision 2017-02-07 {
    description
      "Initial revision";
  }

  grouping otv-isis-hostname-grouping {
    container hostname {
      description
        "Dynamic hostname for IS-IS";
      leaf dynamic {
        description
          "Dynamic hostname";
        type empty;
      }
    }
  }

  grouping otv-isis-skeptical-grouping {
    container skeptical {
      description
        "Be a cautious NSF helper when refresh adjacency";
      leaf interval {
        description
          "Interval during which holdtime will NOT be refreshed";
        type uint32 {
          range "0..1440";
        }
      }
    }
  }

  grouping otv-isis-log-adjacency-changes-grouping {
    container log-adjacency-changes {
      description
        "Log changes in adjacency state";
      presence "true";
      leaf all {
        description
          "Include changes generated by non-IIH event";
        type empty;
      }
    }
  }

  grouping otv-isis-site-grouping {
    container default {
      description
        "Set a command to its defaults";
      status obsolete;
      leaf log-adjacency-changes {
        description
          "Log changes in adjacency state";
        status obsolete;
        type empty;
      }
      leaf net {
        description
          "A Network Entity Title for this process";
        status obsolete;
        type empty;
      }
      container skeptical {
        description
          "Be a cautious NSF helper when refresh adjacency";
        status obsolete;
        leaf interval {
          description
            "Interval during which holdtime will NOT be refreshed";
          status obsolete;
          type empty;
        }
      }
    }
    uses otv-isis-log-adjacency-changes-grouping;
    leaf net {
      description
        "A Network Entity Title for this process";
      type string;
    }
    uses otv-isis-skeptical-grouping;
  }

  grouping otv-isis-authentication-grouping {
    container authentication {
      description
        "ISIS authentication for interface related PDUs";
      leaf key-chain {
        description
          "Authentication key-chain";
        type string;
      }
      leaf mode {
        description
          "Authentication mode for PDUs";
        type enumeration {
          enum md5;
          enum text;
        }
      }
      leaf send-only {
        description
          "Authentication send only, receive ignore";
        type empty;
      }
    }
  }

  grouping interface-overlay-grouping {
    container otv {
      description
        "Configure OTV information";
      container adjacency-server {
        description
          "Indicate if the box is an Adjacency Server";
        leaf unicast-only {
          description
            "Unicast Only";
          type empty;
        }
      }
      leaf control-group {
        description
          "OTV VPN control multicast group";
        type inet:ipv4-address;
      }
      leaf data-group {
        description
          "Multicast group range for data";
        type inet:ipv4-prefix;
      }
      container encapsulation-format {
        description
          "Encapsulation format";
        container ip {
          description
            "Use IP for outer header encapsulation";
          leaf gre {
            description
              "Use GRE middle header encapsulation";
            type empty;
          }
        }
      }
      leaf filter-fhrp {
        description
          "Configure to not forward HSRP, GLBP, and VRRP packets on overlay";
        type empty;
      }
      container isis {
        description
          "ISIS interface subcommands";
        uses otv-isis-authentication-grouping;
        leaf bfd {
          description
            "Bidirectional Forwarding Protocol";
          type empty;
        }
        leaf csnp-interval {
          description
            "Set CSNP interval in seconds";
          type uint16 {
            range "0..65535";
          }
        }
        container hello {
          description
            "Add padding to IS-IS hello packets";
          container padding {
            description
              "Pad hello packets";
            presence "true";
            leaf always {
              description
                "Never pad hello packets if no prefix present";
              type empty;
            }
          }
        }
        container hello-interval {
          description
            "Set Hello interval in seconds";
          leaf value {
            type uint16 {
              range "1..65535";
            }
          }
          leaf minimal {
            description
              "Holdtime 1 second, interval depends on multiplier";
            type empty;
          }
        }
        leaf hello-multiplier {
          description
            "Set multiplier for Hello holding time";
          type uint16 {
            range "3..1000";
          }
        }
        leaf lsp-interval {
          description
            "Set LSP transmission interval";
          type uint64 {
            range "1..4294967295";
          }
        }
        container metric {
          description
            "Configure the metric for interface";
          choice default-maximum {
            case default-case {
              leaf default {
                type uint32 {
                  range "1..16777214";
                }
              }
            }
            case maximum-case {
              leaf maximum {
                description
                  "Maximum metric. All routers will exclude this link from their SPF";
                type empty;
              }
            }
          }
          leaf delay {
            type uint32 {
              range "1..16777214";
            }
          }
          leaf expense {
            type uint32 {
              range "1..16777214";
            }
          }
          leaf error {
            type uint32 {
              range "1..16777214";
            }
          }
        }
        leaf priority {
          description
            "Set priority for Designated Router election";
          type uint8 {
            range "0..127";
          }
        }
        leaf retransmit-interval {
          description
            "Set per-LSP retransmission interval";
          type uint16;
        }
        leaf retransmit-throttle-interval {
          description
            "Set interface LSP retransmission interval";
          type uint16;
        }
      }
      container join-interface {
        description
          "OTV VPN join-interface";
        uses ios-ifc:interface-grouping;
      }
      container suppress {
        description
          "Enable overlay packet suppression";
        leaf arp-nd {
          description
            "Suppress sending ARP and neighbor discovery packets on overlay";
          type empty;
        }
      }
      container use-adjacency-server {
        description
          "Point to remote Adjacency Server address";
        leaf remote-pri-ip {
          type inet:ipv4-address;
        }
        leaf remote-sec-ip {
          type inet:ipv4-address;
        }
        leaf unicast-only {
          description
            "Unicast Only Capability";
          type empty;
        }
      }
      leaf vpn-name {
        description
          "OTV VPN name";
        type string;
      }
    }
  }

  grouping config-otv-grouping {
    container fragmentation {
      description
        "Clear the DF (Don't Fragment) bit in the IP header";
      container join-interface {
        description
          "Allow fragmentation for overlays using this join-interface";
        uses ios-ifc:interface-grouping;
      }
    }
    container isis {
      description
        "OTV ISIS instance subcommands";
      list Overlay {
        description
          "Overlay interface";
        key "number";
        leaf number {
          type uint16 {
            range "0..512";
          }
        }
        uses otv-isis-overlay-grouping;
      }
      container site {
        description
          "Site Instance";
        uses otv-isis-site-grouping;
      }
    }
    list site {
      description
        "OTV site network configuration";
      key "bridge-domain";
      leaf bridge-domain {
        description
          "Bridge-domain to discover local OTV enabled devices";
        type uint16 {
          range "1..8192";
        }
      }
      container default {
        description
          "Set a command to its defaults";
        status obsolete;
        container otv {
          description
            "OTV site configuration subcommands";
          status obsolete;
          uses otv-isis-grouping;
        }
      }
      container otv {
        description
          "OTV site configuration subcommands";
        uses otv-isis-grouping;
      }
    }
    leaf site-identifier {
      description
        "OTV site id";
      type union {
        type uint32;
        type string;
      }
    }
  }

  grouping otv-isis-grouping {
    container isis {
      description
        "ISIS interface subcommands";
      uses otv-isis-authentication-grouping;
      leaf bfd {
        description
          "Bidirectional Forwarding Protocol";
        type empty;
      }
      container hello {
        description
          "Add padding to IS-IS hello packets";
        container padding {
          description
            "Pad hello packets";
          presence "true";
          leaf always {
            description
              "Never pad hello packets if no prefix present";
            type empty;
          }
        }
      }
      container hello-interval {
        description
          "Set Hello interval in seconds";
        leaf value {
          type uint16 {
            range "1..65535";
          }
        }
        leaf minimal {
          description
            "Holdtime 1 second, interval depends on multiplier";
          type empty;
        }
      }
      leaf hello-multiplier {
        description
          "Set multiplier for Hello holding time";
        type uint16 {
          range "3..1000";
        }
      }
      leaf priority {
        description
          "Set priority for Designated Router election";
        type uint8 {
          range "0..127";
        }
      }
    }
  }

  grouping otv-isis-overlay-grouping {
    uses otv-isis-authentication-grouping;
    container default {
      description
        "Set a command to its defaults";
      status obsolete;
      uses otv-isis-authentication-grouping;
      uses otv-isis-hostname-grouping;
      leaf delayed-deletion-interval {
        description
          "Set delayed deletion interval";
        status obsolete;
        type empty;
      }
      leaf log-adjacency-changes {
        description
          "Log changes in adjacency state";
        status obsolete;
        type empty;
      }
      leaf lsp-gen-interval {
        description
          "Minimum interval between regenerating same LSP";
        status obsolete;
        type empty;
      }
      leaf lsp-mtu {
        description
          "Set maximum LSP size";
        status obsolete;
        type empty;
      }
      leaf lsp-refresh-interval {
        description
          "Set LSP refresh interval";
        status obsolete;
        type empty;
      }
      leaf max-lsp-lifetime {
        description
          "Set maximum LSP lifetime";
        status obsolete;
        type empty;
      }
      leaf prc-interval {
        description
          "Minimum interval between partial route calculations";
        status obsolete;
        type empty;
      }
      leaf spf-interval {
        description
          "Minimum interval between SPF calculations";
        status obsolete;
        type empty;
      }
      container nsf {
        description
          "Non-stop forwarding";
        status obsolete;
        leaf cisco {
          description
            "Checkpoint method";
          status obsolete;
          type empty;
        }
        leaf interval {
          description
            "Minimum required stable interval between restarts";
          status obsolete;
          type empty;
        }
      }
      container skeptical {
        description
          "Be a cautious NSF helper when refresh adjacency";
        status obsolete;
        leaf interval {
          description
            "Interval during which holdtime will NOT be refreshed";
          status obsolete;
          type empty;
        }
      }
    }
    leaf delayed-deletion-interval {
      description
        "Set delayed deletion interval";
      type uint32 {
        range "1..86400";
      }
    }
    uses otv-isis-hostname-grouping;
    uses otv-isis-log-adjacency-changes-grouping;
    container lsp-gen-interval {
      description
        "Minimum interval between regenerating same LSP";
      leaf seconds {
        type uint8 {
          range "1..120";
        }
      }
      leaf milliseconds {
        type uint32 {
          range "1..120000";
        }
      }
      leaf wait {
        type uint32 {
          range "1..120000";
        }
      }
    }
    leaf lsp-mtu {
      description
        "Set maximum LSP size";
      type uint32 {
        range "128..4352";
      }
    }
    leaf lsp-refresh-interval {
      description
        "Set LSP refresh interval";
      type uint32 {
        range "1..65535";
      }
    }
    leaf max-lsp-lifetime {
      description
        "Set maximum LSP lifetime";
      type uint32 {
        range "1..65535";
      }
    }
    container nsf {
      description
        "Non-stop forwarding";
      leaf cisco {
        description
          "Checkpoint method";
        type empty;
      }
      leaf interval {
        description
          "Minimum required stable interval between restarts";
        type uint32 {
          range "0..1440";
        }
      }
    }
    container prc-interval {
      description
        "Minimum interval between partial route calculations";
      leaf seconds {
        type uint8 {
          range "1..120";
        }
      }
      leaf milliseconds {
        type uint32 {
          range "1..120000";
        }
      }
      leaf wait {
        type uint32 {
          range "1..120000";
        }
      }
    }
    uses otv-isis-skeptical-grouping;
    container spf-interval {
      description
        "Minimum interval between SPF calculations";
      leaf seconds {
        type uint8 {
          range "1..120";
        }
      }
      leaf milliseconds {
        type uint32 {
          range "1..120000";
        }
      }
      leaf wait {
        type uint32 {
          range "1..120000";
        }
      }
    }
  }

  augment "/ios:native/ios:otv" {
    uses config-otv-grouping;
  }

  augment "/ios:native/ios:interface/ios:overlay" {
    uses ios:interface-common-grouping;
    uses ios-eth:config-interface-ethernet-grouping;
    uses ios-otv:interface-overlay-grouping;
  }
}
