submodule Cisco-IOS-XE-hsrp {
  yang-version 1.1;
  belongs-to Cisco-IOS-XE-native {
    prefix ios;
  }

  import cisco-semver {
    prefix cisco-semver;
  }
  import Cisco-IOS-XE-types {
    prefix ios-types;
  }
  import ietf-inet-types {
    prefix inet;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE Native Hot Standby Redundancy Protocol(HSRP) Yang model.
     Copyright (c) 2021 by Cisco Systems, Inc.
     All rights reserved.";

  revision 2025-07-01 {
    description
      "- Deprecated decrement and shutdown under track and introduced new
         nodes";
    cisco-semver:module-version "4.0.0";
  }
  revision 2025-03-01 {
    description
      "- Added tailf:cli-diff-create-after and cli-diff-delete-before
         under ip-config primary address leaf
       - Removed tailf:cli-diff-create-after and cli-diff-delete-before
         under ip-config primary address leaf and added
         tailf:cli-remove-before-change;";
    cisco-semver:module-version "3.0.1";
  }
  revision 2024-11-01 {
    description
      "- Obsolete the nodes deprecated on 17.9 or before.
       - Reverting alt-name to model source file from annotation file";
    cisco-semver:module-version "3.0.0";
  }
  revision 2023-11-01 {
    description
      "- Added cli-diff-delete-before tailf statement to standby-list.";
    cisco-semver:module-version "2.1.1";
  }
  revision 2022-11-01 {
    description
      "- Update yang-version to 1.1
       - Added default value to mac-refresh leaf.";
    cisco-semver:module-version "2.1.0";
  }
  revision 2022-07-01 {
    description
      "- Add HSRP Group default priority
       - Deprecated standby bfd leaf and added a new leaf of type boolean
       - Fixed HSRP Group-number range.
       - Fixed standby track decrement range.
       - Added tailf statements to standby redirect authentication commands
       - Added tailf statement and default value to standby track decrement
       - Added description and modified standby group number range
       - Added cli-multi-value tailf statement for standby name and follow leaf
       - Removed tailf:cli-trim-default from decrement leaf.";
    cisco-semver:module-version "2.0.0";
  }
  revision 2022-03-01 {
    description
      "- Moved HSRP model code from interfaces.yang to hsrp.yang";
    cisco-semver:module-version "1.0.0";
  }

  grouping config-interface-hsrp-grouping {
    container standby {
      description
        "HSRP interface configuration commands";
      leaf version {
        description
          "HSRP version";
        type enumeration {
          enum 1;
          enum 2;
        }
        default "1";
      }
      leaf bfd-config {
        description
          "Enable HSRP BFD";
        default "true";
        type boolean;
      }
      leaf bfd {
        status obsolete;
        description
          "Enable HSRP BFD (OBSOLETE)";
        type empty;
      }
      container delay {
        description
          "HSRP initialisation delay";
        leaf minimum {
          description
            "Minimum delay";
          type uint16 {
            range "0..10000";
          }
        }
        leaf reload {
          description
            "Delay after reload";
          type uint16 {
            range "0..10000";
          }
        }
      }
      leaf mac-refresh {
        description
          "Refresh MAC cache on switch by periodically sending packet from virtual mac address";
        default "10";
        type uint8 {
          range "0..255";
        }
      }
      container use-bia {
        description
          "HSRP uses interface's burned in address";
        presence "true";
        container scope {
          description
            "Specify the scope of use-bia";
          leaf interface {
            description
              "Use-bia applies to all groups on this interface or sub-interface";
            type empty;
          }
        }
      }
      container redirect {
        description
          "Configure sending of ICMP Redirect messages with an HSRP virtual IP address as the gateway IP address";
        container advertisement {
          description
            "Redirect advertisement messages";
          container authentication {
            description
              "Authentication";
            container md5 {
              description
                "Use MD5 authentication";
              choice md5-choice {
                leaf key-chain {
                  description
                    "Set key chain";
                  type string;
                }
                container key-string {
                  description
                    "Set key string";
                  leaf encrypt {
                    type enumeration {
                      enum 0;
                      enum 7;
                    }
                  }
                  leaf string {
                    type string;
                  }
                  leaf timeout {
                    description
                      "Set timeout";
                    type uint16 {
                      range "0..32767";
                    }
                  }
                }
              }
            }
          }
        }
        container timers {
          description
            "Adjust redirect timers";
          leaf advertisement {
            type uint16 {
              range "10..180";
            }
          }
          leaf holddown {
            type uint16 {
              range "30..3600";
            }
          }
        }
        leaf unknown {
          description
            "Redirect to non-HSRP routers";
          default "true";
          type boolean;
        }
      }
      list standby-list {
        key "group-number";
        leaf group-number {
          description
            "HSRP group number. Supported range for HSRP version 1 is <0-255> and <0-4095> for HSRP version 2";
          type uint16 {
            range "0..4095";
          }
        }
        container authentication {
          description
            "Authentication";
          choice auth {
            leaf word {
              type string;
            }
            container md5 {
              description
                "Use MD5 authentication";
              container md5-config {
                choice md5-choice {
                  leaf key-chain {
                    description
                      "Set key chain";
                    type string;
                  }
                  container key-string {
                    description
                      "Set key string";
                    leaf encrypt {
                      type enumeration {
                        enum 0;
                        enum 7;
                      }
                    }
                    leaf string {
                      type string;
                    }
                    leaf timeout {
                      description
                        "Set timeout";
                      type uint16 {
                        range "0..32767";
                      }
                    }
                  }
                }
              }
              leaf key-chain {
                status obsolete;
                description
                  "Set key chain (OBSOLETE)";
                type string;
              }
              container key-string {
                status obsolete;
                description
                  "Set key string (OBSOLETE)";
                leaf encrypt {
                  status obsolete;
                  type enumeration {
                    enum 0;
                    enum 7;
                  }
                }
                leaf string {
                  status obsolete;
                  type string;
                }
                leaf timeout {
                  status obsolete;
                  description
                    "Set timeout (OBSOLETE)";
                  type uint16 {
                    range "0..32767";
                  }
                }
              }
            }
            leaf text {
              description
                "Plain text authentication";
              type string;
            }
          }
        }
        leaf follow {
          description
            "Name of HSRP group to follow";
          type string;
        }
        container ip-config {
          description
            "Enable HSRP and set the virtual IP address";
          presence "true";
          leaf address {
            type inet:ipv4-address;
          }
          list secondary-address {
            key "address";
            leaf address {
              type inet:ipv4-address;
            }
            leaf secondary {
              description
                "Make this IP address a secondary virtual IP address";
              mandatory true;
              type empty;
            }
          }
        }
        container ipv6-config {
          description
            "Enable HSRP IPv6 and set the virtual IP address";
          leaf ipv6-link-local {
            description
              "IPv6 link-local address";
            type union {
              type inet:ipv6-address;
              type enumeration {
                enum autoconfig;
              }
            }
          }
          list ipv6_prefix {
            key "prefix";
            leaf prefix {
              type ios-types:ipv6-prefix;
            }
          }
        }
        container ip {
          description
            "Enable HSRP and set the virtual IP address (OBSOLETE)";
          status obsolete;
          presence "true";
          leaf address {
            status obsolete;
            type inet:ipv4-address;
          }
          leaf secondary {
            status obsolete;
            description
              "Make this IP address a secondary virtual IP address (OBSOLETE)";
            type empty;
          }
        }
        leaf ipv6 {
          status obsolete;
          description
            "Enable HSRP IPv6 (OBSOLETE)";
          type union {
            type inet:ipv6-address;
            type ios-types:ipv6-prefix;
            type enumeration {
              enum autoconfig;
            }
          }
        }
        leaf mac-address {
          description
            "Virtual MAC address";
          type string;
        }
        leaf name {
          description
            "Redundancy name string";
          type string;
        }
        container preempt {
          description
            "Overthrow lower priority Active routers";
          presence "true";
          container delay {
            description
              "Wait before preempting";
            leaf minimum {
              description
                "Delay at least this long";
              type uint16 {
                range "0..3600";
              }
            }
            leaf reload {
              description
                "Delay after reload";
              type uint16 {
                range "0..3600";
              }
            }
            leaf sync {
              description
                "Wait for IP redundancy client";
              type uint16 {
                range "0..3600";
              }
            }
          }
        }
        leaf priority {
          description
            "Priority level";
          type uint8;
          default "100";
        }
        container redirect {
          status obsolete;
          description
            "Configure sending of ICMP Redirect messages with an HSRP virtual IP address as the gateway IP address";
          container advertisement {
            status obsolete;
            description
              "Redirect advertisement messages";
            container authentication {
              status obsolete;
              description
                "Authentication";
              container md5 {
                status obsolete;
                description
                  "Use MD5 authentication";
                leaf key-chain {
                  status obsolete;
                  description
                    "Set key chain";
                  type string;
                }
                container key-string {
                  status obsolete;
                  description
                    "Set key string";
                  leaf encrypt {
                    status obsolete;
                    type enumeration {
                      enum 0;
                      enum 7;
                    }
                  }
                  leaf string {
                    status obsolete;
                    type string;
                  }
                  leaf timeout {
                    status obsolete;
                    description
                      "Set timeout";
                    type uint16 {
                      range "0..32767";
                    }
                  }
                }
              }
            }
          }
          container timers {
            status obsolete;
            description
              "Adjust redirect timers";
            leaf advertisement {
              status obsolete;
              type uint16 {
                range "10..180";
              }
            }
            leaf holddown {
              status obsolete;
              type uint16 {
                range "30..3600";
              }
            }
          }
          leaf unknown {
            status obsolete;
            description
              "Redirect to non-HSRP routers";
            type empty;
          }
        }
        container timers {
          description
            "Hello and hold timers";
          container hello-interval {
            choice hello-interval-choice {
              leaf seconds {
                type uint8 {
                  range "1..254";
                }
              }
              leaf msec {
                description
                  "Specify hello interval in milliseconds";
                type uint16 {
                  range "15..999";
                }
              }
            }
          }
          container hold-time {
            choice hold-time-choice {
              leaf seconds {
                type uint8 {
                  range "1..255";
                }
              }
              leaf msec {
                description
                  "Specify hold time in milliseconds";
                type uint16 {
                  range "50..3000";
                }
              }
            }
          }
        }
        list track {
          description
            "Priority tracking";
          key "number";
          leaf number {
            type uint16 {
              range "1..1000";
            }
          }
          choice track-options {
            description
              "Configuration options for standby-track";
            leaf track-decrement {
              description
                "Priority decrement";
              type uint8 {
                range "1..255";
              }
            }
            leaf track-shutdown {
              description
                "Shutdown group";
              type empty;
            }
          }
          leaf decrement {
            status deprecated;
            description
              "Priority decrement(Deprecated, use track-options/track-decrement instead)";
            type uint8 {
              range "1..255";
            }
          }
          leaf shutdown {
            status deprecated;
            description
              "Shutdown group(Deprecated, use track-options/track-shutdown instead)";
            type empty;
          }
        }
      }
    }
  }
}
