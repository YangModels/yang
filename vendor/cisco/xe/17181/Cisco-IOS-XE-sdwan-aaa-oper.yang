module Cisco-IOS-XE-sdwan-aaa-oper {
  yang-version 1.1;
  namespace "http://cisco.com/ns/yang/Cisco-IOS-XE-sdwan-aaa-oper";
  prefix sdwan-aaa-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     the operational data of Software defined WAN (SDWAN) config-transaction Authentication, Authorization and Accounting (AAA).
     Copyright (c) 2024 by Cisco Systems, Inc.
     All rights reserved.";

  revision 2025-03-01 {
    description
      "Initial revision";
    reference
      "1.0.0";
    cisco-semver:module-version "1.0.0";
  }

  grouping sdwan-aaa-counters {
    description
      "Counters for active config-transaction sessions, authorized and accounted commands";
    leaf active-sessions {
      type uint64;
      description
        "The number of active config-transaction sessions";
    }
    leaf cmds-authorized {
      type uint64;
      description
        "The number of config-transaction commands that went through authorization";
    }
    leaf cmds-authorized-success {
      type uint64;
      description
        "The number of config-transaction commands that were successfully authorized";
    }
    leaf cmds-authorized-failure {
      type uint64;
      description
        "The number of config-transaction commands that failed to get authorized";
    }
    leaf cmds-accounted {
      type uint64;
      description
        "The number of config-transaction commands that were accounted";
    }
  }

  container sdwan-aaa-oper-data {
    config false;
    description
      "The operational data of SDWAN config-transaction Authentication Authorization and Accounting.";
    container sdwan-aaa-counters {
      presence "sdwan-aaa-counters";
      description
        "Counters for active config-transaction sessions, authorized and accounted commands";
      uses sdwan-aaa-ios-xe-oper:sdwan-aaa-counters;
    }
  }
}
