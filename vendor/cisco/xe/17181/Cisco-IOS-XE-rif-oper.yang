module Cisco-IOS-XE-rif-oper {
  yang-version 1.1;
  namespace "http://cisco.com/ns/yang/Cisco-IOS-XE-rif-oper";
  prefix rif-ios-xe-oper;

  import Cisco-IOS-XE-common-types {
    prefix common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Remote Interface Manager operational data.
     Copyright (c) 2025 by Cisco Systems, Inc.
     All rights reserved.";

  revision 2025-07-01 {
    description
      "Initial revision";
    reference
      "1.0.0";
    cisco-semver:module-version "1.0.0";
  }

  typedef rif-rsrc-port-state {
    type enumeration {
      enum rif-port-state-link-down {
        value 0;
        description
          "RIF port state down";
      }
      enum rif-port-state-link-up {
        value 1;
        description
          "RIF port state up";
      }
      enum rif-port-state-disabled {
        value 2;
        description
          "RIF port state disabled";
      }
    }
    description
      "RIF port state";
  }

  typedef rif-rsrc-chassis-state {
    type enumeration {
      enum unknown {
        value 0;
        description
          "RIF chassis init";
      }
      enum active {
        value 1;
        description
          "RIF chassis active";
      }
      enum standby {
        value 2;
        description
          "RIF chassis non active";
      }
      enum active-recovery {
        value 3;
        description
          "RIF chassis active recovery";
      }
      enum standby-recovery {
        value 4;
        description
          "RIF chassis non active recovery";
      }
    }
    description
      "RIF chassis state";
  }

  typedef rif-gw-reach-status {
    type enumeration {
      enum rif-gw-reach-status-none {
        value 0;
        description
          "Gateway reachability status not tracked";
      }
      enum rif-gw-reach-status-down {
        value 1;
        description
          "Gateway reachability status down";
      }
      enum rif-gw-reach-status-likely-down {
        value 2;
        description
          "Gateway reachability status likely down";
      }
      enum rif-gw-reach-status-up {
        value 3;
        description
          "Gateway reachability status up";
      }
    }
    description
      "Gateway reachability status";
  }

  grouping rif-mgr-gw-state {
    description
      "RIF manager gateway state";
    leaf gw-mntr-conf {
      type boolean;
      description
        "Gateway monitoring configured";
    }
    leaf gw-mntr-interval {
      type uint32;
      description
        "Gateway monitoring interval";
    }
    leaf gw-status {
      type rif-ios-xe-oper:rif-gw-reach-status;
      description
        "Local gateway status";
    }
    leaf peer-gw-status {
      type rif-ios-xe-oper:rif-gw-reach-status;
      description
        "Peer gateway status";
    }
  }

  grouping rif-mgr-lmp-stats {
    description
      "Dual Active Detection(DAD) link protocol statistics";
    leaf info-type-sent {
      type uint64;
      description
        "Total DAD packet information type sent";
    }
    leaf sol-info-type-sent {
      type uint64;
      description
        "Total DAD packet solicit information type sent";
    }
    leaf unsol-info-type-sent {
      type uint64;
      description
        "Total DAD packet un-solicit information type sent";
    }
    leaf reload-type-sent {
      type uint64;
      description
        "Total DAD packet reload type sent";
    }
    leaf recovery-type-sent {
      type uint64;
      description
        "Total DAD packet recovery type sent";
    }
    leaf gw-info-type-sent {
      type uint64;
      description
        "Total DAD packet gateway information type sent";
    }
    leaf sol-enquiry-type-sent {
      type uint64;
      description
        "Total DAD packet solicit enquiry type sent";
    }
    leaf unsol-enquiry-type-sent {
      type uint64;
      description
        "Total DAD packet un-solicit enquiry type sent";
    }
    leaf enquiry-type-sent {
      type uint64;
      description
        "Total DAD packet enquiry type sent";
    }
    leaf info-type-recv {
      type uint64;
      description
        "Total DAD packet information type received";
    }
    leaf sol-info-type-recv {
      type uint64;
      description
        "Total DAD packet solicit information type received";
    }
    leaf unsol-info-type-recv {
      type uint64;
      description
        "Total DAD packet un-solicit information type received";
    }
    leaf reload-type-recv {
      type uint64;
      description
        "Total DAD packet reload type received";
    }
    leaf recovery-type-recv {
      type uint64;
      description
        "Total DAD packet recovery type received";
    }
    leaf gw-info-type-recv {
      type uint64;
      description
        "Total DAD packet gateway information type received";
    }
    leaf enquiry-type-recv {
      type uint64;
      description
        "Total DAD packet enquiry type received";
    }
    leaf sol-enquiry-type-recv {
      type uint64;
      description
        "Total DAD packet solicit enquiry type received";
    }
    leaf unsol-enquiry-type-recv {
      type uint64;
      description
        "Total DAD packet un-solicit enquiry type received";
    }
  }

  grouping rif-mgr-rp-ka-info {
    description
      "RIF manager RP keepalive information";
    leaf local-seq-num-sent {
      type int32;
      description
        "Last RP keepalive sequence number sent to the peer";
    }
    leaf local-ack-num-rcvd {
      type int32;
      description
        "Last RP keepalive acknowledgement number received from the peer";
    }
    leaf peer-seq-num-rcvd {
      type int32;
      description
        "Last RP keepalive sequence number received from the peer";
    }
    leaf peer-ack-num-sent {
      type int32;
      description
        "Last RP keepalive acknowledgement number sent to the peer";
    }
    leaf local-ka-sent-time {
      type yang:date-and-time;
      description
        "Time when last RP keepalive sent to the peer";
    }
    leaf peer-ka-rcvd-time {
      type yang:date-and-time;
      description
        "Time when last RP keepalive received from the peer";
    }
  }

  grouping rif-mgr-rmi-link {
    description
      "RMI link Statistics";
    leaf rmi-re-establish-count {
      type uint64;
      description
        "Total RMI link re-establish count";
    }
    leaf rmi-link-down-time {
      when "(../../rmi-state = 'rif-port-state-link-down')";
      type yang:date-and-time;
      description
        "Time when Redundancy Management Interface(RMI) link went down";
    }
    leaf rmi-link-up-time {
      when "(../../rmi-state = 'rif-port-state-link-up')";
      type yang:date-and-time;
      description
        "Time when Redundancy Management Interface(RMI) link came up ";
    }
    leaf local-rmi-ip {
      type inet:ip-address;
      description
        "Local RMI IP address";
    }
    leaf remote-rmi-ip {
      type inet:ip-address;
      description
        "Remote RMI IP address";
    }
  }

  grouping rif-rsrc-state-info {
    description
      "Route Processor(RP)-Redundancy Management Interface(RMI) port information";
    leaf chass-num {
      type uint8;
      description
        "Chassis number";
    }
    leaf rp-state {
      type rif-ios-xe-oper:rif-rsrc-port-state;
      description
        "Route Processor port state";
    }
    leaf rmi-state {
      type rif-ios-xe-oper:rif-rsrc-port-state;
      description
        "Redundancy Management Interface(RMI) port state";
    }
    container rmi-link {
      description
        "RMI link re-establish";
      uses rif-ios-xe-oper:rif-mgr-rmi-link;
    }
    leaf current-chassis-state {
      type rif-ios-xe-oper:rif-rsrc-chassis-state;
      description
        "Current chassis state indicating active, standby or recovery mode";
    }
    leaf peer-chassis-state {
      type rif-ios-xe-oper:rif-rsrc-chassis-state;
      description
        "Peer chassis state indicating active, standby or recovery mode";
    }
    container gw-state {
      description
        "Gateway state";
      uses rif-ios-xe-oper:rif-mgr-gw-state;
    }
  }

  grouping rif-mgr-gw-mntr-stats {
    description
      "Gateway Monitoring Statistics";
    leaf gw-l2-probes-tx {
      type uint64;
      description
        "Number of L2 probes sent";
    }
    leaf gw-l3-probes-tx {
      type uint64;
      description
        "Number of L3 probes sent";
    }
    leaf gw-l2-resp-rx {
      type uint64;
      description
        "Number of L2 responses received";
    }
    leaf gw-l3-resp-rx {
      type uint64;
      description
        "Number of L3 responses received";
    }
    leaf gw-l2-resp-fail {
      type uint64;
      description
        "Number of L2 responses failed";
    }
    leaf gw-l3-resp-fail {
      type uint64;
      description
        "Number of L3 responses failed";
    }
    leaf gw-last-fail-count {
      type uint64;
      description
        "Sum of the recent continuous L2 and L3 failures";
    }
    leaf gw-last-fail-time {
      type yang:date-and-time;
      description
        "Last fail time";
    }
    leaf gw-long-fail-count {
      type uint64;
      description
        "Sum of the longest continuous L2 and L3 failures";
    }
    leaf gw-long-fail-time {
      type yang:date-and-time;
      description
        "Longest fail time";
    }
  }

  grouping rif-mgr-rmi-stats {
    description
      "Route Processor(RP)-Redundancy Management Interface(RMI) statistics";
    leaf chass-num {
      type uint8;
      description
        "Chassis number";
    }
    leaf rmi-enabled {
      type boolean;
      description
        "Set to true when RMI is configured";
    }
    leaf smgr-rp-down {
      type boolean;
      description
        "Stack Mgr has reported Route Processor link down or not";
    }
    leaf dad-link-stk-mgr {
      type boolean;
      description
        "DAD link status reported to Stack Manager";
    }
    container lmp-stats {
      when "(../rmi-enabled = 'true')";
      description
        "Link management protocol statistics";
      uses rif-ios-xe-oper:rif-mgr-lmp-stats;
    }
    leaf rp-link-down-time {
      when "(../../rif-rsrc-state-info/rp-state = 'rif-port-state-link-down')";
      type yang:date-and-time;
      description
        "Time when Route Processor link went down";
    }
    leaf rp-link-up-time {
      when "(../../rif-rsrc-state-info/rp-state = 'rif-port-state-link-up')";
      type yang:date-and-time;
      description
        "Time when Route Processor Link came up";
    }
    container rp-ka-info {
      when "(../rmi-enabled = 'true')";
      description
        "RP keepalive information";
      uses rif-ios-xe-oper:rif-mgr-rp-ka-info;
    }
    container gw-mntr-stats {
      when "(../rmi-enabled = 'true')";
      description
        "Gateway Monitoring Statistics";
      uses rif-ios-xe-oper:rif-mgr-gw-mntr-stats;
    }
  }

  container rif-oper-data {
    config false;
    description
      "Remote Interface Manager(RIF) resource operational data";
    list location {
      key "fru slot bay chassis node";
      description
        "A list of data provider locations";
      uses common-types-ios-xe:extended-location;
      list rif-rsrc-state-info {
        key "chass-num";
        description
          "RIF resource data";
        uses rif-ios-xe-oper:rif-rsrc-state-info;
      }
      list rmi-stats {
        key "chass-num";
        description
          "RIF statistics";
        uses rif-ios-xe-oper:rif-mgr-rmi-stats;
      }
    }
  }
}
