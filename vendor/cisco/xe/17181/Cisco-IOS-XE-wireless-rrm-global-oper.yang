module Cisco-IOS-XE-wireless-rrm-global-oper {
  yang-version 1.1;
  namespace "http://cisco.com/ns/yang/Cisco-IOS-XE-wireless-rrm-global-oper";
  prefix wireless-rrm-global-oper;

  import Cisco-IOS-XE-wireless-rrm-types {
    prefix wireless-rrm-types;
  }
  import Cisco-IOS-XE-wireless-types {
    prefix wireless-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains rrm operational data.
     Copyright (c) 2021-2023 by Cisco Systems, Inc.
     All rights reserved.";

  revision 2023-07-01 {
    description
      "- Added coverage information
       - Added SNR information
       - Added RSSI information";
    reference
      "1.3.0";
    cisco-semver:module-version "1.3.0";
  }
  revision 2023-03-01 {
    description
      "Added FRA statistics informations";
    reference
      "1.2.0";
    cisco-semver:module-version "1.2.0";
  }
  revision 2022-11-01 {
    description
      "- Update yang-version to 1.1
       - Added channel energy levels
       - Added RRM client data
       - Added spectrum AQ worst data
       - Added scan radio type enums";
    reference
      "1.1.0";
    cisco-semver:module-version "1.1.0";
  }
  revision 2022-07-01 {
    description
      "Initial revision";
    reference
      "1.0.0";
    cisco-semver:module-version "1.0.0";
  }

  typedef enm-scan-radio-type {
    type enumeration {
      enum radio-type-legacy {
        value 0;
        description
          "Scan radio type legacy.";
      }
      enum radio-type-rhl {
        value 1;
        description
          "Scan radio type AUX RHL";
      }
      enum radio-type-pine {
        value 2;
        description
          "Scan radio type AUX pine.";
      }
    }
    description
      "Scan radio type";
  }

  grouping st-rrm-client-data {
    description
      "RRM client operational data";
    leaf phy-type {
      type wireless-rrm-types:enm-rrm-phy-type;
      description
        "Radio type";
    }
    leaf last-chd-run {
      type yang:date-and-time;
      description
        "Timestamp at which CHD algorithm was last run";
    }
    leaf disassociations {
      type uint32;
      description
        "Number of dissociations by client";
    }
    leaf rejections {
      type uint32;
      description
        "Number of rejections by client";
    }
  }

  grouping st-rrm-one-shot-counters-data {
    description
      "Transmit power and channel update count";
    leaf phy-type {
      type wireless-rrm-types:enm-rrm-phy-type;
      description
        "Radio type";
    }
    leaf power-counter {
      type uint32;
      description
        "Transmit power update count";
    }
  }

  grouping st-rrm-channel-params-data {
    description
      "RRM channel parameter data";
    leaf phy-type {
      type wireless-rrm-types:enm-rrm-phy-type;
      description
        "Radio type";
    }
    leaf min-dwell {
      type uint32;
      units "seconds";
      description
        "Minimum channel dwell time";
    }
    leaf avg-dwell {
      type uint32;
      units "seconds";
      description
        "Average channel dwell time";
    }
    leaf max-dwell {
      type uint32;
      units "seconds";
      description
        "Maximum channel dwell time";
    }
    leaf min-rssi {
      type int8;
      units "dBm";
      description
        "Minimum channel energy level";
    }
    leaf max-rssi {
      type int8;
      units "dBm";
      description
        "Maximum channel energy level";
    }
    leaf avg-rssi {
      type int8;
      units "dBm";
      description
        "Average channel energy level";
    }
    leaf channel-counter {
      type uint32;
      description
        "Channel Update Count";
    }
  }

  grouping snr-info-data {
    description
      "Information related to client signal to noise ratios";
    leaf snr {
      type int8;
      description
        "Client signal to noise ratio";
    }
    leaf num-clients {
      type int32;
      description
        "Number of clients per SNR";
    }
  }

  grouping rssi-info-data {
    description
      "Information related to client signal strengths";
    leaf rssi {
      type int8;
      description
        "Received signal strength from the client";
    }
    leaf num-clients {
      type int32;
      description
        "Number of clients per RSSI";
    }
  }

  grouping st-coverage-info-data {
    description
      "Coverage information";
    leaf failed-client-count {
      type uint32;
      description
        "Number of failed clients";
    }
    list snr-info {
      max-elements 10;
      description
        "Client signal to noise ratio";
      uses wireless-rrm-global-oper:snr-info-data;
    }
    list rssi-info {
      max-elements 7;
      description
        "Received signal strength from the client";
      uses wireless-rrm-global-oper:rssi-info-data;
    }
  }

  grouping st-spectrum-aq-worst {
    description
      "Air quality index operational data";
    leaf band-id {
      type uint8;
      description
        "Band ID";
    }
    leaf detecting-ap-name {
      type string;
      description
        "AP name";
    }
    leaf channel-num {
      type uint8;
      description
        "Channel number";
    }
    leaf min-aqi {
      type uint8;
      description
        "Min air quality index";
    }
    leaf aqi {
      type uint8;
      description
        "Air quality index";
    }
    leaf total-intf-device-count {
      type uint8;
      description
        "Interference device count";
    }
    leaf wtp-ca-si-capable {
      type wireless-rrm-types:enm-ca-si-capable;
      description
        "AP SI capable or not";
    }
    leaf scan-radio-type {
      type wireless-rrm-global-oper:enm-scan-radio-type;
      description
        "Scan radio type";
    }
  }

  grouping st-rrm-fra-statistics {
    description
      "RRM flexible radio statistics";
    leaf dual-band-monitor-to-24ghz {
      type uint32;
      description
        "Dual-band radio transition from monitor to 2.4GHz";
    }
    leaf dual-band-monitor-to-5ghz {
      type uint32;
      description
        "Dual-band radio transition from monitor to 5GHz";
    }
    leaf dual-band-24ghz-to-5ghz {
      type uint32;
      description
        "Dual-band radio transition from 2.4GHz to 5GHz";
    }
    leaf dual-band-24ghz-to-monitor {
      type uint32;
      description
        "Dual-band radio transition from 2.4GHz to monitor";
    }
    leaf dual-band-5ghz-to-24ghz {
      type uint32;
      description
        "Dual-band radio transition from 5GHz to 2.4GHz";
    }
    leaf dual-band-5ghz-to-monitor {
      type uint32;
      description
        "Dual-band radio transition from 5GHz to monitor";
    }
    leaf sec-radio-monitor-to-5ghz {
      type uint32;
      description
        "Secondary radio transition from monitor to 5GHz";
    }
    leaf sec-radio-5ghz-to-monitor {
      type uint32;
      description
        "Secondary radio transition from 5GHz to monitor";
    }
    leaf dual-band-6ghz-to-5ghz {
      type uint32;
      description
        "Dual-band radio transition from 6GHz to 5GHz";
    }
    leaf dual-band-5ghz-to-6ghz {
      type uint32;
      description
        "Dual-band radio transition from 5GHz to 6GHz";
    }
  }

  grouping ewlc-emulated-radio-config {
    description
      "Radio oper data";
    leaf ap-mac {
      type yang:mac-address;
      description
        "MAC address";
    }
    leaf slot-id {
      type uint8;
      description
        "Timestamp at which CHD algorithm was last run";
    }
    leaf name {
      type string;
      description
        "WTP name";
    }
    leaf spectrum-capable {
      type empty;
      description
        "AP is cleanair capable or not";
    }
    leaf num-slots {
      type uint8;
      description
        "Number of slots";
    }
    leaf mesh-radio-role {
      type wireless-types:ap-role;
      description
        "Radio Role";
    }
    leaf ap-up-time {
      type yang:date-and-time;
      description
        "AP up time";
    }
    leaf capwap-up-time {
      type yang:date-and-time;
      description
        "CAPWAP uptime";
    }
    leaf is-sia-rptnc-present {
      type empty;
      description
        "Antenna present or not";
    }
    leaf is-sia-dart-present {
      type empty;
      description
        "Antenna type present or not";
    }
    leaf sia-marlin4-present {
      type empty;
      description
        "Antenna type present or not";
    }
  }

  grouping st-spectrum-band-data {
    description
      "AP spectrum config for band";
    leaf band-id {
      type wireless-types:enm-ewlc-dot11-radio-band;
      description
        "Band of AP for configuration";
    }
    leaf spectrum-admin-state {
      type boolean;
      description
        "Spectrum admin state";
    }
  }

  grouping st-spectrum-ap-band-config {
    description
      "AP spectrum band config";
    leaf ap-mac {
      type yang:mac-address;
      description
        "MAC address of the AP";
    }
    list spectrum-band-config {
      description
        "Spectrum band config";
      uses wireless-rrm-global-oper:st-spectrum-band-data;
    }
  }

  container rrm-global-oper-data {
    config false;
    description
      "RRM operational data";
    list rrm-one-shot-counters {
      key "phy-type";
      description
        "Transmit power and channel update count";
      uses wireless-rrm-global-oper:st-rrm-one-shot-counters-data;
    }
    list rrm-channel-params {
      key "phy-type";
      description
        "RRM channel parameter data";
      uses wireless-rrm-global-oper:st-rrm-channel-params-data;
    }
    list spectrum-aq-worst-table {
      key "band-id";
      description
        "Air quality index data";
      uses wireless-rrm-global-oper:st-spectrum-aq-worst;
    }
    list radio-oper-data-24g {
      key "wtp-mac radio-slot-id";
      description
        "2.4 ghz radio oper data";
      uses wireless-rrm-global-oper:ewlc-emulated-radio-config;
      uses wireless-types:radio-slot-key;
    }
    list radio-oper-data-5g {
      key "wtp-mac radio-slot-id";
      description
        "5 ghz radio oper data";
      uses wireless-rrm-global-oper:ewlc-emulated-radio-config;
      uses wireless-types:radio-slot-key;
    }
    list radio-oper-data-6ghz {
      key "wtp-mac radio-slot-id";
      description
        "6 ghz radio oper data";
      uses wireless-types:radio-slot-key;
      uses wireless-rrm-global-oper:ewlc-emulated-radio-config;
    }
    list spectrum-band-config-data {
      key "ap-mac";
      description
        "AP spectrum config";
      uses wireless-rrm-global-oper:st-spectrum-ap-band-config;
    }
    list radio-oper-data-dualband {
      key "wtp-mac radio-slot-id";
      description
        "Dual band radio oper data";
      uses wireless-rrm-global-oper:ewlc-emulated-radio-config;
      uses wireless-types:radio-slot-key;
    }
    list rrm-client-data {
      key "phy-type";
      description
        "RRM client data";
      uses wireless-rrm-global-oper:st-rrm-client-data;
    }
    container rrm-fra-stats {
      presence "rrm-fra-stats";
      description
        "RRM flexible radio statistics";
      uses wireless-rrm-global-oper:st-rrm-fra-statistics;
    }
    list rrm-coverage {
      key "wtp-mac radio-slot-id";
      description
        "Coverage information";
      uses wireless-types:radio-slot-key;
      uses wireless-rrm-global-oper:st-coverage-info-data;
    }
  }
}
