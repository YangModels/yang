module Cisco-IOS-XE-controller-shdsl-oper {
  yang-version 1.1;
  namespace "http://cisco.com/ns/yang/Cisco-IOS-XE-controller-shdsl-oper";
  prefix shdsl-ios-xe-oper;

  import Cisco-IOS-XE-controller-shdsl-common {
    prefix shdsl-ios-xe-common;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring controller SHDSL operational information.
     Copyright (c) 2019, 2022 by Cisco Systems, Inc.
     All rights reserved.";

  revision 2022-11-01 {
    description
      "Update yang-version to 1.1";
    reference
      "1.1.0";
    cisco-semver:module-version "1.1.0";
  }
  revision 2020-03-01 {
    description
      "Initial revision";
    reference
      "1.0.0";
    cisco-semver:module-version "1.0.0";
  }

  grouping shdsl-controller-info {
    description
      "SHDSL Controller Information";
    leaf state {
      type shdsl-ios-xe-common:controller-state;
      description
        "Controller State";
    }
    leaf hardware {
      type string;
      description
        "Hardware";
    }
    leaf efm-capabilities {
      type string;
      description
        "Ethernet Capabilities";
    }
    leaf atm-capabilities {
      type string;
      description
        "ATM Capabilities";
    }
    leaf termination {
      type shdsl-ios-xe-common:term-type;
      description
        "Termination";
    }
    leaf configured-mode {
      type shdsl-ios-xe-common:mode-type;
      description
        "Configured Mode";
    }
    leaf vendor {
      type string;
      description
        "Vendor";
    }
    leaf chipset {
      type string;
      description
        "Description";
    }
    leaf phy-source {
      type string;
      description
        "Phy source";
    }
    leaf phy-firmware-files {
      type string;
      description
        "Phy Firmware Files";
    }
    leaf idc-firmware-version {
      type string;
      description
        "Integrated Device Control Firmware version";
    }
    leaf dfe-firmware-version {
      type string;
      description
        "Digital Front End Firmware Version";
    }
    list groups-conf {
      description
        "Groups Configuration";
      uses shdsl-ios-xe-common:shdsl-configured-group;
    }
  }

  container shdsl-oper-data {
    config false;
    description
      "SHDSL controller information";
    list shdsl-info {
      key "slot-num subslot-num";
      description
        "SHDSL controller information";
      uses shdsl-ios-xe-oper:shdsl-controller-info;
      uses shdsl-ios-xe-common:shdsl-slot-info-key;
    }
  }
}
