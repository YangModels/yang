module Cisco-IOS-XE-wireless-rlan-cfg {
  yang-version 1.1;
  namespace "http://cisco.com/ns/yang/Cisco-IOS-XE-wireless-rlan-cfg";
  prefix wireless-rlan-cfg;

  import Cisco-IOS-XE-wireless-enum-types {
    prefix wireless-enum-types;
  }
  import Cisco-IOS-XE-wireless-types {
    prefix wireless-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing RLAN configuration
      Copyright (c) 2020, 2023 by Cisco Systems, Inc.
       All rights reserved.";

  revision 2025-03-01 {
    description
      "Added Dot1x and webauth configuration constraint";
    reference
      "5.0.0";
    cisco-semver:module-version "5.0.0";
  }
  revision 2023-07-01 {
    description
      "Added Layer 3 forwarding support";
    reference
      "4.0.0";
    cisco-semver:module-version "4.0.0";
  }
  revision 2023-03-01 {
    description
      "- Added ND rate limiting configuration";
    reference
      "3.1.0";
    cisco-semver:module-version "3.1.0";
  }
  revision 2022-11-01 {
    description
      "Update yang-version to 1.1
       - Added ARP rate limiting configuration
       - Added constraints on Voice and Data VLANs configuration in RLAN policy profile";
    reference
      "3.0.0";
    cisco-semver:module-version "3.0.0";
  }
  revision 2022-03-01 {
    description
      "- Added support for authentication fallback for RLAN clients
       - Added support for dot1x EAP timer configuration for RLAN clients";
    reference
      "2.2.0";
    cisco-semver:module-version "2.2.0";
  }
  revision 2021-11-01 {
    description
      "- Added fabric profile name in RLAN policy profile";
    reference
      "2.1.0";
    cisco-semver:module-version "2.1.0";
  }
  revision 2021-03-01 {
    description
      "- Add ASCII 32-126 and leading/trailing spaces restriction for remote lan name and remote lan policy name";
    reference
      "2.0.0";
    cisco-semver:module-version "2.0.0";
  }
  revision 2020-07-01 {
    description
      " - Updated description string from User Private Network to User Defined (Private) Network";
    reference
      "1.2.1";
    cisco-semver:module-version "1.2.1";
  }
  revision 2019-11-01 {
    description
      "- Added User Private Network configuration.
       - Added User Private Network configuration for unicast
       - Added power-level-id config on Remote LAN policy profile";
    reference
      "1.2.0";
    cisco-semver:module-version "1.2.0";
  }
  revision 2019-05-01 {
    description
      "- Added MDNS mode config on RLAN Profile and MDNS service policy on RLAN Policy.
       - Added semantic version";
    reference
      "1.1.0";
    cisco-semver:module-version "1.1.0";
  }
  revision 2019-01-05 {
    description
      "Initial revision";
    reference
      "1.0.0";
    cisco-semver:module-version "1.0.0";
  }

  grouping st-split-tunnel {
    description
      "Configuration of Split tunnel";
    leaf split-tunnel-enabled {
      type boolean;
      description
        "Enable or Disable split tunnel";
    }
    leaf acl-name {
      type string {
        length "0..31" {
          error-message "Invalid string length for ACL name:Valid string has be 0 to 32 characters";
          error-app-tag "must-violation";
        }
      }
      description
        "ACL in split tunnel";
    }
    leaf split-tunnel-override {
      type boolean;
      description
        "Split tunnel override";
    }
    leaf split-tunnel-gateway {
      type inet:ip-address;
      description
        "Gateway for split tunnel";
    }
    leaf split-tunnel-netmask {
      type inet:ip-address;
      description
        "Netmask for split tunnel";
    }
  }

  grouping st-multi-domain-vlans {
    description
      "Configure voice and data VLAN's";
    leaf voice-vlan-id {
      type uint16;
      must '(../voice-vlan-id >= 0 and ../voice-vlan-id <= 4094)' {
        error-message "Voice VLAN ID must be in range of 0..4094";
        error-app-tag "must-violation";
      }
      description
        "Configure Voice VLAN ID in range of 0..4094";
    }
    leaf data-vlan-id {
      type uint16;
      must '(../data-vlan-id >= 0 and ../data-vlan-id <= 4094)' {
        error-message "Data VLAN ID must be in range of 0..4094";
        error-app-tag "must-violation";
      }
      description
        "Configure Data VLAN ID in range of 0..4094";
    }
  }

  grouping st-flow-monitor {
    description
      "Flexible Netflow configuration";
    leaf flow-monitor-ingress-name {
      type string {
        length "1..32" {
          error-message "Invalid string length for Wireless flow monitor ingress names:Valid string has be 1 to 32 characters";
          error-app-tag "must-violation";
        }
      }
      must "../../central-switching = 'true' and ../ingress-enable = 'true' " {
        error-message "RLAN switching policy central-switching and ingress-enable should be enabled when using flow monitors";
        error-app-tag "must-violation";
      }
      description
        "Enable flow monitor on ingress traffic";
    }
    leaf flow-monitor-egress-name {
      type string {
        length "1..32" {
          error-message "Invalid string length for Wireless flow monitor egress names:Valid string has be 1 to 32 characters";
          error-app-tag "must-violation";
        }
      }
      must "../../central-switching = 'true' and ../egress-enable = 'true' " {
        error-message "RLAN switching policy central-switching and egress-enable should be enabled when using flow monitors";
        error-app-tag "must-violation";
      }
      description
        "Enable flow monitor on egress traffic";
    }
    leaf ingress-enable {
      type boolean;
      must "../../central-switching = 'true' and (string-length(../flow-monitor-ingress-name) > 0)" {
        error-message "RLAN switching policy central-switching should be enabled and ingress-name must be entered when using flow monitors";
        error-app-tag "must-violation";
      }
      description
        "Enable/Disable flow monitor on ingress traffic";
    }
    leaf egress-enable {
      type boolean;
      must "../../central-switching = 'true' and (string-length(../flow-monitor-egress-name) > 0)" {
        error-message "RLAN switching policy central-switching should be enabled and egress-name must be entered when using flow monitors";
        error-app-tag "must-violation";
      }
      description
        "Enable/Disable flow monitor on egress traffic";
    }
  }

  grouping blacklist-params {
    description
      "Set client blacklisting listing on RLAN";
    leaf is-blacklist-enabled {
      type boolean;
      default "true";
      description
        "Enable/Disable blacklisting";
    }
    leaf blacklist-timeout {
      type uint32 {
        range "0 .. 2147483647";
      }
      default "60";
      description
        "Set time the client will be excluded";
    }
  }

  grouping upn-config {
    description
      "User Defined (Private) Network related configuration";
    leaf is-upn-restrict-enable {
      type boolean;
      default "false";
      description
        "User Defined (Private) Network status";
    }
    leaf upn-unicast-disable {
      type boolean;
      default "false";
      description
        "User Defined (Private) Network Unicast disable status";
    }
  }

  grouping rlan-policy-profile-arprate {
    description
      "Per client arp rate limiting configuration";
    leaf rate-none {
      type boolean;
      default "false";
      description
        "Enable or disable the client arp rate limiting";
    }
    leaf rate-pps {
      type uint16 {
        range "15 .. 1500";
      }
      default "100";
      description
        "Set the arp packet rate allowed";
    }
    leaf burst-interval {
      type uint8 {
        range "3 .. 255";
      }
      default "5";
      description
        "Set the burst count for the client to be excluded";
    }
  }

  grouping rlan-policy-profile-ndprate {
    description
      "Per client ND rate limiting configuration";
    leaf rate-none {
      type boolean;
      default "false";
      description
        "Enable or disable the client ND rate limiting";
    }
    leaf rate-pps {
      type uint16 {
        range "15 .. 1500";
      }
      default "100";
      description
        "Set the ND packet rate allowed";
    }
    leaf burst-interval {
      type uint8 {
        range "3 .. 255";
      }
      default "5";
      description
        "Set the burst count for the client to be excluded";
    }
  }

  grouping st-rlan-policy-profile-config {
    description
      "Remote LAN policy profile";
    leaf profile-name {
      type string {
        length "1..32" {
          error-message "Invalid string length for Remote LAN Policy Profile name:Valid string has be 1 to 32 characters";
          error-app-tag "must-violation";
        }
        pattern '[!-~]([ -~]*[!-~])?';
      }
      description
        "Remote LAN Policy Profile Name";
    }
    leaf status {
      type boolean;
      default "false";
      description
        "Remote LAN Policy Profile status";
    }
    leaf description {
      type string;
      description
        "Remote LAN Policy Profile Description";
    }
    leaf ipv4-acl {
      type string {
        length "0..31" {
          error-message "Invalid string length for IPv4 ACL name:Valid string has be 0 to 32 characters";
          error-app-tag "must-violation";
        }
      }
      description
        "Name of IPv4 ACL";
    }
    leaf ipv6-acl {
      type string {
        length "0..31" {
          error-message "Invalid string length for IPv6 ACL name:Valid string has be 0 to 32 characters";
          error-app-tag "must-violation";
        }
      }
      description
        "Configure the name of IPv6 ACL";
    }
    leaf aaa-override {
      type boolean;
      default "false";
      description
        "Enable or Disable AAA override for the global RLAN parameters.";
    }
    leaf aaa-policy-name {
      type string;
      default "default-aaa-policy";
      description
        "AAA policy name.";
    }
    leaf central-switching {
      type boolean;
      default "true";
      description
        "Enable or Disable central switching";
    }
    leaf central-dhcp {
      type boolean;
      description
        "Enable or Disable central DHCP";
    }
    leaf interface-name {
      type string;
      default "1";
      description
        "Name of the VLAN name for the vlan-acl mapping.";
    }
    leaf poe {
      type boolean;
      description
        "Enable or Disable poe";
    }
    leaf host-mode {
      type wireless-types:enm-host-mode;
      default "single-host-mode";
      description
        "Configure the host mode for the remote LAN";
    }
    container host-mode-vlans {
      description
        "Change the host mode VLAN for the remote LAN";
      uses wireless-rlan-cfg:st-multi-domain-vlans;
    }
    leaf violation-mode {
      type wireless-types:enm-violation-mode;
      description
        "Violation mode for the remote LAN.";
    }
    container blacklist {
      description
        "Configure the blacklist for the remote LAN";
      uses wireless-rlan-cfg:blacklist-params;
    }
    leaf pre-auth {
      type boolean;
      description
        "Enable or Disable pre_auth";
    }
    leaf session-timeout {
      type uint32 {
        range "0 .. 86400";
      }
      default "28800";
      description
        "Configure the session timeout for the remote LAN";
    }
    container flow-monitor-ipv4 {
      description
        "Configure the flow monitor IPv4 for the remote LAN";
      uses wireless-rlan-cfg:st-flow-monitor;
    }
    container flow-monitor-ipv6 {
      description
        "Configure the flow monitor IPv6 for the remote LAN";
      uses wireless-rlan-cfg:st-flow-monitor;
    }
    container split-tunnel-param {
      description
        "Configure the split tunnel for the remote LAN";
      uses wireless-rlan-cfg:st-split-tunnel;
    }
    leaf dhcp-server {
      type inet:ipv4-address;
      description
        "Configure DHCP parameters for Remote-LAN";
    }
    leaf is-dhcp-enabled {
      type boolean;
      default "false";
      description
        "Configure DHCP enabled for Remote-LAN";
    }
    leaf accounting-list {
      type string;
      description
        "Configure the accounting list for IEEE 802.1x";
    }
    leaf mdns-policy-name {
      type string;
      default "default-mdns-service-policy";
      description
        "The Name of MDNS service policy";
    }
    container upn {
      description
        "Configure User Defined (Private) Network policies";
      uses wireless-rlan-cfg:upn-config;
    }
    leaf power-level-id {
      type uint8 {
        range "1 .. 4";
      }
      default "4";
      description
        "Power level for the AP PoE port";
    }
    leaf fabric-profile-name {
      type string;
      description
        "Fabric profile name";
    }
    container arprate-params {
      description
        "ARP rate limiting configuration on RLAN policy profile";
      uses wireless-rlan-cfg:rlan-policy-profile-arprate;
    }
    container ndp-rate-params {
      description
        "ND rate limiting configuration on RLAN policy profile";
      uses wireless-rlan-cfg:rlan-policy-profile-ndprate;
    }
    leaf dhcp-server-vrf-name {
      type string;
      default "";
      description
        "Configure DHCP server VRF name for Remote-LAN";
    }
  }

  grouping st-rlan-web-pre-auth-acl {
    description
      "Configuration of RLAN Web ACL";
    leaf ipv4-acl {
      type string {
        length "0..31" {
          error-message "Invalid string length for IPv4 ACL name:Valid string has be 0 to 32 characters";
          error-app-tag "must-violation";
        }
      }
      description
        "Configure IPv4 RLAN Web ACL";
    }
    leaf ipv6-acl {
      type string {
        length "0..31" {
          error-message "Invalid string length for IPv6 ACL name:Valid string has be 0 to 32 characters";
          error-app-tag "must-violation";
        }
      }
      description
        "Configure IPv6 RLAN Web ACL";
    }
  }

  grouping st-rlan-config {
    description
      "Configure remote LAN profile";
    leaf rlan-id {
      type uint32 {
        range "1 .. 128";
      }
      description
        "Remote LAN Profile Id";
    }
    leaf profile-name {
      type string {
        pattern '[!-~]([ -~]*[!-~])?';
      }
      must "not( (../security-8021x-dot1x = 'true' or string-length(../auth-list-dot1x) > 0) and (../security-web-auth = 'true' or string-length(../auth-list) > 0 or string-length(../web-auth-parameter-map) > 0) )" {
        error-message "Dot1x parameters and webauth parameters cannot be active together";
        error-app-tag "must-violation";
      }
      description
        "Remote LAN Profile Name";
    }
    leaf mac-filtering {
      type string;
      description
        "Mac filtering on remote LAN";
    }
    leaf auth-list {
      type string;
      description
        "Configure auth list on remote LAN";
    }
    leaf security-8021x-dot1x {
      type boolean;
      description
        "Configures 802.1X";
    }
    leaf auth-list-dot1x {
      type string;
      description
        "Configures security web auth";
    }
    leaf security-web-auth {
      type boolean;
      description
        "Configures security web auth";
    }
    leaf local-auth-eap-profile-name {
      type string;
      description
        "Configure the EAP profile on a Remote-LAN";
    }
    leaf local-eap-auth-enabled {
      type boolean;
      description
        "Enable/Disable the EAP profile on a Remote-LAN";
    }
    leaf web-auth-parameter-map {
      type string;
      description
        "Configure parameter map on a Remote-LAN";
    }
    leaf max-associated-clients {
      type uint32;
      default "0";
      description
        "Configure maximum client connections per Remote-LAN";
    }
    leaf status {
      type boolean;
      default "false";
      description
        "Remote LAN Profile status";
    }
    container web-pre-auth-acl {
      description
        "Configure Web ACL for Remote-LAN";
      uses wireless-rlan-cfg:st-rlan-web-pre-auth-acl;
    }
    leaf mdns-sd-mode {
      type wireless-enum-types:enm-wlan-mdns-sd-cfg;
      default "mdns-sd-bridging";
      description
        "MDNS mode on remote LAN";
    }
    leaf rlan-fallback-type {
      type wireless-enum-types:enm-rlan-fallback-type;
      default "rlan-auth-fback-none";
      description
        "RLAN fallback authentication type";
    }
    leaf dot1x-eapid-retries-set {
      type boolean;
      default "false";
      description
        "Enable/Disable EAP identity request retry setting";
    }
    leaf dot1x-eapid-req-retries {
      type uint8 {
        range "1 .. 20";
      }
      must "(../dot1x-eapid-retries-set = 'true')" {
        error-message "dot1x EAP identity retry setting must be set to true to enable EAP identity request retransmissions";
        error-app-tag "must-violation";
      }
      description
        "Maximum number of EAP identity request retransmissions";
    }
    leaf dot1x-eapid-req-timeout {
      type uint8 {
        range "1 .. 120";
      }
      units "seconds";
      description
        "Timeout for EAP identity requests";
    }
    leaf dot1x-eap-retries-set {
      type boolean;
      default "false";
      description
        "Enable/Disable EAP request retry setting";
    }
    leaf dot1x-eap-req-max-retries {
      type uint8 {
        range "0 .. 20";
      }
      must "(../dot1x-eap-retries-set = 'true')" {
        error-message "dot1x-eap-retries-set must be set to true to enable this setting";
        error-app-tag "must-violation";
      }
      description
        "Maximum number of EAP request retransmissions";
    }
    leaf dot1x-eap-req-timeout {
      type uint8 {
        range "1 .. 120";
      }
      units "seconds";
      description
        "Timeout for EAP request retransmission";
    }
  }

  container rlan-cfg-data {
    description
      "RLAN profile configurations";
    container rlan-configs {
      description
        "RLAN profile configuration";
      list rlan-config {
        key "rlan-id";
        unique "profile-name";
        description
          "RLAN profile";
        uses wireless-rlan-cfg:st-rlan-config {
          refine "profile-name" {
            mandatory true;
          }
        }
      }
    }
    container rlan-policy-profile-configs {
      description
        "RLAN policy profile configuration";
      list rlan-policy-profile-config {
        key "profile-name";
        description
          "RLAN policy profile";
        uses wireless-rlan-cfg:st-rlan-policy-profile-config;
      }
    }
  }
}
