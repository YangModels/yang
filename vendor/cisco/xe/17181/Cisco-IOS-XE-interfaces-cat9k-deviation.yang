module Cisco-IOS-XE-interfaces-cat9k-deviation {
  yang-version 1.1;
  namespace "http://cisco.com/ns/yang/Cisco-IOS-XE-interfaces-cat9k-deviation";
  prefix ios-interfaces-cat9k-deviate;

  import Cisco-IOS-XE-native {
    prefix ios;
  }

  organization
    "Cisco Systems, Inc.";
  description
    "Cisco XE Native Interfaces Deviation Yang model for Cat9k platform.
     Copyright (c) 2019-2024 by Cisco Systems, Inc.
     All rights reserved.";

  revision 2025-03-01 {
    description
      "- Added deviation for interface description length";
  }

  deviation "/ios:native/ios:interface/ios:AppNav-Compress/ios:description" {
    deviate replace {
      type string {
        length "0..230";
      }
    }
  }

  deviation "/ios:native/ios:interface/ios:AppNav-UnCompress/ios:description" {
    deviate replace {
      type string {
        length "0..230";
      }
    }
  }

  deviation "/ios:native/ios:interface/ios:ATM/ios:description" {
    deviate replace {
      type string {
        length "0..230";
      }
    }
  }

  deviation "/ios:native/ios:interface/ios:ATM-subinterface/ios:ATM/ios:description" {
    deviate replace {
      type string {
        length "0..230";
      }
    }
  }

  deviation "/ios:native/ios:interface/ios:BDI/ios:description" {
    deviate replace {
      type string {
        length "0..230";
      }
    }
  }

  deviation "/ios:native/ios:interface/ios:Embedded-Service-Engine/ios:description" {
    deviate replace {
      type string {
        length "0..230";
      }
    }
  }

  deviation "/ios:native/ios:interface/ios:Ethernet/ios:description" {
    deviate replace {
      type string {
        length "0..230";
      }
    }
  }

  deviation "/ios:native/ios:interface/ios:FastEthernet/ios:description" {
    deviate replace {
      type string {
        length "0..230";
      }
    }
  }

  deviation "/ios:native/ios:interface/ios:ucse/ios:description" {
    deviate replace {
      type string {
        length "0..230";
      }
    }
  }

  deviation "/ios:native/ios:interface/ios:Ethernet-Internal/ios:description" {
    deviate replace {
      type string {
        length "0..230";
      }
    }
  }

  deviation "/ios:native/ios:interface/ios:Service-Engine/ios:description" {
    deviate replace {
      type string {
        length "0..230";
      }
    }
  }

  deviation "/ios:native/ios:interface/ios:GigabitEthernet/ios:description" {
    deviate replace {
      type string {
        length "0..230";
      }
    }
  }

  deviation "/ios:native/ios:interface/ios:TwoGigabitEthernet/ios:description" {
    deviate replace {
      type string {
        length "0..230";
      }
    }
  }

  deviation "/ios:native/ios:interface/ios:FiveGigabitEthernet/ios:description" {
    deviate replace {
      type string {
        length "0..230";
      }
    }
  }

  deviation "/ios:native/ios:interface/ios:AppGigabitEthernet/ios:description" {
    deviate replace {
      type string {
        length "0..230";
      }
    }
  }

  deviation "/ios:native/ios:interface/ios:TenGigabitEthernet/ios:description" {
    deviate replace {
      type string {
        length "0..230";
      }
    }
  }

  deviation "/ios:native/ios:interface/ios:TwentyFiveGigE/ios:description" {
    deviate replace {
      type string {
        length "0..230";
      }
    }
  }

  deviation "/ios:native/ios:interface/ios:FortyGigabitEthernet/ios:description" {
    deviate replace {
      type string {
        length "0..230";
      }
    }
  }

  deviation "/ios:native/ios:interface/ios:FiftyGigabitEthernet/ios:description" {
    deviate replace {
      type string {
        length "0..230";
      }
    }
  }

  deviation "/ios:native/ios:interface/ios:HundredGigE/ios:description" {
    deviate replace {
      type string {
        length "0..230";
      }
    }
  }

  deviation "/ios:native/ios:interface/ios:TwoHundredGigE/ios:description" {
    deviate replace {
      type string {
        length "0..230";
      }
    }
  }

  deviation "/ios:native/ios:interface/ios:FourHundredGigE/ios:description" {
    deviate replace {
      type string {
        length "0..230";
      }
    }
  }

  deviation "/ios:native/ios:interface/ios:Loopback/ios:description" {
    deviate replace {
      type string {
        length "0..230";
      }
    }
  }

  deviation "/ios:native/ios:interface/ios:LORAWAN/ios:description" {
    deviate replace {
      type string {
        length "0..230";
      }
    }
  }

  deviation "/ios:native/ios:interface/ios:WPAN/ios:description" {
    deviate replace {
      type string {
        length "0..230";
      }
    }
  }

  deviation "/ios:native/ios:interface/ios:Virtual-WPAN/ios:description" {
    deviate replace {
      type string {
        length "0..230";
      }
    }
  }

  deviation "/ios:native/ios:interface/ios:L2LISP/ios:description" {
    deviate replace {
      type string {
        length "0..230";
      }
    }
  }

  deviation "/ios:native/ios:interface/ios:L2LISP-subinterface/ios:L2LISP/ios:description" {
    deviate replace {
      type string {
        length "0..230";
      }
    }
  }

  deviation "/ios:native/ios:interface/ios:LISP/ios:description" {
    deviate replace {
      type string {
        length "0..230";
      }
    }
  }

  deviation "/ios:native/ios:interface/ios:LISP-subinterface/ios:LISP/ios:description" {
    deviate replace {
      type string {
        length "0..230";
      }
    }
  }

  deviation "/ios:native/ios:interface/ios:nve/ios:description" {
    deviate replace {
      type string {
        length "0..230";
      }
    }
  }

  deviation "/ios:native/ios:interface/ios:Port-channel/ios:description" {
    deviate replace {
      type string {
        length "0..230";
      }
    }
  }

  deviation "/ios:native/ios:interface/ios:Port-channel-subinterface/ios:Port-channel/ios:description" {
    deviate replace {
      type string {
        length "0..230";
      }
    }
  }

  deviation "/ios:native/ios:interface/ios:PRP-channel/ios:description" {
    deviate replace {
      type string {
        length "0..230";
      }
    }
  }

  deviation "/ios:native/ios:interface/ios:SM/ios:description" {
    deviate replace {
      type string {
        length "0..230";
      }
    }
  }

  deviation "/ios:native/ios:interface/ios:Cellular/ios:description" {
    deviate replace {
      type string {
        length "0..230";
      }
    }
  }

  deviation "/ios:native/ios:interface/ios:Dialer/ios:description" {
    deviate replace {
      type string {
        length "0..230";
      }
    }
  }

  deviation "/ios:native/ios:interface/ios:Vlan/ios:description" {
    deviate replace {
      type string {
        length "0..230";
      }
    }
  }

  deviation "/ios:native/ios:interface/ios:GMPLS/ios:description" {
    deviate replace {
      type string {
        length "0..230";
      }
    }
  }

  deviation "/ios:native/ios:interface/ios:Group-Async/ios:description" {
    deviate replace {
      type string {
        length "0..230";
      }
    }
  }

  deviation "/ios:native/ios:interface/ios:Multilink/ios:description" {
    deviate replace {
      type string {
        length "0..230";
      }
    }
  }

  deviation "/ios:native/ios:interface/ios:Serial/ios:description" {
    deviate replace {
      type string {
        length "0..230";
      }
    }
  }

  deviation "/ios:native/ios:interface/ios:Async/ios:description" {
    deviate replace {
      type string {
        length "0..230";
      }
    }
  }

  deviation "/ios:native/ios:interface/ios:Tunnel/ios:description" {
    deviate replace {
      type string {
        length "0..230";
      }
    }
  }

  deviation "/ios:native/ios:interface/ios:vmi/ios:description" {
    deviate replace {
      type string {
        length "0..230";
      }
    }
  }

  deviation "/ios:native/ios:interface/ios:Virtual-Template/ios:description" {
    deviate replace {
      type string {
        length "0..230";
      }
    }
  }

  deviation "/ios:native/ios:interface/ios:Virtual-PPP/ios:description" {
    deviate replace {
      type string {
        length "0..230";
      }
    }
  }

  deviation "/ios:native/ios:interface/ios:VirtualPortGroup/ios:description" {
    deviate replace {
      type string {
        length "0..230";
      }
    }
  }

  deviation "/ios:native/ios:interface/ios:vasileft/ios:description" {
    deviate replace {
      type string {
        length "0..230";
      }
    }
  }

  deviation "/ios:native/ios:interface/ios:vasiright/ios:description" {
    deviate replace {
      type string {
        length "0..230";
      }
    }
  }

  deviation "/ios:native/ios:interface/ios:Vif/ios:description" {
    deviate replace {
      type string {
        length "0..230";
      }
    }
  }

  deviation "/ios:native/ios:interface/ios:Wlan-GigabitEthernet/ios:description" {
    deviate replace {
      type string {
        length "0..230";
      }
    }
  }

  deviation "/ios:native/ios:interface/ios:BD-VIF/ios:description" {
    deviate replace {
      type string {
        length "0..230";
      }
    }
  }

  deviation "/ios:native/ios:interface/ios:MFR/ios:description" {
    deviate replace {
      type string {
        length "0..230";
      }
    }
  }

  deviation "/ios:native/ios:interface/ios:Serial-subinterface/ios:Serial/ios:description" {
    deviate replace {
      type string {
        length "0..230";
      }
    }
  }

  deviation "/ios:native/ios:interface/ios:MFR-subinterface/ios:MFR/ios:description" {
    deviate replace {
      type string {
        length "0..230";
      }
    }
  }

  deviation "/ios:native/ios:interface/ios:Bundle/ios:description" {
    deviate replace {
      type string {
        length "0..230";
      }
    }
  }
}
