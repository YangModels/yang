module Cisco-IOS-XE-wireless-afc-oper {
  yang-version 1.1;
  namespace "http://cisco.com/ns/yang/Cisco-IOS-XE-wireless-afc-oper";
  prefix wireless-afc-oper;

  import Cisco-IOS-XE-wireless-afc-types {
    prefix wireless-afc-types;
  }
  import Cisco-IOS-XE-wireless-enum-types {
    prefix wireless-enum-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing AFC
     Copyright (c) 2022-2023 by Cisco Systems, Inc.
     All rights reserved.";

  revision 2024-03-01 {
    description
      "- Added slot to AFC AP response";
    reference
      "1.1.0";
    cisco-semver:module-version "1.1.0";
  }
  revision 2023-11-01 {
    description
      "Initial revision";
    reference
      "1.0.0";
    cisco-semver:module-version "1.0.0";
  }

  grouping afc-ap-req {
    description
      "AFC request information";
    leaf ap-mac {
      type yang:mac-address;
      description
        "AP MAC address";
    }
    container req-data {
      description
        "AFC request data";
      uses wireless-afc-types:afc-request-data;
    }
    leaf request-status {
      type wireless-enum-types:afc-request-status;
      description
        "AFC request status";
    }
    leaf request-status-ts {
      type yang:date-and-time;
      description
        "AFC request status timestamp";
    }
    leaf req-id-sent {
      type uint64;
      description
        "AFC request ID sent to AFC Service";
    }
  }

  grouping afc-ap-resp {
    description
      "AFC response information";
    leaf ap-mac {
      type yang:mac-address;
      description
        "AP MAC address";
    }
    container resp-data {
      description
        "AFC response data";
      uses wireless-afc-types:afc-response-data;
    }
    leaf slot {
      type uint8;
      description
        "AFC enabled slot identifier";
    }
  }

  container afc-oper-data {
    config false;
    description
      "AFC Operational Data Model";
    list ewlc-afc-ap-req {
      key "ap-mac";
      description
        "AFC request";
      uses wireless-afc-oper:afc-ap-req;
    }
    list ewlc-afc-ap-resp {
      key "ap-mac";
      description
        "AFC response";
      uses wireless-afc-oper:afc-ap-resp;
    }
  }
}
