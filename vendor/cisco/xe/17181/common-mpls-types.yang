module common-mpls-types {
  namespace "urn:ietf:params:xml:ns:yang:common-mpls-types";
  prefix mpls-types;

  import cisco-semver {
    prefix cisco-semver;
  }

  organization
    "Cisco Systems
     170 West Tasman Drive
     San Jose, CA 95134-1706
     USA";
  contact
    "Robert Sawaya - rsawaya@cisco.com,
     Vasanth Sabavat - vsabavat@cisco.com";
  description
    "This module contains a collection of generally useful YANG types
     that are specific to MPLS that can be usefully shared
     between multiple models.

     Terms and Acronyms

     MPLS: Multi Protocol Label Switching";

  revision 2019-07-01 {
    description
      "Establish semantic version baseline";
    cisco-semver:module-version "1.0.0";
  }
  revision 2015-05-28 {
    description
      "Initial revision";
    reference
      "";
  }

  typedef ietf-mpls-label {
    type union {
      type uint32 {
        range "16 .. 1048575";
      }
      type enumeration {
        enum v4-explicit-null {
          value 0;
          description
            "IETF MPLS IPv4 explicit null Label (0)";
        }
        enum v6-explicit-null {
          value 2;
          description
            "IETF MPLS IPv6 explicit null label (2)";
        }
        enum implicit-null {
          value 3;
          description
            "IETF MPLS implicit null label (3)";
        }
      }
    }
    description
      "Temporary type until IETF definition";
  }

  grouping out-label-stack {
    container stack {
      leaf-list label-stack {
        type ietf-mpls-label;
        min-elements 1;
        ordered-by user;
        description
          "First label in the list is the top of the stack";
      }
      description
        "The label stack";
    }
    description
      "The output label stack";
  }
}
