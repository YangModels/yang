module cisco-extensions {
  namespace "http://cisco.com/yang/cisco-extensions";
  prefix cisco-ext;

  organization
    "Cisco Systems";
  contact
    "<mailto:cs-yang@cisco.com>";
  description
    "This module defines extensions for additional metadata.
     Copyright (c) 2024 by Cisco Systems, Inc.
     All rights reserved.";

  extension replacement-info {
    argument value;
    description
      "Provides replacement model information for deprecated/obsolete model.";
  }
}
