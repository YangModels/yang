module Cisco-IOS-XE-uplink-autoconfig {
  yang-version 1.1;
  namespace "http://cisco.com/ns/yang/Cisco-IOS-XE-uplink-autoconfig";
  prefix ios-uac;

  import cisco-semver {
    prefix cisco-semver;
  }
  import Cisco-IOS-XE-native {
    prefix ios;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE Uplink auto config YANG model.
     Copyright (c) 2024 by Cisco Systems, Inc.
     All rights reserved.";

  revision 2025-07-01 {
    description
      "- Added L3 routed port support
       - Deprecated vlan and interface, added vlan leaf under new node interface-type";
    cisco-semver:module-version "1.1.0";
  }
  revision 2024-07-01 {
    description
      "- Initial revision for uplink-auto config";
    cisco-semver:module-version "1.0.0";
  }

  grouping config-uplink-autoconfig-grouping {
    container uplink {
      leaf autoconfig {
        description
          "Enable uplink auto config";
        type empty;
      }
      container ipv4 {
        description
          "Uplink IPv4 interface";
        when '../autoconfig';
        uses uplink-autoconfig-interface-vlan-grouping;
      }
      container ipv6 {
        description
          "Uplink IPv6 interface";
        when '../autoconfig';
        uses uplink-autoconfig-interface-vlan-grouping;
      }
    }
  }

  grouping uplink-autoconfig-interface-vlan-grouping {
    container interface-type {
      description
        "uplink interface";
      choice interface-type-choice {
        leaf vlan {
          description
            "VLAN ID for uplink interface";
          type uint16 {
            range "1..4094";
          }
          default "1";
        }
        leaf name {
          description
            "L3 Routed Port for Uplink";
          type string;
        }
      }
    }
    container interface {
      status deprecated;
      description
        "This node is deprecated and replaced by interface-type";
      leaf vlan {
        status deprecated;
        description
          "This node is deprecated and replaced by interface-type/vlan";
        type uint16 {
          range "1..4094";
        }
        default "1";
      }
    }
  }

  augment "/ios:native" {
    uses config-uplink-autoconfig-grouping;
  }
}
