module Cisco-IOS-XE-ngfw-events {
  yang-version 1.1;
  namespace "http://cisco.com/ns/yang/Cisco-IOS-XE-ngfw-events";
  prefix ngfw-ios-xe-events;

  import Cisco-IOS-XE-ios-common-oper {
    prefix ios-common-ios-xe-oper;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for NGFW events operational data.
     Copyright (c) 2024 by Cisco Systems, Inc.
     All rights reserved.";

  revision 2025-03-01 {
    description
      "Initial revision";
    reference
      "1.0.0";
    cisco-semver:module-version "1.0.0";
  }

  typedef ngfw-event-type {
    type enumeration {
      enum ngfw-policy-error {
        value 0;
        description
          "NGFW FW Policy error.";
      }
      enum ngfw-object-error {
        value 1;
        description
          "NGFW Policy Object error.";
      }
      enum ngfw-general-error {
        value 2;
        description
          "NGFW general error.";
      }
    }
    description
      "NGFW Event type";
  }

  typedef ngfw-event-err-reason {
    type enumeration {
      enum ngfw-fw-db-error {
        value 0;
        description
          "NGFW FW DB error.";
      }
      enum ngfw-fw-memory-error {
        value 1;
        description
          "NGFW FW Memory error.";
      }
      enum ngfw-fw-config-error {
        value 2;
        description
          "NGFW FW Config error.";
      }
      enum ngfw-fw-classif-error {
        value 3;
        description
          "NGFW FW Classification error.";
      }
      enum ngfw-fw-internal-error {
        value 4;
        description
          "NGFW FW Internal error.";
      }
      enum ngfw-fw-general-error {
        value 5;
        description
          "NGFW FW general error.";
      }
    }
    description
      "NGFW event error reason";
  }

  grouping ngfw-notif {
    description
      "NGFW configuration event";
    leaf severity-level {
      type ios-common-ios-xe-oper:notification-severity;
      description
        "Event severity";
    }
    leaf host-name {
      type string;
      description
        "NGFW Event hostname";
    }
    leaf zp-name {
      type string;
      description
        "NGFW Event zone-pair name";
    }
    leaf policy-name {
      type string;
      description
        "NGFW Event policy-map name";
    }
    leaf event-type {
      type ngfw-ios-xe-events:ngfw-event-type;
      description
        "NGFW Event Type";
    }
    leaf err-reason {
      type ngfw-ios-xe-events:ngfw-event-err-reason;
      description
        "NGFW Event description";
    }
  }

  notification ngfw-event {
    description
      "NGFW Error  Notification";
    uses ngfw-ios-xe-events:ngfw-notif;
  }
}
