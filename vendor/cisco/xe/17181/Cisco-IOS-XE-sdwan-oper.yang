module Cisco-IOS-XE-sdwan-oper {
  yang-version 1.1;
  namespace "http://cisco.com/ns/yang/Cisco-IOS-XE-sdwan-oper";
  prefix ios-xe-sdwan-oper;

  import Cisco-IOS-XE-sdwan-types {
    prefix ios-xe-sdwan-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     the operational data of IOS-XE SDWAN interface.
     Copyright (c) 2025 by Cisco Systems, Inc.
     All rights reserved.";

  revision 2025-07-01 {
    description
      "Initial revision";
    reference
      "1.0.0";
    cisco-semver:module-version "1.0.0";
  }

  grouping sdwan-if {
    description
      "The content of SDWAN interface";
    leaf if-name {
      type string;
      description
        "Name of WAN interface";
    }
    leaf color {
      type ios-xe-sdwan-types:sdwan-color-enum;
      description
        "Color of WAN interface";
    }
    leaf color-descr {
      type string;
      description
        "Description of WAN interface";
    }
  }

  container sdwan-oper-data {
    config false;
    description
      "The operational data of SDWAN interface";
    list sdwan-if {
      key "if-name";
      description
        "The operational data of SDWAN interface";
      uses ios-xe-sdwan-oper:sdwan-if;
    }
  }
}
