module Cisco-IOS-XE-gnmi-cfg {
  yang-version 1.1;
  namespace "http://cisco.com/ns/yang/Cisco-IOS-XE-gnmi-cfg";
  prefix gnmi-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for gNMI configuration data.
     Copyright (c) 2021-2022, 2024-2025 by Cisco Systems, Inc.
     All rights reserved.";

  revision 2025-07-01 {
    description
      "Add leaf 'vrf' to configure the gNxI server's VRF";
    reference
      "1.4.0";
    cisco-semver:module-version "1.4.0";
  }
  revision 2025-03-01 {
    description
      "- Add length and pattern constraints to secure trustpoint name
       - Add length and pattern constraints to secure client auth trustpoint name
       - Fix constraints tying secure server and trustpoint name";
    reference
      "1.3.0";
    cisco-semver:module-version "1.3.0";
  }
  revision 2024-07-01 {
    description
      "- Add 'enable-gnoi' leaf to control whether gNOI services are enabled/disabled.
       - Add 'read-only' leaf to enable/disable read-only mode";
    reference
      "1.2.0";
    cisco-semver:module-version "1.2.0";
  }
  revision 2022-11-01 {
    description
      "Update yang-version to 1.1";
    reference
      "1.1.0";
    cisco-semver:module-version "1.1.0";
  }
  revision 2021-07-01 {
    description
      "Initial revision";
    reference
      "1.0.0";
    cisco-semver:module-version "1.0.0";
  }

  grouping gnmi-config {
    description
      "gNMI server configuration data type.";
    leaf enable {
      type boolean;
      default "false";
      description
        "Enables the gNMI port listening.";
    }
    leaf port {
      type uint16 {
        range "1024 .. 65535";
      }
      must '(../port != ../secure-port)' {
        error-message "The insecure and secure port cannot share the same numeric value";
        error-app-tag "must-violation";
      }
      default "50052";
      description
        "gNMI insecure server port.";
    }
    leaf secure-enable {
      type boolean;
      must "(../secure-enable = 'false') or ((../secure-enable = 'true') and string-length(../secure-tsname) > 0)" {
        error-message "Secure server can only be enabled in combination with a valid secure trustpoint name.";
        error-app-tag "must-violation";
      }
      default "false";
      description
        "Enables the gNMI secure server.";
    }
    leaf secure-client-auth {
      type boolean;
      default "false";
      description
        "Enables gNMI with client authentication.";
    }
    leaf secure-port {
      type uint16 {
        range "1024 .. 65535";
      }
      must '(../port != ../secure-port)' {
        error-message "The insecure and secure port cannot share the same numeric value";
        error-app-tag "must-violation";
      }
      default "9339";
      description
        "gNMI secure server port.";
    }
    leaf secure-tsname {
      type string {
        length "1..128";
        pattern "[\\] A-Za-z0-9!\"#%&()*+,\\-./:;<=>^?@\\\\$_`{|}\\[']+";
      }
      description
        "gNMI server certificate trustpoint name.";
    }
    leaf service {
      type boolean;
      default "false";
      description
        "Starts the gNMI service.";
    }
    leaf secure-client-auth-tsname {
      type string {
        length "1..128";
        pattern "[\\] A-Za-z0-9!\"#%&()*+,\\-./:;<=>^?@\\\\$_`{|}\\[']+";
      }
      description
        "The gNMI server peer validation trustpoint name.";
    }
    leaf secure-password-auth {
      type boolean;
      default "false";
      description
        "Set gNMI with password authentication.";
    }
    leaf enable-gnoi {
      type boolean;
      default "true";
      description
        "Enable the supported set of gRPC Network Operations Interface (gNOI) services.
         If gNOI is disabled then the device wil behave as if the service is not implemented.
         All RPCs belonging to disabled services will fail with a gRPC UNIMPLEMENTED status code";
    }
    leaf read-only {
      type boolean;
      default "false";
      description
        "Operate in a read-only mode.
         - All gNOI services are disabled. The behavior will be equivalent to setting 'enable-gnoi' to 'false'
         - The gNMI/Set RPC will fail with a gRPC PERMISSION_DENIED status code.";
    }
    leaf vrf {
      type string {
        length "1..32";
        pattern "[\\] A-Za-z0-9!\"#%&()*+,\\-./:;<=>^?@\\\\$_`{|}\\[']+";
      }
      description
        "The Virtual Routing and Forwarding (VRF) instance to use for connections to the gNxI server.";
    }
  }

  container gnmi-cfg-data {
    description
      "gNMI configuration data.";
    container config {
      presence "config";
      description
        "gNMI server configuration data.";
      uses gnmi-cfg:gnmi-config;
    }
  }
}
