module Cisco-IOS-XE-spanning-tree-oper {
  yang-version 1.1;
  namespace "http://cisco.com/ns/yang/Cisco-IOS-XE-spanning-tree-oper";
  prefix stp-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring vlans in a Network Element.
     Copyright (c) 2016-2017, 2019, 2022-2025 by Cisco Systems, Inc.
     All rights reserved.";

  revision 2025-07-01 {
    description
      "-Added new leaf protocol for stp-details
       -Added new leaf for aging timer
       -Extended STP global to represent the global configurations and
        to get STP data with key as vlan id";
    reference
      "1.5.0";
    cisco-semver:module-version "1.5.0";
  }
  revision 2024-11-01 {
    description
      "Added new leaf root-if-name for stp-details";
    reference
      "1.4.0";
    cisco-semver:module-version "1.4.0";
  }
  revision 2024-07-01 {
    description
      "-Added portfast mode and guard status in STP interface data
       -Extended STP interface with
       aggregate port channel number and legacy STP connection";
    reference
      "1.3.0";
    cisco-semver:module-version "1.3.0";
  }
  revision 2022-11-01 {
    description
      "Update yang-version to 1.1";
    reference
      "1.2.0";
    cisco-semver:module-version "1.2.0";
  }
  revision 2019-05-01 {
    description
      "Added semantic version";
    reference
      "1.1.0";
    cisco-semver:module-version "1.1.0";
  }
  revision 2017-08-10 {
    description
      "Initial revision";
    reference
      "1.0.0";
    cisco-semver:module-version "1.0.0";
  }

  typedef stp-port-state {
    type enumeration {
      enum stp-disabled {
        value 0;
      }
      enum stp-blocking {
        value 1;
      }
      enum stp-listening {
        value 2;
      }
      enum stp-learning {
        value 3;
      }
      enum stp-forwarding {
        value 4;
      }
      enum stp-broken {
        value 5;
      }
      enum stp-invalid {
        value 6;
      }
    }
    description
      "Spanning Tree Protocol port states";
  }

  typedef stp-port-role {
    type enumeration {
      enum stp-master {
        value 0;
      }
      enum stp-alternate {
        value 1;
      }
      enum stp-root {
        value 2;
      }
      enum stp-designated {
        value 3;
      }
      enum stp-backup {
        value 4;
      }
    }
    description
      "Spanning Tree Protocol port roles";
  }

  typedef stp-link-role {
    type enumeration {
      enum stp-auto {
        value 0;
      }
      enum stp-point-to-point {
        value 1;
      }
      enum stp-shared {
        value 2;
      }
    }
    description
      "Type definition for the different link types";
  }

  typedef stp-port-guard {
    type enumeration {
      enum stp-port-guard-default {
        value 0;
      }
      enum stp-port-guard-root {
        value 1;
      }
      enum stp-port-guard-loop {
        value 2;
      }
      enum stp-port-guard-none {
        value 3;
      }
    }
    description
      "Interface's spanning tree guard mode";
  }

  typedef stp-port-bpduguard {
    type enumeration {
      enum stp-port-bpduguard-disable {
        value 0;
      }
      enum stp-port-bpduguard-enable {
        value 1;
      }
      enum stp-port-bpduguard-default {
        value 2;
      }
    }
    description
      "Accept BPDUs on this interface";
  }

  typedef stp-port-bpdufilter {
    type enumeration {
      enum stp-port-bpdufilter-disable {
        value 0;
      }
      enum stp-port-bpdufilter-enable {
        value 1;
      }
      enum stp-port-bpdufilter-default {
        value 2;
      }
    }
    description
      "Send or receive BPDUs on this interface";
  }

  typedef stp-mode {
    type enumeration {
      enum stp-mode-pvst {
        value 0;
      }
      enum stp-mode-rapid-pvst {
        value 1;
      }
      enum stp-mode-mst {
        value 2;
      }
    }
    description
      "Spanning tree operating mode";
  }

  typedef stp-inconsistency-status {
    type enumeration {
      enum stp-ps-rootgrd-act {
        value 0;
        description
          "Port is in root-inconsistent state";
      }
      enum stp-ps-bpdugrd-act {
        value 1;
        description
          "Port is in Bpdu-guard error-disabled state";
      }
      enum stp-ps-loopgrd-act {
        value 2;
        description
          "Port is in loop-inconsistent state";
      }
      enum stp-ps-bpducflt-act {
        value 3;
        description
          "Port is in BPDU Sender-conflict state";
      }
      enum stp-ps-inconst-none {
        value 4;
        description
          "Port is in consistent state";
      }
    }
    description
      "Interface's spanning tree inconsistency status";
  }

  typedef stp-protocol-status {
    type enumeration {
      enum stp-proto-invalid {
        value 0;
        description
          "The protocol is not valid type for this spanning tree";
      }
      enum stp-proto-def {
        value 1;
        description
          "Spanning tree is using default protocol declared";
      }
      enum stp-proto-ieee {
        value 2;
        description
          "Spanning tree is using IEEE compliant protocol";
      }
      enum stp-proto-dec {
        value 3;
        description
          "Spanning tree is using DEC compliant protocol";
      }
      enum stp-proto-ibm {
        value 4;
        description
          "Spanning tree is using IBM compliant protocol";
      }
      enum stp-proto-vlan-br {
        value 5;
        description
          "Spanning tree is using Vlan bridge protocol";
      }
      enum stp-proto-rstp {
        value 6;
        description
          "Spanning tree is using Rapid STP protocol";
      }
      enum stp-proto-mstp {
        value 7;
        description
          "Spanning tree is using Multiple STP protocol";
      }
    }
    description
      "Spanning tree protocol";
  }

  typedef stp-portfast-status {
    type enumeration {
      enum stp-pf-default {
        value 0;
        description
          "Uses portfast global configuration";
      }
      enum stp-pf-edge {
        value 1;
        description
          "Portfast edge";
      }
      enum stp-pf-disable {
        value 2;
        description
          "Port is a normal spanning-tree port";
      }
      enum stp-pf-trunk {
        value 3;
        description
          "Portfast edge trunk";
      }
      enum stp-pf-network {
        value 4;
        description
          "Portfast network";
      }
    }
    description
      "Spanning tree portfast status";
  }

  typedef stp-pathcost-method {
    type enumeration {
      enum stp-pc-long {
        value 0;
        description
          "Path cost method used is long";
      }
      enum stp-pc-short {
        value 1;
        description
          "Path cost method used is short";
      }
      enum stp-pc-max {
        value 2;
        description
          "Path cost method used is max";
      }
    }
    description
      "Spanning tree path cost methods";
  }

  grouping interfaces {
    description
      "List of interfaces on which STP is enable";
    leaf name {
      type string;
      description
        "Reference to the STP ethernet interface";
    }
    leaf cost {
      type uint64;
      description
        "The port's contribution, when it is the Root Port, to the Root Path Cost for the Bridge";
    }
    leaf port-priority {
      type uint16;
      description
        "The manageable component of the Port Identifier, also known as the Port Priority";
    }
    leaf port-num {
      type uint16;
      description
        "The port number of the bridge port";
    }
    leaf role {
      type stp-ios-xe-oper:stp-port-role;
      description
        "The current role of the bridge port";
    }
    leaf state {
      type stp-ios-xe-oper:stp-port-state;
      description
        "The current state of the bridge port";
    }
    leaf designated-root-priority {
      type uint32;
      description
        "The bridge priority of the bridge recorded as the root in the configuration BPDUs transmitted by the designated bridge for the segment to which the port is attached";
    }
    leaf designated-root-address {
      type yang:mac-address;
      description
        "The bridge address of the bridge recorded as the root in the configuration BPDUs transmitted by the designated bridge for the segment to which the port is attached";
    }
    leaf designated-cost {
      type uint32;
      description
        "The path cost of the Designated Port of the segment connected to this port";
    }
    leaf designated-bridge-priority {
      type uint32;
      description
        "The bridge priority of the bridge that this port considers to be the designated bridge for this port's segment";
    }
    leaf designated-bridge-address {
      type yang:mac-address;
      description
        "The bridge address of the bridge that this port considers to be the designated bridge for this port's segment";
    }
    leaf designated-port-priority {
      type uint16;
      description
        "The Port priority of the port on the Designated Bridge for this port's segment, two octet string";
    }
    leaf designated-port-num {
      type uint16;
      description
        "The Port number of the port on the Designated Bridge for this port's segment, two octet string";
    }
    leaf forward-transitions {
      type uint64;
      description
        "The number of times this port has transitioned from the Learning state to the Forwarding state";
    }
    leaf link-type {
      type stp-ios-xe-oper:stp-link-role;
      description
        "Interface's link type";
    }
    leaf guard {
      type stp-ios-xe-oper:stp-port-guard;
      description
        "Interface's spanning tree guard mode";
    }
    leaf bpdu-guard {
      type stp-ios-xe-oper:stp-port-bpduguard;
      description
        "BPDU guard on this interface";
    }
    leaf bpdu-filter {
      type stp-ios-xe-oper:stp-port-bpdufilter;
      description
        "BPDU filter on this interface";
    }
    leaf bpdu-sent {
      type uint64;
      description
        "The number of BPDU packet sent";
    }
    leaf bpdu-received {
      type uint64;
      description
        "The number of BPDU packet received";
    }
    leaf oper-p2p {
      type empty;
      description
        "Spanning tree operational link-type is Point-to-Point";
    }
    leaf oper-portfast-edge {
      type empty;
      description
        "Spanning tree interface is operating in portfast EDGE";
    }
    leaf guard-status {
      type stp-ios-xe-oper:stp-inconsistency-status;
      description
        "Interface's spanning tree guard inconsistent status";
    }
    leaf agg-port-id {
      type uint16;
      description
        "The number of the etherchannel group";
    }
    leaf legacy {
      type empty;
      description
        "Spanning tree is operating in legacy STP mode.";
    }
  }

  grouping stp-oper-crimson {
    description
      "Attributes of spanning-tree";
    leaf instance {
      type string;
      description
        "Spanning-tree enabled mode and id";
    }
    leaf hello-time {
      type int32;
      description
        "The interval between periodic transmissions of configuration messages by designated ports";
    }
    leaf max-age {
      type int32;
      description
        "The maximum age of the information transmitted by the bridge when it is the root bridge";
    }
    leaf forwarding-delay {
      type int32;
      description
        "The delay used by STP bridges to transition root and designated ports to forwarding";
    }
    leaf hold-count {
      type uint32;
      description
        "The maximum number of BPDUs per second that the switch can send from an interface";
    }
    leaf bridge-priority {
      type uint16;
      description
        "The manageable component of the Bridge Identifier";
    }
    leaf bridge-address {
      type yang:mac-address;
      description
        "A unique 48-bit Universally Administered MAC Address assigned to the bridge";
    }
    leaf designated-root-priority {
      type uint32;
      description
        "The bridge priority of the root of the spanning tree, as determined by the Spanning Tree Protocol, as executed by this node";
    }
    leaf designated-root-address {
      type yang:mac-address;
      description
        "The bridge address of the root of the spanning tree, as determined by the Spanning Tree Protocol, as executed by this node";
    }
    leaf root-port {
      type uint16;
      description
        "The port number of the port which offers the lowest cost path from this bridge to the root bridge";
    }
    leaf root-cost {
      type uint64;
      description
        "The cost of the path to the root as seen from this bridge";
    }
    leaf hold-time {
      type uint64;
      description
        "This time value determines the interval length during which no more than two Configuration bridge PDUs shall be transmitted by this node";
    }
    leaf topology-changes {
      type uint64;
      description
        "The total number of topology changes detected by this bridge since the management entity was last reset or initialized";
    }
    leaf time-of-last-topology-change {
      type yang:date-and-time;
      description
        "The time of the last topology change that was detected by the bridge entity.The time is POSIX time UTC";
    }
    container interfaces {
      description
        "List of interfaces on which STP is enable";
      list interface {
        key "name";
        description
          "List of interfaces on which STP is enable";
        uses stp-ios-xe-oper:interfaces;
      }
    }
    leaf root-if-name {
      type string;
      description
        "Root interface name of the STP root port";
    }
    leaf protocol {
      type stp-ios-xe-oper:stp-protocol-status;
      description
        "Indicates the type of Spanning Tree Protocol currently being used on the switch";
    }
    leaf aging-time {
      type uint32;
      units "seconds";
      description
        "The aging timer refers to the duration that the switch keeps track of learned MAC addresses";
    }
  }

  grouping stp-vlan-if {
    description
      "List of interfaces STP is enable";
    leaf if-name {
      type string;
      description
        "Reference to the STP ethernet interface";
    }
    leaf cost {
      type uint64;
      description
        "The port's contribution, when it is the root port, to the root path cost for the bridge";
    }
    leaf port-pri {
      type uint16;
      description
        "The manageable component of the port identifier, also known as the port priority";
    }
    leaf port-num {
      type uint16;
      description
        "The port number of the bridge port";
    }
    leaf role {
      type stp-ios-xe-oper:stp-port-role;
      description
        "The current role of the bridge port";
    }
    leaf state {
      type stp-ios-xe-oper:stp-port-state;
      description
        "The current state of the bridge port";
    }
    leaf oper-p2p {
      type empty;
      description
        "Spanning tree vlan interface operational link-type is point-to-point";
    }
  }

  grouping stp-vlan {
    description
      "Attributes of vlan";
    leaf id {
      type uint16;
      description
        "Vlan id";
    }
    leaf inst {
      type string;
      description
        "Instance of the vlan";
    }
    leaf vlan-mode {
      type stp-ios-xe-oper:stp-mode;
      description
        " Spanning tree mode enable on the device";
    }
    leaf des-root-pri {
      type uint32;
      description
        "The bridge priority of the bridge recorded as the root in the configuration BPDUs transmitted by the designated bridge for the segment to which the port is attached";
    }
    leaf des-root-addr {
      type yang:mac-address;
      description
        "The bridge address of the bridge recorded as the root in the configuration BPDUs transmitted by the designated bridge for the segment to which the port is attached";
    }
    leaf bridge-is-root {
      type empty;
      description
        "The bridge is the root";
    }
    leaf des-brg-pri {
      type uint32;
      description
        "The bridge priority of the bridge that this port considers to be the designated bridge for this port's segment";
    }
    leaf des-brg-addr {
      type yang:mac-address;
      description
        "The bridge address of the bridge that this port considers to be the designated bridge for this port's segment";
    }
    leaf vlan-cost {
      type uint64;
      description
        "The port's contribution, when it is the root port, to the root path cost for the bridge";
    }
    leaf vlan-port-num {
      type uint16;
      description
        "The port number of the bridge port";
    }
    list stp-vlan-if {
      key "if-name";
      description
        "List of interfaces STP is enable";
      uses stp-ios-xe-oper:stp-vlan-if;
    }
  }

  grouping mst-global {
    description
      "Global state for MST ONLY";
    leaf mst-config-revision {
      type uint16;
      description
        "Configuration revision number(used by MSTP only)";
    }
    leaf mst-config-name {
      type string;
      description
        "Configuration name(used by MSTP only)";
    }
    leaf max-hops {
      type uint16;
      description
        "The max hops value for the spanning tree(used by MSTP only)";
    }
  }

  grouping stp-global {
    description
      "Global spanning tree state";
    leaf mode {
      type stp-ios-xe-oper:stp-mode;
      description
        "Spanning tree mode enabled on the device";
    }
    leaf bridge-assurance {
      type empty;
      description
        "Enable STP Bridge Assurance feature";
    }
    leaf loop-guard {
      type empty;
      description
        "Enable loopguard by default";
    }
    leaf bpdu-guard {
      type empty;
      description
        "Enable portfast bpdu guard";
    }
    leaf bpdu-filter {
      type empty;
      description
        "Enable portfast bpdu filter";
    }
    leaf etherchannel-misconfig-guard {
      type empty;
      description
        "Enable guard to protect against etherchannel misconfiguration";
    }
    container mst-only {
      description
        "Global state for MST ONLY";
      uses stp-ios-xe-oper:mst-global;
    }
    leaf prtfst-dflt {
      type stp-ios-xe-oper:stp-portfast-status;
      description
        "Portfast feature status on the device";
    }
    leaf bpdu-dly-mntr {
      type empty;
      description
        "BPDU Delay Monitor feature status on the device";
    }
    leaf bpdu-sndr-cnflt {
      type empty;
      description
        "BPDU Sender Conflict feature status on the device";
    }
    leaf pvst-sim {
      type empty;
      description
        "PVST Simulation feature status on the device";
    }
    leaf dispute {
      type empty;
      description
        "Dispute feature status on the device";
    }
    leaf bkbn-fst {
      type empty;
      description
        "Back bone fast feature status on the device";
    }
    leaf ext-sysid {
      type empty;
      description
        "Extended System ID feature status on the device";
    }
    leaf pathcost {
      type stp-ios-xe-oper:stp-pathcost-method;
      description
        "Path Cost feature status on the device";
    }
    leaf uplinkfast {
      type empty;
      description
        "Uplink fast feature status in the device";
    }
    leaf total-vlan {
      type uint32;
      description
        "Total number of VLANs in the spanning tree instance";
    }
    leaf total-vblk {
      type uint32;
      description
        "Total count of ports in the blocking state across all VLAN instances";
    }
    leaf total-vlstn {
      type uint32;
      description
        "Total count of ports in the listening state across all VLAN instances";
    }
    leaf total-vlrn {
      type uint32;
      description
        "Total count of ports in the learning state across all VLAN instances";
    }
    leaf total-vfwd {
      type uint32;
      description
        "Total count of ports in the forwarding state across all VLAN instances";
    }
    leaf total-vactv {
      type uint32;
      description
        "Total count of active spanning tree instances across all VLAN instances";
    }
    leaf total-mst {
      type uint32;
      description
        "Total number of MST in the spanning tree instance";
    }
    leaf total-mblk {
      type uint32;
      description
        "Total count of ports in the blocking state across all MST";
    }
    leaf total-mlstn {
      type uint32;
      description
        "Total count of ports in the listening state across all MST";
    }
    leaf total-mlrn {
      type uint32;
      description
        "Total count of ports in the learning state across all MST";
    }
    leaf total-mfwd {
      type uint32;
      description
        "Total count of ports in the forwarding state across all MST";
    }
    leaf total-mactv {
      type uint32;
      description
        "Total count of active spanning tree instances across all MST";
    }
  }

  grouping stp-vlan-global {
    description
      "Details about VLAN states in Spanning Tree";
    leaf vlan-id {
      type uint16;
      description
        "VLAN id";
    }
    leaf vlan-blk {
      type uint32;
      description
        "Number of ports in the blocking state in the VLAN";
    }
    leaf vlan-lstn {
      type uint32;
      description
        "Number of ports in the listening state in the VLAN";
    }
    leaf vlan-lrn {
      type uint32;
      description
        "Number of ports in the learning state in the VLAN";
    }
    leaf vlan-fwd {
      type uint32;
      description
        "Number of ports in the forwarding state in the VLAN";
    }
    leaf vlan-actv {
      type uint32;
      description
        "Number of active spanning tree instances for the VLAN";
    }
  }

  grouping stp-mst-global {
    description
      "Details about MST states in Spanning Tree";
    leaf mst-inst {
      type string;
      description
        "MST instance";
    }
    leaf mst-blk {
      type uint32;
      description
        "Number of ports in the blocking state in the MST";
    }
    leaf mst-lstn {
      type uint32;
      description
        "Number of ports in the listening state in the MST";
    }
    leaf mst-lrn {
      type uint32;
      description
        "Number of ports in the learning state in the MST";
    }
    leaf mst-fwd {
      type uint32;
      description
        "Number of ports in the forwarding state in the MST";
    }
    leaf mst-actv {
      type uint32;
      description
        "Number of active spanning tree instances for the MST";
    }
  }

  container stp-details {
    config false;
    description
      "Top-level container for spanning tree operational data";
    list stp-detail {
      key "instance";
      description
        "List of mst/rapid-pvst spanning-tree, keyed by instance name";
      uses stp-ios-xe-oper:stp-oper-crimson;
    }
    list stp-vlan {
      key "id";
      description
        "List of vlan on spanning-tree, keyed by vlan id";
      uses stp-ios-xe-oper:stp-vlan;
    }
    container stp-global {
      presence "stp-global";
      description
        "Global state data";
      uses stp-ios-xe-oper:stp-global;
    }
    list stp-vlan-global {
      key "vlan-id";
      description
        "List of Vlan details";
      uses stp-ios-xe-oper:stp-vlan-global;
    }
    list stp-mst-global {
      key "mst-inst";
      description
        "List of MST details";
      uses stp-ios-xe-oper:stp-mst-global;
    }
  }
}
