module Cisco-IOS-XE-group-policy {
  yang-version 1.1;
  namespace "http://cisco.com/ns/yang/Cisco-IOS-XE-group-policy";
  prefix ios-group-policy;

  import cisco-semver {
    prefix cisco-semver;
  }
  import Cisco-IOS-XE-native {
    prefix ios;
  }
  import ietf-inet-types {
    prefix inet;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE PnP Yang model.
     Copyright (c) 2020-2021 by Cisco Systems, Inc.
     All rights reserved.";

  revision 2023-03-01 {
    description
      "- Adding model for steering permissions CLI";
    cisco-semver:module-version "1.2.0";
  }
  revision 2022-11-01 {
    description
      "- Update yang-version to 1.1";
    cisco-semver:module-version "1.1.0";
  }
  revision 2021-07-01 {
    description
      "Added yang support for group-policy traffic-steering";
    cisco-semver:module-version "1.0.0";
  }

  grouping config-group-policy-grouping {
    container group-policy {
      description
        "Group-policy configuration";
      container traffic-steering {
        description
          "Traffic-steering configuration";
        leaf enable {
          description
            "Enable Group-policy traffic-steering";
          type boolean;
          default "false";
        }
        container environment-data {
          description
            "Traffic-steering environment-data configuration";
          leaf enable {
            description
              "Enable Group-policy traffic-steering environment-data";
            type boolean;
            default "false";
          }
        }
        leaf device-id {
          description
            "Specify the traffic-steering device ID";
          type string;
        }
        container transport {
          description
            "Specify the traffic-steering transport type";
          choice transport-protocol {
            container TLS {
              description
                "Traffic-steering transport type is TLS";
              presence "true";
              leaf-list server-name {
                description
                  "Specify the policy-server name";
                must '../../../../server/name[server-profile-name = current()]' {
                  error-message "Policy server not created, create server first";
                }
                type string;
              }
            }
            leaf RADIUS {
              description
                "Traffic-steering transport type is Radius";
              type empty;
            }
          }
        }
        container server {
          description
            "Specify type of the traffic-steering servers";
          leaf DNAC {
            description
              "Option to select D-NAC as steering policy server";
            type string;
          }
        }
        container permissions {
          description
            "Steering policy from source group to destination group";
          list permissions-list {
            description
              "Steering policy from source group to destination group";
            key "from to";
            leaf from {
              description
                "Source Group Tag (SGT) of filtered traffic";
              type uint16 {
                range "2..65519";
              }
            }
            leaf to {
              description
                "Destination Group Tag (DGT) of filtered traffic";
              type uint16 {
                range "2..65519";
              }
            }
            container ipv4 {
              description
                "Protocol Version - IPv4";
              leaf-list Policy-name {
                description
                  "Traffic steering policy definition";
                ordered-by user;
                type string;
              }
            }
          }
        }
      }
      container server {
        description
          "group-policy Server Configuration";
        list name {
          description
            "Configure name of the server, max string length 225 char";
          key "server-profile-name";
          leaf server-profile-name {
            description
              "Specify a profile name";
            type string {
              length "1..225";
            }
          }
          container address {
            description
              "Policy server address";
            leaf-list ipv4 {
              description
                "IPv4 Address of policy server";
              max-elements 8;
              type inet:ipv4-address;
            }
            leaf-list ipv6 {
              description
                "IPv6 Address of policy server";
              max-elements 8;
              type inet:ipv6-address;
            }
          }
          container content-type {
            description
              "Application content type";
            leaf json {
              description
                "data format in REST API";
              type empty;
            }
          }
          leaf port {
            description
              "Policy server port number";
            type uint16 {
              range "443..65535";
            }
          }
          leaf retransmit {
            description
              "Maximum number of retries to server";
            type uint8 {
              range "0..5";
            }
          }
          leaf timeout {
            description
              "Time to wait for response";
            type uint8 {
              range "1..60";
            }
          }
          container tls {
            description
              "TLS parameters";
            leaf server-trustpoint {
              description
                "Server trustpoint, max string length 128 char";
              type string {
                length "1..128";
              }
            }
          }
        }
        container order {
          description
            "Order of server selection";
          leaf random {
            description
              "Pick a server in random order";
            type empty;
          }
        }
        container server-credential {
          description
            "Credentials to access the REST API";
          leaf username {
            description
              "Specify the username for the user";
            type string;
          }
          leaf password {
            description
              "Set the password for the user";
            type empty;
          }
          leaf encryption {
            description
              "Specify the password encryption type";
            type enumeration {
              enum 0;
              enum 6;
              enum 7;
            }
          }
          leaf password-string {
            type string {
              pattern '.*';
            }
          }
        }
      }
    }
  }

  grouping config-interface-group-policy-grouping {
    container group-policy {
      description
        "Group-policy configuration";
      when "/ios:native/ios-group-policy:group-policy/ios-group-policy:traffic-steering/ios-group-policy:enable = 'true'";
      container traffic-steering {
        description
          "Traffic steering configuration";
        leaf enable {
          description
            "Enable Group-policy traffic steering.";
          type boolean;
          default "true";
        }
      }
    }
  }

  augment "/ios:native" {
    uses config-group-policy-grouping;
  }

  augment "/ios:native/ios:interface/ios:FastEthernet" {
    uses config-interface-group-policy-grouping;
  }

  augment "/ios:native/ios:interface/ios:GigabitEthernet" {
    uses config-interface-group-policy-grouping;
  }

  augment "/ios:native/ios:interface/ios:TwoGigabitEthernet" {
    uses config-interface-group-policy-grouping;
  }

  augment "/ios:native/ios:interface/ios:FiveGigabitEthernet" {
    uses config-interface-group-policy-grouping;
  }

  augment "/ios:native/ios:interface/ios:AppGigabitEthernet" {
    uses config-interface-group-policy-grouping;
  }

  augment "/ios:native/ios:interface/ios:TenGigabitEthernet" {
    uses config-interface-group-policy-grouping;
  }

  augment "/ios:native/ios:interface/ios:TwentyFiveGigE" {
    uses config-interface-group-policy-grouping;
  }

  augment "/ios:native/ios:interface/ios:FortyGigabitEthernet" {
    uses config-interface-group-policy-grouping;
  }

  augment "/ios:native/ios:interface/ios:HundredGigE" {
    uses config-interface-group-policy-grouping;
  }
}
