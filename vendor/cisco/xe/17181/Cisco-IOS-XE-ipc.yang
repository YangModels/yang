module Cisco-IOS-XE-ipc {
  yang-version 1.1;
  namespace "http://cisco.com/ns/yang/Cisco-IOS-XE-ipc";
  prefix ios-ipc;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE ipc YANG model.
     Copyright (c) 2023 by Cisco Systems, Inc.
     All rights reserved.";

  revision 2024-11-01 {
    description
      "-Removed the range statement in buffers min-free";
  }
  revision 2024-07-01 {
    description
      "-Added support for ipc YANG model";
  }
  revision 2023-11-01 {
    description
      "-Establish semantic version baseline";
    cisco-semver:module-version "1.0.0";
  }

  grouping config-ipc-grouping {
    container ipc {
      description
        "IPC system configuration";
      container holdq {
        description
          "IPC hold parameters configuration";
        container threshold {
          description
            "IPC hold threshold values configuration";
          leaf lower {
            description
              "Lower threshold value for IPC hold; number of messages.";
            must 'current() < ../upper' {
              error-message
                "Please configure a value for higher threshold first and
                 value lesser than that previously configured for higher
                 threshold";
            }
            type uint16 {
              range "1|10..2000";
            }
            default "1";
          }
          leaf upper {
            description
              "Upper threshold value for IPC hold; number of messages.";
            type uint16 {
              range "20|40..4000";
            }
            default "20";
          }
        }
      }
      container header-cache {
        description
          "IPC Permanent cache configuration";
        container permanent {
          description
            "Number of IPC Permanent caches";
          leaf cache {
            description
              "Maximum number of permanent cache size in bytes";
            type uint16 {
              range "1000..10000";
            }
            default "1000";
          }
          leaf dynamic {
            description
              "Low water mark cache for dynamic growth";
            must 'current() < ../cache' {
              error-message "Invalid input: ipc cache size should be > low water mark";
            }
            type uint16 {
              range "100..2000";
            }
            default "100";
          }
        }
      }
      container buffers {
        description
          "IPC buffer pool configuration";
        leaf min-free {
          description
            "Minimum number of free buffers";
          type uint16;
        }
      }
    }
  }

  augment "/ios:native" {
    uses config-ipc-grouping;
  }
}
